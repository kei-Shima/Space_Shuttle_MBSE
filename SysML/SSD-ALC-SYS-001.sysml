// SysML v2 テキスト：割付（機能 → 部品、部品・機能 → 機器 → 区画、振る舞い → 部品）
// SSD-ALC-SYS-001 割付定義書（機能・機器・区画・振る舞い） の表と同じデータ（機能説明書の機能行、SSD-PHY-ORB-001、振る舞いの定義書）から生成（lib/build_docs_af.py）。
package SSD_ALC_SYS_001 {
    doc /* SSD-ALC-SYS-001 割付定義書（機能・機器・区画・振る舞い）。構造モデル SSD_BLK_SYS_001 と振る舞いのモデル SSD_BEH_ORB_002〜004 を読み込んでから読む。 */
    private import SSD_BLK_SYS_001::*;
    // ---- 機能（機能説明書の機能行。機能説明書ごとの package）
    package Functions {
        package <'SSD-FD-EXT-001'> FN_EXT {
            action <'F-NET-01'> F_NET_01 { doc /* S帯のフォワードリンクとリターンリンクは、地上局網STDNまたはTDRSを経由する。 */ }
            action <'F-NET-02'> F_NET_02 { doc /* 完全運用時のTDRSシステムは、静止軌道上で約130°離れた東西2機の衛星から成り、両機ともホワイトサンズ地上局（WSGT）が支援する。 */ }
            action <'F-NET-03'> F_NET_03 { doc /* 通常高度のオービタがどちらの衛星とも見通せない不可視域（ZOE）が、インド洋上空に存在する。 */ }
            action <'F-NET-04'> F_NET_04 { doc /* WSGTは、シャトルのS帯・Ku帯リターンリンク信号を処理する。 */ }
            action <'F-MCC-01'> F_MCC_01 { doc /* 飛行管制官は、GPC収集データ、ペイロードデータ、計測データ、機上音声を含むダウンリンクを通じて、機上システムの状態を監視する。 */ }
            action <'F-MCC-02'> F_MCC_02 { doc /* DPS担当管制官は、5台のGPC、飛行重要・打上げデータライン、マスメモリなどを含むデータ処理系の状態を判断する。 */ }
            action <'F-MCC-03'> F_MCC_03 { doc /* 軌道離脱噴射の目標データは地上で計算され、アップリンクで機上のGPCに格納される。 */ }
            action <'F-LPS-01'> F_LPS_01 { doc /* 2系統の双方向の打上げデータバス（LDB）が、機上コンピュータ系と打上げ処理システムを結ぶ。 */ }
            action <'F-LPS-02'> F_LPS_02 { doc /* 機体組立棟（VAB）で移動式発射台の上に外部タンク・SRB・オービタを結合して統合機体を点検した後、移動式発射台が機体全体を射点へ運び、射点で整備・点検を行う。 */ }
        }
        package <'SSD-FD-ET-001'> FN_ET {
            action <'F-ET-01'> F_ET_01 { doc /* 外部タンクは液体水素燃料と液体酸素酸化剤を収め、打上げ・上昇中にオービタの3基のSSMEへ加圧供給する。 */ }
            action <'F-ET-02'> F_ET_02 { doc /* SSME停止後に投棄され、大気圏に再突入して分解し、遠隔の海域に落下する（回収しない）。 */ }
            action <'F-ET-03'> F_ET_03 { doc /* 前部の液体酸素タンク、主に電気機器を収める非与圧のインタータンク、後部の液体水素タンクの3主要部から成る。 */ }
            action <'F-ET-04'> F_ET_04 { doc /* 全長153.8 ft、直径27.6 ftで、推進薬充填時にはシャトル構成要素の中で最大かつ最重量である。 */ }
        }
        package <'SSD-FD-ET-ITK-001'> FN_ET_ITK {
            action <'F-ET-ITK-01'> F_ET_ITK_01 { doc /* インタタンクは鋼/アルミのセミモノコックの円筒構造で、両端のフランジでLO2タンクとLH2タンクをつなぐ。 */ }
            action <'F-ET-ITK-02'> F_ET_ITK_02 { doc /* インタタンクはETの計装の部品を収め、地上設備のアームとつながるアンビリカル板（パージガス・危険ガスの検知・水素のボイルオフ）を持つ。 */ }
            action <'F-ET-ITK-03'> F_ET_ITK_03 { doc /* インタタンクは飛行中にベントされる。 */ }
            action <'F-ET-ITK-04'> F_ET_ITK_04 { doc /* インタタンクには前部のSRB/ET結合の推力ビームと金具があり、SRBの荷重をLO2・LH2タンクへ分配する。 */ }
            action <'F-ET-ITK-05'> F_ET_ITK_05 { doc /* インタタンクは長さ270 in・直径331 in・重量12,100 lbである。 */ }
            action <'F-ET-ITK-06'> F_ET_ITK_06 { doc /* ETの構造は推進薬タンクとなり、オービタ・SRBとの間で応力の荷重を受けて分配し、スペースシャトル全体の荷重経路の連続を与える。 */ }
        }
        package <'SSD-FD-ET-LH2-001'> FN_ET_LH2 {
            action <'F-ET-LH2-01'> F_ET_LH2_01 { doc /* LH2タンクは溶接した胴の区分・5つの主リングフレーム・前後の楕円ドームから成るアルミのセミモノコック構造で、32〜34 psiaで運用する。 */ }
            action <'F-ET-LH2-02'> F_ET_LH2_02 { doc /* タンクは渦防止のバッフルとサイフォンの出口を持ち、LH2を直径17 inの管で左後部のアンビリカルへ送り、SSMEの104%運転で465 lb/sで流れる。 */ }
            action <'F-ET-LH2-03'> F_ET_LH2_03 { doc /* LH2タンクの前端にET/オービタの前部結合のポッド支柱、後端に2つの後部結合のボール金具とSRB/ETの後部安定支柱の取付けがある。 */ }
            action <'F-ET-LH2-04'> F_ET_LH2_04 { doc /* LH2タンクは直径331 in・長さ1,160 in・容積53,518 ft3・乾燥重量29,000 lbである。 */ }
            action <'F-ET-LH2-05'> F_ET_LH2_05 { doc /* 6:1の混合比に必要な量より1,100 lb多いLH2を積み、MECOの推進薬比を燃料過多にしてエンジンの浸食を防ぐ。 */ }
            action <'F-ET-LH2-06'> F_ET_LH2_06 { doc /* LH2タンクのアレージ圧が27.7 psia未満ならLH2 ULLAGE PRESSスイッチで手動で制御し、ベント/リリーフ弁の低い作動圧を避けるため35 psiaを超えないようにする。 */ }
        }
        package <'SSD-FD-ET-LOX-001'> FN_ET_LOX {
            action <'F-ET-LOX-01'> F_ET_LOX_01 { doc /* ETは液体水素と液体酸素を収め、上昇中にオービタの3基のSSMEへ加圧して供給する。 */ }
            action <'F-ET-LOX-02'> F_ET_LOX_02 { doc /* ETは前方のLO2タンク、電気部品の大半を収める与圧されないインタタンク、後方のLH2タンクの3つから成る。 */ }
            action <'F-ET-LOX-03'> F_ET_LOX_03 { doc /* LO2タンクは化学切削のゴア・パネル・削り出し金具・リングコードを溶接したアルミのモノコック構造で、20〜22 psigで運用する。 */ }
            action <'F-ET-LOX-04'> F_ET_LOX_04 { doc /* タンクは残液を減らし液の動きを抑える揺動防止・渦防止の装置を持つ。 */ }
            action <'F-ET-LOX-05'> F_ET_LOX_05 { doc /* LO2は直径17 inの供給管でインタタンクを通ってETの外へ出て右後部のアンビリカルへ送られ、SSMEの104%運転で約2,787 lb/sで流れる。 */ }
            action <'F-ET-LOX-06'> F_ET_LOX_06 { doc /* LO2タンクの二重くさびのノーズコーンは抗力と加熱を減らし、電気部品を収め、避雷針となる。 */ }
            action <'F-ET-LOX-07'> F_ET_LOX_07 { doc /* LO2タンクは直径331 in・長さ592 in・空虚重量12,000 lbである。 */ }
        }
        package <'SSD-FD-ET-SEP-001'> FN_ET_SEP {
            action <'F-ET-SEP-01'> F_ET_SEP_01 { doc /* MECOの後、機体の角速度が0.7 deg/sを超えるか供給管の切離しが故障すると「ET SEP INH」が出て、通常・ATOでは分離が抑止される。 */ }
            action <'F-ET-SEP-02'> F_ET_SEP_02 { doc /* RTLSでは、ベントのための短い遅れのあと自動でETを分離する。 */ }
            action <'F-ET-SEP-03'> F_ET_SEP_03 { doc /* ET/オービタの17 inの切離し弁が閉じたと確かめられないときは、開いた弁の推力の減衰を待って再接触を防ぐため、分離をMECO＋6分まで遅らせる。 */ }
            action <'F-ET-SEP-04'> F_ET_SEP_04 { doc /* 分離の直前にオービタの信号でタンブル系が作動してLO2タンク前部の弁を開き、残りのガスを噴き出してETを回転させ、定めた区域に落とす。 */ }
            action <'F-ET-SEP-05'> F_ET_SEP_05 { doc /* 射場安全系（RSS）は、打上げからETの着水までETの推進薬を分散させる手段で、冗長な電池・受信/解読器・アンテナ・火工品から成る。 */ }
            action <'F-ET-SEP-06'> F_ET_SEP_06 { doc /* 同じタンクの低レベルのセンサが3つ以上乾きに故障すると、上り坂の能力が無ければTALアボートを行う。 */ }
            action <'F-ET-SEP-07'> F_ET_SEP_07 { doc /* ETは回収せず、大気に再突入して分解し、遠い海域に落ちる。 */ }
        }
        package <'SSD-FD-ET-TPS-001'> FN_ET_TPS {
            action <'F-ET-TPS-01'> F_ET_TPS_01 { doc /* ETのTPSは吹付けの発泡断熱材と成形済みのアブレータから成り、空気の液化を防ぐフェノールの断熱材も使う。 */ }
            action <'F-ET-TPS-02'> F_ET_TPS_02 { doc /* LH2タンクの取付部には、空気にさらされる金属の液化を防ぎ、LH2への熱の流れを減らす断熱材が必要である。 */ }
            action <'F-ET-TPS-03'> F_ET_TPS_03 { doc /* TPSの重量は4,823 lbである。 */ }
            action <'F-ET-TPS-04'> F_ET_TPS_04 { doc /* TPSはいくつかの組成のアブレータと発泡材を、吹付け・真空成形・成形品の接着などの方法で施工する。 */ }
            action <'F-ET-TPS-05'> F_ET_TPS_05 { doc /* 吹付けのポリイソシアヌレート発泡材（CPR-488）は、LO2タンク・インタタンク・LH2タンクの胴の発泡材である。 */ }
            action <'F-ET-TPS-06'> F_ET_TPS_06 { doc /* 秒読みでは、固定サービス構造の振り腕のキャップがETのLO2タンクのベントを覆って酸素の蒸気を吸い取り、ETに氷ができてオービタのTPSを傷めるのを防ぐ。 */ }
        }
        package <'SSD-FD-ET-UMB-001'> FN_ET_UMB {
            action <'F-ET-UMB-01'> F_ET_UMB_01 { doc /* ETは前部1か所・後部2か所でオービタに結合し、後部の結合部には液体・気体・電気信号・電力をタンクとオービタの間で伝えるアンビリカルがあり、オービタとSRBの間の信号もここを通る。 */ }
            action <'F-ET-UMB-02'> F_ET_UMB_02 { doc /* 2つの後部のETアンビリカル板はオービタ側の板と合わさってボルトで締結され、分離の指令で火工品がボルトを切る。 */ }
            action <'F-ET-UMB-03'> F_ET_UMB_03 { doc /* ETはオービタのアンビリカルとつながる5つの推進薬のアンビリカル弁（LO2タンク2・LH2タンク3）を持つ。 */ }
            action <'F-ET-UMB-04'> F_ET_UMB_04 { doc /* LH2の中間径のアンビリカルは、打上げ前のLH2の予冷のシーケンスだけで使う再循環用である。 */ }
            action <'F-ET-UMB-05'> F_ET_UMB_05 { doc /* ETの2つの電気アンビリカルは、オービタからタンクと2本のSRBへ電力を送り、SRBとETの情報をオービタへ送る。 */ }
            action <'F-ET-UMB-06'> F_ET_UMB_06 { doc /* 推進薬の枯渇センサは燃料・酸化剤に各4つあり、規定の質量を過ぎてから2つが乾きを検知するとエンジンを停止する。 */ }
            action <'F-ET-UMB-07'> F_ET_UMB_07 { doc /* 各タンクの前端にはベント/リリーフ弁があり、飛行中はLH2タンクのアレージ圧36 psig、LO2タンク31 psigで開く。 */ }
        }
        package <'SSD-FD-ORB-001'> FN_ORB {
            action <'F-ORB-01'> F_ORB_01 { doc /* 3基の主エンジンは後部胴体に、軌道制御系（OMS）は後部胴体の2つの外部ポッドに収められている。 */ }
            action <'F-ORB-02'> F_ORB_02 { doc /* 姿勢制御系（RCS）は、2つのOMSポッドと前部胴体機首部のモジュールに収められている。 */ }
            action <'F-ORB-03'> F_ORB_03 { doc /* 各機能は2重または3重に冗長化された機器で構成され、1故障後もミッションを継続でき（フェイルオペレーショナル）、2故障後も着陸地点へ安全に帰還できる（フェイルセーフ）ことを目標としている。 */ }
        }
        package <'SSD-FD-APU-001'> FN_APU {
            action <'F-APU-01'> F_APU_01 { doc /* オービタには独立した3系統の油圧系がある。 */ }
            action <'F-APU-02'> F_APU_02 { doc /* 各系統は、SSMEのジンバルによる推力方向制御、SSMEの各種制御弁、空力舵面（エレボン、ボディフラップ、ラダー／スピードブレーキ）、外部タンク切離しアンビリカルの格納、降着装置の展開、主脚ブレーキとアンチスキッド、前輪操向に油圧を供給する。 */ }
            action <'F-APU-03'> F_APU_03 { doc /* 3台の同一で独立した改良型APUが、油圧系に動力を供給する。 */ }
            action <'F-APU-04'> F_APU_04 { doc /* APUはヒドラジン燃料のタービン駆動装置で、軸動力で油圧ポンプを回し、1台の質量は約88 lb、出力は135馬力である。 */ }
            action <'F-APU-05'> F_APU_05 { doc /* 3台のAPUは打上げ5分前から上昇段階を通して作動し、最初のOMS噴射の後に停止される。 */ }
        }
        package <'SSD-FD-APU-CIR-001'> FN_APU_CIR {
            action <'F-APU-CIR-01'> F_APU_CIR_01 { doc /* 循環ポンプは1台の電動機で駆動する2台の固定容量形歯車ポンプを直列にしたもので、高圧・小流量側（2,500 psig）は休止中のアキュムレータ圧力の維持に、低圧・大流量側（350 psig）は作動油の循環に使う。 */ }
            action <'F-APU-CIR-02'> F_APU_CIR_02 { doc /* 作動油はフレオン／油圧熱交換器を通ってオービタのフレオン冷却ループの熱を受け取り、温度制御のバイパス弁は熱交換器の入口が105°F未満なら熱交換器へ通し、115°F超なら迂回させる。 */ }
            action <'F-APU-CIR-03'> F_APU_CIR_03 { doc /* HYD CIRC PUMPスイッチをGPCにすると、SM GPCは制御温度のどれかが（場所により）0°Fまたは−10°F未満になると循環ポンプを起動し、すべてが20°F超になるか系1で15分・系2・3で10分たつと停止する。 */ }
            action <'F-APU-CIR-04'> F_APU_CIR_04 { doc /* 循環ポンプは1台で2.4 kWを使うため、制御プログラムは同時に1台だけが運転するよう優先順位をつける。 */ }
            action <'F-APU-CIR-05'> F_APU_CIR_05 { doc /* アキュムレータ圧力が1,960 psiまで下がると制御プログラムは再加圧のために循環ポンプを最優先で起動し（このとき2台が同時に運転しうる）、1,960 psiを超えるか2分たつと停止する。 */ }
            action <'F-APU-CIR-06'> F_APU_CIR_06 { doc /* 循環ポンプは、APU制御器が対応するAPUの運転指令を出すと自動的に切り離される。 */ }
            action <'F-APU-CIR-07'> F_APU_CIR_07 { doc /* 循環で温められない油圧配管の部分はサーモスタットで自動制御するヒータで温め、各部は冗長なA・Bのヒータを持ち、パネルA12のHYDRAULIC HEATERスイッチで制御する。 */ }
            action <'F-APU-CIR-08'> F_APU_CIR_08 { doc /* MPS/TVC隔離弁とブレーキ隔離弁は圧力で作動し、操作に100 psid以上が必要なため、APUが止まっているときは循環ポンプで圧力を与える（A10-74A）。 */ }
            action <'F-APU-CIR-09'> F_APU_CIR_09 { doc /* 循環ポンプは、FESの故障時のフレオンループの補助冷却や、APUの始動がEI−13分より遅れるときの作動油の加温にも使う（A10-74A）。 */ }
            action <'F-APU-CIR-10'> F_APU_CIR_10 { doc /* 循環ポンプの本体温度または運転中のリザーバ温度が230°Fを超えると循環ポンプを喪失とするが、循環ポンプの喪失だけでは油圧系の喪失としない（A10-51B）。 */ }
            action <'F-APU-CIR-11'> F_APU_CIR_11 { doc /* 軌道上ではAPUの始動前のリザーバ温度を162°F未満に保つよう努め、そのために循環ポンプの運転時間を減らすか、ATCSを組み替えてフレオン／油圧熱交換器でのフレオン温度を95°F未満に下げる（A10-73E）。 */ }
            action <'F-APU-CIR-12'> F_APU_CIR_12 { doc /* 循環ポンプの起動時には大きな突入電流・4〜5 Vの母線電圧の低下・電磁干渉が生じるため、オービタが電力を与える火工品を使うペイロード展開の間は循環ポンプを入り切りさせない（A10-74B）。 */ }
        }
        package <'SSD-FD-APU-CTL-001'> FN_APU_CTL {
            action <'F-APU-CTL-01'> F_APU_CTL_01 { doc /* 各APUは専用のデジタル制御器を持ち、制御器は故障を検知し、タービン回転数、ギアボックスの加圧、燃料ポンプ・ガス発生器のヒータを制御する。 */ }
            action <'F-APU-CTL-02'> F_APU_CTL_02 { doc /* 制御器はパネルR2のAPU CNTLR PWRスイッチで入切し、ONで制御器とAPUに28 V直流電力が送られ、制御器は内部の2重の遠隔電力制御器で冗長に給電される。 */ }
            action <'F-APU-CTL-03'> F_APU_CTL_03 { doc /* APU 1・2・3の制御器は、それぞれ後部アビオニクスベイ4・5・6の棚3のコールドプレートに取り付けられる。 */ }
            action <'F-APU-CTL-04'> F_APU_CTL_04 { doc /* 通常の運転では主制御弁がパルス動作でAPUの回転数を約74,000 rpm（103%）に保ち、副制御弁は113%で制御しようとする。 */ }
            action <'F-APU-CTL-05'> F_APU_CTL_05 { doc /* 主燃料制御弁のパルスの頻度と長さはAPUにかかる油圧の負荷で決まり、回転数が目標を超えると弁が閉じて燃料はバイパス管で燃料ポンプの入口へ戻る。 */ }
            action <'F-APU-CTL-06'> F_APU_CTL_06 { doc /* APU SPEED SELECTスイッチのNORMは回転数を74,160 rpm（103%±8%）、HIGHは81,360 rpm（113%±8%）に制御し、HIGHでは82,800 rpm（115%）が第2の予備となる。 */ }
            action <'F-APU-CTL-07'> F_APU_CTL_07 { doc /* 自動停止を有効にした制御器は、回転数が57,600 rpm（80%）未満または92,880 rpm（129%）超になるとAPUを停止し、停止の指令で副燃料弁と燃料タンク隔離弁を閉じる。 */ }
            action <'F-APU-CTL-08'> F_APU_CTL_08 { doc /* 始動の論理は、始動指令から10.5秒間は低速度の検査を遅らせて正常な回転数に達する時間を与えるが、過速度の検査は遅らせない。 */ }
            action <'F-APU-CTL-09'> F_APU_CTL_09 { doc /* R2のAPU/HYD READY TO START表示は、ガス発生器温度190°F超、タービン回転数80%未満、WSB制御器の準備完了、燃料タンク隔離弁の開、主油圧ポンプの減圧がそろうと灰色になり、始動して80%を超えるとバーバーポールになる。 */ }
            action <'F-APU-CTL-10'> F_APU_CTL_10 { doc /* タービン回転数は3個の磁気ピックアップ（MPU）が制御器に与え、2個のMPUが故障すると4つの回転数制御チャンネルのうち3つが低速度を判定してAPUが停止する（A10-26の根拠）。 */ }
            action <'F-APU-CTL-11'> F_APU_CTL_11 { doc /* デジタル制御器の冗長性により誤った自動停止は極めて起こりにくく、始動から10.5秒を過ぎた後の誤停止には制御器部品またはMPUの2つ以上の故障が必要である（A10-26の根拠）。 */ }
            action <'F-APU-CTL-12'> F_APU_CTL_12 { doc /* APU AUTO SHUT DOWNスイッチをINHIBITにすると自動停止だけが禁止され、80%未満・129%超ではAPU UNDERSPEED・APU OVERSPEEDの灯と警報音は出続ける。 */ }
        }
        package <'SSD-FD-APU-FUL-001'> FN_APU_FUL {
            action <'F-APU-FUL-01'> F_APU_FUL_01 { doc /* 各APUの燃料系は燃料タンクと燃料タンク隔離弁、燃料ポンプ、燃料制御弁から成り、3台のAPUと燃料系は後部胴体にある。 */ }
            action <'F-APU-FUL-02'> F_APU_FUL_02 { doc /* 燃料は貯蔵性の無水ヒドラジンで、中央に隔膜を持つ総容量約350 lbのタンクに入れ、隔膜の反対側のGN2の圧力で燃料を配管へ押し出す。 */ }
            action <'F-APU-FUL-03'> F_APU_FUL_03 { doc /* 燃料タンクは直径28インチの球形で、タンク1・2は後部胴体の左舷、タンク3は右舷にあり、打上げ前に365 psiに加圧される。 */ }
            action <'F-APU-FUL-04'> F_APU_FUL_04 { doc /* 打上げ前の標準の搭載量は約332 lbで、ミッションでの公称運転時間90分、またはAOAのように約110分連続運転するアボートを支え、運転中のAPUは毎分約3〜3.5 lbの燃料を消費する。 */ }
            action <'F-APU-FUL-05'> F_APU_FUL_05 { doc /* 各燃料配管にはフィルタがあり、配管はフィルタの下流で2本の並列の経路に分かれ、各経路の隔離弁がAPUへの燃料の冗長な経路となる。 */ }
            action <'F-APU-FUL-06'> F_APU_FUL_06 { doc /* 燃料タンク隔離弁は電磁弁で、両弁を閉じた後の熱の戻りで下流の圧力がタンク圧力より40〜200 psi高くなると逆方向に逃がし、弁の温度は弁ごとに2点（APUごとに4点）計測される。 */ }
            action <'F-APU-FUL-07'> F_APU_FUL_07 { doc /* 燃料ポンプは固定容量形の歯車ポンプで、減速ギアボックスを介してタービンに駆動されて約1,400〜1,500 psiを吐出し、出口のフィルタが詰まると約1,725 psiでポンプ入口へ逃がす。 */ }
            action <'F-APU-FUL-08'> F_APU_FUL_08 { doc /* 燃料ポンプ軸のシールからの漏れはAPUごとに500 ccの回収ボトルへ導かれ、ボトルが満杯になると約45 psiaで破裂板が破れて機外へ排出される。 */ }
            action <'F-APU-FUL-09'> F_APU_FUL_09 { doc /* 回転数は燃料ポンプの下流に直列に置いた主・副の電磁パルス式燃料制御弁で制御し、主弁は電力を失うと全開になり、副弁は電力を失うと閉じてAPUを停止させる。 */ }
            action <'F-APU-FUL-10'> F_APU_FUL_10 { doc /* 燃料タンク・燃料配管・水配管のヒータはA・Bの冗長な系に分かれ、パネルA12のAPU HEATER TANK/FUEL LINE/H2O SYSスイッチで選んで1系統ずつ使い、サーモスタットで55〜65°Fに保つ。 */ }
            action <'F-APU-FUL-11'> F_APU_FUL_11 { doc /* 燃料タンク・燃料配管の圧力の説明のつかない低下などでヒドラジンの漏れが確認または疑われる場合はAPUを喪失とし、漏れの確認は地上が行う（A10-1）。 */ }
            action <'F-APU-FUL-12'> F_APU_FUL_12 { doc /* ヒドラジンは35°Fで凍るため、燃料系の温度を35°F超に保てない場合と、燃料配管が2回以上の凍結・解凍を受けた場合はAPUを喪失とする（A10-1）。 */ }
        }
        package <'SSD-FD-APU-HYD-001'> FN_APU_HYD {
            action <'F-APU-HYD-01'> F_APU_HYD_01 { doc /* オービタには独立した3系統の油圧系があり、各系統は主油圧ポンプ、リザーバ、ブートストラップ式アキュムレータ、フィルタ、制御弁、油圧／フレオン熱交換器、電動循環ポンプ、電気ヒータから成る。 */ }
            action <'F-APU-HYD-02'> F_APU_HYD_02 { doc /* 主油圧ポンプは可変容量形で、APUが通常の回転数のとき3,000 psiで0〜63 gpm、高速のとき最大69.6 gpmを送る。 */ }
            action <'F-APU-HYD-03'> F_APU_HYD_03 { doc /* 各主ポンプには電動の減圧弁があり、APUの始動時には吐出圧を2,900〜3,100 psiから500〜1,000 psiに下げてAPUに必要なトルクを減らす。 */ }
            action <'F-APU-HYD-04'> F_APU_HYD_04 { doc /* 各油圧系のフィルタモジュールの高圧逃がし弁は、供給管の圧力が3,850 psidを超えるとポンプ供給管の圧力を戻り管へ逃がす。 */ }
            action <'F-APU-HYD-05'> F_APU_HYD_05 { doc /* リザーバの圧力はアキュムレータのブートストラップ機構（可変面積のピストンで約40:1に減圧）で保たれ、主ポンプと循環ポンプの入口圧力を確保して始動・運転中のキャビテーションを防ぐ。 */ }
            action <'F-APU-HYD-06'> F_APU_HYD_06 { doc /* 主ポンプが止まるとプライオリティ弁が閉じてアキュムレータが約2,500 psiを保ち、主ポンプの入口に約62 psiaを与える（確実な始動に必要な最低入口圧力は20 psia）。 */ }
            action <'F-APU-HYD-07'> F_APU_HYD_07 { doc /* 各リザーバの容量は8ガロンで、作動油は火災の危険を減らす合成炭化水素のMIL-H-83282であり、リザーバの量はMEDS表示のHYDRAULIC QUANTITY計に百分率で示される。 */ }
            action <'F-APU-HYD-08'> F_APU_HYD_08 { doc /* アキュムレータはベローズ式で70°FでGN2を1,700 psigに予圧し、GN2の容積は115立方インチ、作動油の容積は51立方インチである。 */ }
            action <'F-APU-HYD-09'> F_APU_HYD_09 { doc /* 各油圧系はSSMEのジンバル（TVC）、SSMEの制御弁、空力舵面、外部タンク切離しアンビリカルの格納、主脚・前脚の展開、主脚ブレーキとアンチスキッド、前輪操舵（系1、系2が予備）の作動器に圧力を与える。 */ }
            action <'F-APU-HYD-10'> F_APU_HYD_10 { doc /* 切替弁は同じ作動器に割り当てた2つの冗長な系の圧力を比べて十分な圧力の系から作動器へ流す2位置弁で、3系統を割り当てた作動器には主／待機1と待機1／待機2の2個の切替弁がある（A10-51の根拠）。 */ }
            action <'F-APU-HYD-11'> F_APU_HYD_11 { doc /* MPS/TVC隔離弁は軌道上では閉じ、SSMEの油圧の再加圧とSSMEの再配置のときだけ開く（A10-71D）。 */ }
            action <'F-APU-HYD-12'> F_APU_HYD_12 { doc /* 油圧系は、APUの運転中に主ポンプを加圧して要求流量で2,760〜3,500 psiaを出せない場合、確認された隔離できない漏れがある場合、作動油の温度を−40°F超に保てない場合などに喪失とする（A10-51）。 */ }
            action <'F-APU-HYD-13'> F_APU_HYD_13 { doc /* 上昇中に油圧の漏れがあっても対処はMECOの後とし、MECOの後に該当するMPS/TVC隔離弁を閉じ、それでも隔離できなければ低圧（LOW PRESS）にするかAPUを停止する（A10-72A）。 */ }
        }
        package <'SSD-FD-APU-OPS-001'> FN_APU_OPS {
            action <'F-APU-OPS-01'> F_APU_OPS_01 { doc /* WSB制御器は打上げの8時間前に電源を入れてボイラの水タンクを加圧し、APUの起動は燃料を節約するためにできるだけ遅らせ、T−6分15秒に操縦手が起動前の手順を始める。 */ }
            action <'F-APU-OPS-02'> F_APU_OPS_02 { doc /* T−5分に3台を起動して主ポンプを加圧し、T−4分5秒までに3系統の主ポンプ圧力が2,800 psiを超えなければ地上打上げシーケンサ（GLS）が自動で打上げを保留する。 */ }
            action <'F-APU-OPS-03'> F_APU_OPS_03 { doc /* APUとWSBは主エンジンのパージ・投棄・格納のシーケンスが終わると停止するが、AOAを宣言した場合はAPUを止めずに油圧ポンプを減圧して燃料の消費を抑える。 */ }
            action <'F-APU-OPS-04'> F_APU_OPS_04 { doc /* 軌道離脱の前日にはMCCが選んだ1台のAPUを起動し、主ポンプを通常の圧力にして空力舵面の駆動を確かめるFCSチェックアウトを約5分行う。 */ }
            action <'F-APU-OPS-05'> F_APU_OPS_05 { doc /* 軌道離脱噴射の5分前にMCCが選んだ1台を低圧のまま起動し、突入インタフェースの13分前に残る2台を起動して3系統を通常の圧力にする。 */ }
            action <'F-APU-OPS-06'> F_APU_OPS_06 { doc /* 上昇中は、APUや油圧の故障が破局につながらない限り主エンジンへの油圧を途切れさせないようMECOの後まで系を停止せず、動力飛行中に1系統を失うとSSMEが油圧ロックアップになる。 */ }
            action <'F-APU-OPS-07'> F_APU_OPS_07 { doc /* APUは確認された129%超の過速度を除いてMECOの前に停止せず、上昇中やRTLSで1系統以上を失った場合は残るAPUを高速で運転する（A10-25）。 */ }
            action <'F-APU-OPS-08'> F_APU_OPS_08 { doc /* 1系統を失っても通常どおりEOMまで飛行を続け、次の故障で突入中に単一APUの運用となる冗長度の喪失では次のPLSを行う（A10-21A）。 */ }
            action <'F-APU-OPS-09'> F_APU_OPS_09 { doc /* 2系統を失った場合は次のPLSで突入し、全系統の喪失が迫っている場合は最も早い機会にアボートする（優先順位はRTLS・TAL・AOA・初日PLS・PLS・ELS）（A10-21A）。 */ }
            action <'F-APU-OPS-10'> F_APU_OPS_10 { doc /* 突入・アボートと計画では、空力舵面のための2系統、脚展開の冗長、必要時の前輪操舵、半分のブレーキ能力の冗長を確保するためにAPUを「必要」と定義し、単一のAPU/油圧系での着陸は認定されていない（A10-33）。 */ }
            action <'F-APU-OPS-11'> F_APU_OPS_11 { doc /* 軌道離脱の前に必要なAPU燃料とWSBの水は、2〜3系統が使えるときは192 lbと63 lb、1系統のときは203 lbと67 lbである（A10-32B）。 */ }
            action <'F-APU-OPS-12'> F_APU_OPS_12 { doc /* APUの燃料と窒素の漏れは量が少なくなるまで区別できないため燃料の漏れとして扱い、MECOの後はAPUを停止して燃料タンク隔離弁を閉じ、隔離できなければ再起動して燃料を使い切る。 */ }
        }
        package <'SSD-FD-APU-TRB-001'> FN_APU_TRB {
            action <'F-APU-TRB-01'> F_APU_TRB_01 { doc /* ガス発生器は圧力容器にShell 405触媒の床を収めたもので、APUの排気室の内側に取り付けられ、ヒドラジンは触媒に触れると発熱反応で約1,700°Fの高温ガスに分解する。 */ }
            action <'F-APU-TRB-02'> F_APU_TRB_02 { doc /* 高温ガスは単段のタービン翼車を2回通過した後、ガス発生器の外側を流れて機外へ出て、排気ダクトでのガスの温度は約1,000°Fである。 */ }
            action <'F-APU-TRB-03'> F_APU_TRB_03 { doc /* タービンの排気はガス発生器の外側を流れてそれを冷やした後、後部胴体の上部の垂直尾翼の近くにある排気ダクトから機外へ出る。 */ }
            action <'F-APU-TRB-04'> F_APU_TRB_04 { doc /* タービンの軸動力は減速ギアボックスを介して主油圧ポンプ・燃料ポンプ・潤滑油ポンプを駆動し、通常の回転数はそれぞれ3,918 rpm・3,918 rpm・12,215 rpmである。 */ }
            action <'F-APU-TRB-05'> F_APU_TRB_05 { doc /* 潤滑油系は固定容量ポンプを用いる掃気式で、無重量下でも潤滑油ポンプの始動に必要な吸込み圧力を得るためにGN2で加圧され、潤滑油系ごとに専用の窒素容器を持つ。 */ }
            action <'F-APU-TRB-06'> F_APU_TRB_06 { doc /* 潤滑油ポンプは潤滑油を約60 psiに昇圧して対応する水噴霧ボイラへ送って冷却し、潤滑油系ごとの2個のアキュムレータが熱膨張の吸収、最低約15 psiaの圧力の維持、無重量・全高度の潤滑油溜めの役割を果たす。 */ }
            action <'F-APU-TRB-07'> F_APU_TRB_07 { doc /* ガス発生器床・噴射器・排気ガスの温度はBFS SM SYS SUMM 2（GG BED、INJ、EGT）に表示され、床温度は軌道上の停止中にヒータで保温している床の監視に使う。 */ }
            action <'F-APU-TRB-08'> F_APU_TRB_08 { doc /* 噴射器の水冷却系は約180分の通常の冷却期間がとれない場合だけ使い、熱の戻りでヒドラジンが噴射器への燃料配管で爆発しないよう噴射器の分岐流路を400°F未満に冷やす。 */ }
            action <'F-APU-TRB-09'> F_APU_TRB_09 { doc /* 噴射器冷却用の水タンクは後部胴体に1個あって3台のAPUが共用し、約9 lb（連続21分）の水を120 psiのGN2で押し出し、高温での再起動の約6回分に足りる。 */ }
            action <'F-APU-TRB-10'> F_APU_TRB_10 { doc /* 改良型APUの燃料ポンプとガス発生器弁モジュールはヒートシンクと遮熱板による受動冷却で熱の戻りを防ぎ、燃料ポンプが210°F超またはガス発生器弁モジュールが200°F超のときは爆発のおそれがあるため再起動しない。 */ }
            action <'F-APU-TRB-11'> F_APU_TRB_11 { doc /* パネルA12のAPU HEATER GAS GEN/FUEL PUMPスイッチのヒータ（A・B系）は燃料ポンプとガス発生器弁モジュールを約100°Fに保ち、APU HEATER LUBE OIL LINEスイッチのヒータは潤滑油配管を55〜65°Fに保つ。 */ }
            action <'F-APU-TRB-12'> F_APU_TRB_12 { doc /* MECOの後に潤滑油出口温度が325°F超またはギアボックス軸受温度が350°F超になると、MCCの判断でAPUを停止する（A10-24A）。 */ }
            action <'F-APU-TRB-13'> F_APU_TRB_13 { doc /* ボイラによる潤滑油の冷却をすべて失うと、全運転温度に達したAPUは2〜3分で軸受が焼き付く。 */ }
        }
        package <'SSD-FD-APU-WSB-001'> FN_APU_WSB {
            action <'F-APU-WSB-01'> F_APU_WSB_01 { doc /* 水噴霧ボイラ系はAPU・油圧系ごとに1台の同一で独立した3台のボイラから成り、各ボイラは潤滑油系と油圧系の管に水を噴霧して蒸発させることで潤滑油と作動油を冷やし、蒸気は垂直尾翼の右舷側にあるボイラごとの排気ダクトから出る。 */ }
            action <'F-APU-WSB-02'> F_APU_WSB_02 { doc /* 各ボイラは45×31×19インチで制御器とベントノズルを含めて181 lbあり、後部胴体のXo 1340〜1400に取り付けられ、水の容量は142 lbである。 */ }
            action <'F-APU-WSB-03'> F_APU_WSB_03 { doc /* 作動油はボイラを3回、潤滑油は2回通り、作動油の管には3本、潤滑油の管には2本の噴霧バーで水を吹き付け、両者の給水弁は別々に制御される。 */ }
            action <'F-APU-WSB-04'> F_APU_WSB_04 { doc /* 冗長な電気制御器が完全に自動で運転し、潤滑油を約250°F、作動油を210〜220°Fに保つ。 */ }
            action <'F-APU-WSB-05'> F_APU_WSB_05 { doc /* 2台の制御器はパネルR2のBOILER CNTLR/HTRスイッチで選んで給電し（OFFで両方の電源を断つ）、水量はA・Bのどちらかの制御器に給電していれば得られる。 */ }
            action <'F-APU-WSB-06'> F_APU_WSB_06 { doc /* 予め入れた水が蒸発した後で能動冷却が始まる前に残った水が凍る凍結への対策として、ベローズ式の貯水タンクに水とPGMEの混合液（PGME 47%・水53%）を入れ、STS-114以後はボイラとタンクの両方に搭載している。 */ }
            action <'F-APU-WSB-07'> F_APU_WSB_07 { doc /* 各ボイラのGN2は直径6インチの球形容器に70°Fで2,400 psi・0.77 lb入り、R2のBOILER N2 SUPPLYスイッチで操作する遮断弁と24.5〜26 psigに調圧する調圧器を経て水タンクを加圧する。 */ }
            action <'F-APU-WSB-08'> F_APU_WSB_08 { doc /* 打上げ時は各ボイラに最大4.86 lbのPGME/水の混合液を入れておくプールモードで、上昇中に水が沸騰し尽くすと打上げの約13分後に噴霧モードに移り、作動油は上昇中は通常は噴霧冷却を要しない。 */ }
            action <'F-APU-WSB-09'> F_APU_WSB_09 { doc /* 運転中の制御器は作動油と潤滑油の出口温度をそれぞれ208°F・250°Fの設定点と比べて給水弁を開き、水は最大で作動油部に毎分10 lb、潤滑油部に毎分5 lb流れる。 */ }
            action <'F-APU-WSB-10'> F_APU_WSB_10 { doc /* 作動油の流量の一時的な急増（最大63 gpm）でボイラが流量を制限しないよう、ボイラ前後の差圧が49 psiを超えるとばね式のポペット弁が開いて逃がす。 */ }
            action <'F-APU-WSB-11'> F_APU_WSB_11 { doc /* ボイラ・水タンク・蒸気ベントには軌道上の凍結を防ぐ電気ヒータがあり、水タンクとボイラのヒータは50°Fで入り55°Fで切れ、蒸気ベントのヒータはAPU起動の約2時間前から使う。 */ }
            action <'F-APU-WSB-12'> F_APU_WSB_12 { doc /* WSBは、N2・H2Oの漏れが消耗品のレッドラインを割る場合、制御器A・Bのどちらでも潤滑油戻り温度325°F未満・リザーバ温度230°F未満を保てない場合、2つの蒸気ベントヒータをともに失った場合などに喪失とし、WSBの喪失はやがて対応するAPU・油圧系の喪失につながる（A10-101）。 */ }
            action <'F-APU-WSB-13'> F_APU_WSB_13 { doc /* WSBのN2供給弁は、APUの運転の準備と運転中を除いて閉じておく（A10-121）。 */ }
        }
        package <'SSD-FD-CREW-001'> FN_CREW {
            action <'F-CREW-01'> F_CREW_01 { doc /* 乗員系は、他の大きな系に属さない、乗員の効率と快適のための装備（被服、衛生用品、睡眠設備、運動器具、清掃用具、拘束具、収納容器、撮影機器、医療キット、生体計測、放射線計測、空気サンプリング）から成る。 */ }
            action <'F-CREW-02'> F_CREW_02 { doc /* 睡眠設備は寝袋とライナー、または寝台ごとに寝袋1つとライナー2つを備えた固定式の睡眠ステーションで、ステーションの各段は照明と換気の吸気口・排気口を持つ。 */ }
            action <'F-CREW-03'> F_CREW_03 { doc /* 脱出系は乗員の緊急・非常脱出のための装備で、乗員が着用する装備、オービタに組み込まれた機器、射点の外部設備から成り、脱出の形態はミッションの段階（打上げ前・飛行中・着陸後）で異なる。 */ }
            action <'F-CREW-04'> F_CREW_04 { doc /* 飛行中の脱出系は、高度30,000 ft以下の制御された滑空飛行中に乗員が脱出できるよう、与圧服、酸素ボトル、パラシュート、救命いかだ、キャビンベントと側面ハッチ投棄の火工品、脱出ポールを備える。 */ }
            action <'F-CREW-05'> F_CREW_05 { doc /* 射点で破局的な事態が迫った場合、乗員はスライドワイヤのバスケットで安全な区域へ降りる。 */ }
            action <'F-CREW-06'> F_CREW_06 { doc /* 左側の頭上窓は2次の緊急脱出口で、外側の窓ガラスを投棄して20×20インチの開口を得る。 */ }
        }
        package <'SSD-FD-CREW-ESC-001'> FN_CREW_ESC {
            action <'F-CREW-ESC-01'> F_CREW_ESC_01 { doc /* 脱出系は乗員が着る装備、オービタに組み込んだ機器、射点の外部設備から成り、脱出の形態は打上げ前・飛行中・着陸後で異なる。 */ }
            action <'F-CREW-ESC-02'> F_CREW_ESC_02 { doc /* 飛行中の脱出は高度30,000 ft以下の制御された滑空中に行い、与圧服・酸素ボトル・パラシュート・救命いかだ・キャビンベントと側面ハッチ投棄の火工品・脱出ポールを使う。 */ }
            action <'F-CREW-ESC-03'> F_CREW_ESC_03 { doc /* 先進乗員脱出服（ACES）は全与圧服で、2重の服制御器が圧力を保ち、全膨張で絶対圧3.67 psiaを与える。 */ }
            action <'F-CREW-ESC-04'> F_CREW_ESC_04 { doc /* ACESの酸素マニホールドは、オービタの酸素供給ホース、パラシュートハーネスの非常用酸素ボトル、呼吸用の調整器をつなぐ。 */ }
            action <'F-CREW-ESC-05'> F_CREW_ESC_05 { doc /* 側面ハッチの3組の火工品は前方のT字ハンドルで同時に作動し、ヒンジを切る線形成形爆薬4個、70本の破断ボルトを割る膨張チューブ2組、ハッチを約45 ft/sで離すスラスタパック3個から成る。 */ }
            action <'F-CREW-ESC-06'> F_CREW_ESC_06 { doc /* 脱出ポールは、側面ハッチから出る乗員を左翼に当たらない軌道に導く、ばね式の伸縮する湾曲した筒である。 */ }
            action <'F-CREW-ESC-07'> F_CREW_ESC_07 { doc /* 側面ハッチから出られないときは左舷の頭上窓（窓8）が2次の非常脱出口となり、各乗員は降下器（Sky Genie）で右舷側の地上へ降りる。 */ }
            action <'F-CREW-ESC-08'> F_CREW_ESC_08 { doc /* 射点の非常脱出では乗員はスライドワイヤのバスケットで安全な区域へ降り、その終点の近くにM-113装甲車が待機する。 */ }
            action <'F-CREW-ESC-09'> F_CREW_ESC_09 { doc /* キャビンベントとハッチ投棄の火工品はオービタの電力を要さず、電力を失っても作動できる。 */ }
        }
        package <'SSD-FD-CREW-HAB-001'> FN_CREW_HAB {
            action <'F-CREW-HAB-01'> F_CREW_HAB_01 { doc /* 乗員の被服は飛行前に各乗員が必須・任意の装備の一覧から選び、軌道上ではズボン・上着・シャツ・睡眠用ショーツなどを着る。 */ }
            action <'F-CREW-HAB-02'> F_CREW_HAB_02 { doc /* 洗顔用の常温の温水はギャレーの補助ポートにつないだ個人衛生ホース（PHH）から得て、ほかの衛生用品は中甲板のロッカーなどに収める。 */ }
            action <'F-CREW-HAB-03'> F_CREW_HAB_03 { doc /* 1日は通常8時間の睡眠と16時間の活動に分ける。 */ }
            action <'F-CREW-HAB-04'> F_CREW_HAB_04 { doc /* 睡眠設備は寝袋とライナー、または寝台ごとに寝袋1つとライナー2つの固定式睡眠ステーションで、寝袋は中甲板右舷の壁に取り付けて軌道上で移す。 */ }
            action <'F-CREW-HAB-05'> F_CREW_HAB_05 { doc /* 24時間運用のミッションでは4段の固定式睡眠ステーションを中甲板右舷に置き、各段は照明と換気の吸気口・排気口を持つ。 */ }
            action <'F-CREW-HAB-06'> F_CREW_HAB_06 { doc /* 運動は心肺機能の低下と骨・筋肉の減少を防ぐためで、主な器具は中甲板の床のスタッドに取り付ける自転車エルゴメータ（CE）である。 */ }
            action <'F-CREW-HAB-07'> F_CREW_HAB_07 { doc /* 各乗員は1日に何度か5〜15分の清掃作業（廃棄物処理区画・食事区域・空気フィルタの清掃、ごみ処理、LiOHキャニスタの交換）を行う。 */ }
            action <'F-CREW-HAB-08'> F_CREW_HAB_08 { doc /* 中甲板の床下の8 ft3の湿ったごみの収納区画（Volume F）は、臭気を抑えるため船外へ約3 lb/日で排気する。 */ }
        }
        package <'SSD-FD-CREW-LTG-001'> FN_CREW_LTG {
            action <'F-CREW-LTG-01'> F_CREW_LTG_01 { doc /* 照明系は機内と機外の照明から成り、機内照明は投光照明・パネル照明・計器照明・数字表示・表示灯である。 */ }
            action <'F-CREW-LTG-02'> F_CREW_LTG_02 { doc /* 非常照明は、必須母線からの別の電源入力で給電される特定の照明器具である。 */ }
            action <'F-CREW-LTG-03'> F_CREW_LTG_03 { doc /* 中甲板の天井には8つの投光照明器具があり、パネルMO13QのMID DECK FLOODSスイッチで個別に入切する。 */ }
            action <'F-CREW-LTG-04'> F_CREW_LTG_04 { doc /* 機外の投光照明は、ペイロードベイドアの操作・EVA・RMSの操作・ステーションキーピング・ドッキングの視界を良くする。 */ }
            action <'F-CREW-LTG-05'> F_CREW_LTG_05 { doc /* ペイロードベイの投光照明はメタルハライド灯で、各灯に高電圧を作るDC/DC電源があり、電力は中部電力制御組立から10 Aの遠隔電力制御器で供給する。 */ }
            action <'F-CREW-LTG-06'> F_CREW_LTG_06 { doc /* メタルハライド灯の電源は、フレオンループで冷やす投光照明電子組立に取り付けられる。 */ }
            action <'F-CREW-LTG-07'> F_CREW_LTG_07 { doc /* 操縦室の照明をすべて点けると消費電力は1〜2 kWになり、ペイロードベイの投光照明は点けたら10分以上点けたままにする。 */ }
        }
        package <'SSD-FD-CREW-MED-001'> FN_CREW_MED {
            action <'F-CREW-MED-01'> F_CREW_MED_01 { doc /* SOMSは軽い病気やけがの飛行中の治療と、重い傷病者を地球に帰るまで安定させるためのもので、主に用途別のサブパックに分けた医療キットから成る。 */ }
            action <'F-CREW-MED-02'> F_CREW_MED_02 { doc /* SOMSの多くは中甲板のロッカー1つにまとめて収め、使うときに取り出してベルクロで取り付ける。 */ }
            action <'F-CREW-MED-03'> F_CREW_MED_03 { doc /* 蘇生器は中甲板のパネルMO32M・MO69Mと飛行甲板のパネルC6でオービタの酸素供給につなぎ、100%の補助酸素を手動または要求流量で与える。 */ }
            action <'F-CREW-MED-04'> F_CREW_MED_04 { doc /* 汚染除去キット（CCK）の非常用洗眼器はギャレーの清水につないで、化学やけどや煙で傷んだ目を洗う。 */ }
            action <'F-CREW-MED-05'> F_CREW_MED_05 { doc /* 生体計測系（OBS）は乗員の心電図の信号をアビオニクスに送り、デジタルデータにして実時間で地上へ送るか記録する。 */ }
            action <'F-CREW-MED-06'> F_CREW_MED_06 { doc /* 各乗員は飛行の間ずっと受動線量計を身に着け、太陽フレアなどのときは能動線量計を読み出す。 */ }
            action <'F-CREW-MED-07'> F_CREW_MED_07 { doc /* 空気サンプリングは、採気容器（GSC）による飛行後の分析と、一酸化炭素・シアン化水素・塩化水素の実時間の分析の2つの方式がある。 */ }
        }
        package <'SSD-FD-CREW-OPS-001'> FN_CREW_OPS {
            action <'F-CREW-OPS-01'> F_CREW_OPS_01 { doc /* 医療キットのうち「医師の承認が必要」とした品は、医師でない乗員はFCRの航空医官か搭乗した医師の指示でのみ使い、使った品は記録する。 */ }
            action <'F-CREW-OPS-02'> F_CREW_OPS_02 { doc /* 乗員の健康に関わる飛行の早期終了は実時間で判断し、軌道上で適切な治療ができないときだけ考える。 */ }
            action <'F-CREW-OPS-03'> F_CREW_OPS_03 { doc /* CDR・PLT・MS2にはFD04からEOM-1まで少なくとも1日おきに処方の運動を組み、11日を超える飛行ではほかの乗員にも3日ごとに組む。 */ }
            action <'F-CREW-OPS-04'> F_CREW_OPS_04 { doc /* 居住区画の24時間平均の騒音が74 dBA以上なら、騒音源の電源を切る、日程を組み替える、睡眠中に耳栓を使うなどの処置をとる。 */ }
            action <'F-CREW-OPS-05'> F_CREW_OPS_05 { doc /* 乗員の電離放射線の被ばくは法定の限度を守り、合理的に達成できる限り低く（ALARA）保つ。 */ }
            action <'F-CREW-OPS-06'> F_CREW_OPS_06 { doc /* 生命維持のGo/No-Go基準は、LESの酸素供給系（2系統）の1系統の喪失でMDF、2系統の喪失で次のPLSとする。 */ }
            action <'F-CREW-OPS-07'> F_CREW_OPS_07 { doc /* 機上の診断装置と乗員からの情報により、管制センターの航空医官と相談して傷病を診断・治療する。 */ }
            action <'F-CREW-OPS-08'> F_CREW_OPS_08 { doc /* これまでの飛行の被ばく線量は0.05〜0.07 remで、乗員の被ばく限度を十分下回る。 */ }
        }
        package <'SSD-FD-CREW-STW-001'> FN_CREW_STW {
            action <'F-CREW-STW-01'> F_CREW_STW_01 { doc /* 収納はおもに硬い容器と柔らかい容器から成り、収納場所は飛行甲板・中甲板・エアロック・下部機器ベイにある。 */ }
            action <'F-CREW-STW-02'> F_CREW_STW_02 { doc /* モジュラーロッカーは交換可能で、ばね付きの拘束ボルトでオービタに取り付け、軌道上で乗員が外したり付けたりできる。 */ }
            action <'F-CREW-STW-03'> F_CREW_STW_03 { doc /* 収納容積は約150 ft3で、その95%近くが中甲板にあり、ロッカー1つは2 ft3・68 lb以下を収める。 */ }
            action <'F-CREW-STW-04'> F_CREW_STW_04 { doc /* 中甲板の前方アビオニクスベイに33個、エアロックの右舷側に11個のロッカーを取り付けられる。 */ }
            action <'F-CREW-STW-05'> F_CREW_STW_05 { doc /* 床下には7つの収納区画があり、Volume F は湿ったごみ、Volume G は非常用の衛生用品、Volume H は EVA の付属品を収める。 */ }
            action <'F-CREW-STW-06'> F_CREW_STW_06 { doc /* 拘束具（足ループ・座席拘束・保持ネット・ベルクロなど）と移動補助具（手すり・中甲板の非常脱出ネット・甲板間のはしご）で、乗員は乗込み・退出・軌道飛行の作業を安全に行う。 */ }
            action <'F-CREW-STW-07'> F_CREW_STW_07 { doc /* 中甲板収納ラック（MAR）は側面ハッチの前方に置き、約15 ft3・約340 lbまでの小型ペイロードや実験を収める。 */ }
        }
        package <'SSD-FD-CT-001'> FN_CT {
            action <'F-CT-01'> F_CT_01 { doc /* S帯FM、S帯PM、Ku帯、UHFの各系が、RF信号でオービタと地上の間の情報を伝送する。 */ }
            action <'F-CT-02'> F_CT_02 { doc /* ペイロード通信系はハードラインまたはRFでオービタとペイロードの間の情報を伝送し、音声系は機内の音声通信を、CCTVは作業の目視監視と記録を担う。 */ }
            action <'F-CT-03'> F_CT_03 { doc /* NASAのS帯フォワードリンクは2,041.9 MHz（主）または2,106.4 MHz（副）、リターンリンクは2,217.5 MHz（主）または2,287.5 MHz（副）の位相変調で、STDNまたはTDRSを経由する。 */ }
            action <'F-CT-04'> F_CT_04 { doc /* Ku帯系は、ランデブ時に分離衛星の距離と角度を測るレーダと、双方向通信の二役を担う。 */ }
        }
        package <'SSD-FD-CT-AUD-001'> FN_CT_AUD {
            action <'F-CT-AUD-01'> F_CT_AUD_01 { doc /* 音声分配系（ADS）は機内に音声信号を配り、乗員どうしとS帯PM・Ku帯・UHF・SSOR経由のMCCなど外部との通信の手段となり、C/W系のトーン信号と3台のTACANの識別符号の音声も扱う。 */ }
            action <'F-CT-AUD-02'> F_CT_AUD_02 { doc /* 主な要素は、内部冗長のLRUで中央交換台として働くACCU、乗員通信局のATU、スピーカユニット、音声センタパネル、携帯通信機器、CCUジャックである。 */ }
            action <'F-CT-AUD-03'> F_CT_AUD_03 { doc /* 音声系には、A/G 1、A/G 2、A/A（UHF SPLX）、ICOM A、ICOM B、PAGE、C/W、TACANの8つのループがある。 */ }
            action <'F-CT-AUD-04'> F_CT_AUD_04 { doc /* A/G 1・2はS帯PM・Ku帯系で地上と、EVA中はSSORでEV乗員と通信し、A/AはUHFに対応する地上局の上空でUHF（ATC）系によりMCCと通信する。 */ }
            action <'F-CT-AUD-05'> F_CT_AUD_05 { doc /* ACCUはミッドデッキの前方アビオニクスベイにあり、同じ筐体に冗長な2台を持つが、一度に使うのは1台である。 */ }
            action <'F-CT-AUD-06'> F_CT_AUD_06 { doc /* パネルC3のAUDIO CENTERスイッチを1にするとESS 2CA AUD CTR 1、2にするとMN C AUD CTR 2の遮断器（パネルR14）から給電され、OFFではACCUの電力がすべて断たれる。 */ }
            action <'F-CT-AUD-07'> F_CT_AUD_07 { doc /* ACCUは打上げアンビリカルのICOM A・Bのチャネルも働かせ、どの乗員局のATUも打上げ管制センター（LCC）とインターコムで通話でき、アンビリカルで扱うのはインターコムだけである。 */ }
            action <'F-CT-AUD-08'> F_CT_AUD_08 { doc /* ATUは乗員室の6か所（パネルO5、O9、R10、L9、MO42F、AW18D）にあって各音声ループの選択と音量を制御し、電源スイッチはAUD/TONE、AUD、OFFの3位置である。 */ }
            action <'F-CT-AUD-09'> F_CT_AUD_09 { doc /* 4台のATU（パネルO5、O9、AW18D、R10）は、故障したATUの乗員がCONTROLノブで別のATUへ切り替えられる。 */ }
            action <'F-CT-AUD-10'> F_CT_AUD_10 { doc /* スピーカユニットはパネルA2とMO29Jにあり、上のスピーカは音声用、下はクラクソン・サイレン専用である。 */ }
            action <'F-CT-AUD-11'> F_CT_AUD_11 { doc /* パネルA1Rの音声センタは、SSOR（UHFスイッチ）・ドッキングしたISS（Spacelabスイッチ）との音声と記録するループを選び、VOICE RECORD SELECTの2つのノブで選んだ音声をNSP経由で記録器へ送る。 */ }
            action <'F-CT-AUD-12'> F_CT_AUD_12 { doc /* 打上げ・再突入では、各乗員が騒音を和らげA/G通信を明瞭にするため打上げ・再突入用ヘルメットを着け、CCAのヘッドセットをHIU・通信ケーブル・CCUを介してATUにつなぐ。 */ }
        }
        package <'SSD-FD-CT-CCTV-001'> FN_CT_CCTV {
            action <'F-CT-CCTV-01'> F_CT_CCTV_01 { doc /* CCTVは軌道上でオービタとペイロードの作業を支援し、実時間と記録の映像をS帯FM、S帯PM、Ku帯の通信系でMCCへ送る。 */ }
            action <'F-CT-CCTV-02'> F_CT_CCTV_02 { doc /* CCTVは映像処理装置、テレビカメラ、PTU、カムコーダ、VTR、カラーモニタ（CTVM）と配線・付属品から成り、大半の構成指令はMCCのINCOも実行できる。 */ }
            action <'F-CT-CCTV-03'> F_CT_CCTV_03 { doc /* ペイロードベイにはCTVC（カラー）、ITVC（白黒・低照度用）、Videospectionの3種類のカメラを搭載し、カメラとPTUには-8°Cで入り0°Cで切れるサーモスタット制御のヒータがある。 */ }
            action <'F-CT-CCTV-04'> F_CT_CCTV_04 { doc /* VCUはCCTVの中央処理装置で、RCUとVSUの2つのLRUから成り、後部フライトデッキのパネルR17・R18の裏にあってキャビンファンで強制空冷される。 */ }
            action <'F-CT-CCTV-05'> F_CT_CCTV_05 { doc /* RCUは乗員とMCCのすべてのCCTV指令を受け、MCCがアップリンクで指令できるのはパネルA7UのTV POWER CONTROLスイッチがCMDのときだけである。 */ }
            action <'F-CT-CCTV-06'> F_CT_CCTV_06 { doc /* RCUの同期信号はカメラとVSUへ配られ、カメラへの指令は同期信号に埋め込まれ、アドレスが合うカメラだけが応答する。 */ }
            action <'F-CT-CCTV-07'> F_CT_CCTV_07 { doc /* VSUは最大13入力・7出力（パネルA7Uで使えるのは10入力・4出力）で映像を切り替え、カメラのID・温度・パン/チルト角を読み、45°Cを超えるカメラを検知するとRCUへ過熱警告を送る。 */ }
            action <'F-CT-CCTV-08'> F_CT_CCTV_08 { doc /* VPU（STS-92から）はCCTVからISSへ2本、ISSからCCTVへ1本の映像を渡し、EVAヘルメットカメラ（WVS）のインタフェースボックスを含む。 */ }
            action <'F-CT-CCTV-09'> F_CT_CCTV_09 { doc /* DTV（STS-110から）はCCTVのアナログNTSC映像をデジタルに変換して記録またはKu帯のチャネル3（PAYLOAD MAX）でMCCへ送り、そのVIPはAC2 PAYLOAD 3相から給電される。 */ }
            action <'F-CT-CCTV-10'> F_CT_CCTV_10 { doc /* PTUはカメラA・B・C・DとRMSの肘カメラに使い、正負各170°のパン・チルトを高速12°/s、低速1.2°/sで行う。 */ }
            action <'F-CT-CCTV-11'> F_CT_CCTV_11 { doc /* パネルA3には10インチのカラーモニタ（CTVM）2台が常に搭載され、NTSCとFSCのカラー映像を表示する。 */ }
            action <'F-CT-CCTV-12'> F_CT_CCTV_12 { doc /* OBSS（STS-114から）は右舷シルに格納した50 ftのブームの後端に2つのセンサパッケージを持ち、TPSの点検映像とデータはKu帯でMCCへ送られる。 */ }
        }
        package <'SSD-FD-CT-INST-001'> FN_CT_INST {
            action <'F-CT-INST-01'> F_CT_INST_01 { doc /* オービタのOIは機体とペイロードの変換器・センサの情報を収集・処理・分配し、監視するパラメータは3,000を超える。 */ }
            action <'F-CT-INST-02'> F_CT_INST_02 { doc /* 計装系は変換器、DSC 14台、MDM 7台、PCMMU 2台、記録器2台、主時刻装置、機上点検装置から成り、センサと一部のDSCを除き前方・後方のアビオニクスベイにある。 */ }
            action <'F-CT-INST-03'> F_CT_INST_03 { doc /* DSCは周波数・温度・角速度・電圧・電流などのセンサの信号をMDMが受け付ける0〜5 V dcに変換し、14台は前方4、後方3、ペイロードベイ下3、左右の尾部4に分かれる。 */ }
            action <'F-CT-INST-04'> F_CT_INST_04 { doc /* OI MDMは多重化器としてだけ働き、PCMMUの要求に応じてデータを選び・デジタル化してOIデータバスで送り（要求・応答方式）、前方4台（OF）・後方3台（OA）がある。 */ }
            action <'F-CT-INST-05'> F_CT_INST_05 { doc /* PCMMUはOI MDMのデータ、GPCのダウンリスト、PDIのペイロードテレメトリを受け、テレメトリ形式ロード（TFL）に従ってインタリーブ・形式化する。 */ }
            action <'F-CT-INST-06'> F_CT_INST_06 { doc /* PCMMUのテレメトリはNSPを経てSSRにも送られて記録され、後でS帯FMまたはKu帯でダウンリンクされる。 */ }
            action <'F-CT-INST-07'> F_CT_INST_07 { doc /* PCMMUはPROMとRAMの2つの形式メモリを持ち、電源を切ると（予備への切替時など）TFLはPROMの固定形式に変わる。 */ }
            action <'F-CT-INST-08'> F_CT_INST_08 { doc /* 各MDMの主ポートはPCMMU 1、副ポートはPCMMU 2と働き、PCMMUはMTUから同期クロックを受け、それが無いときは自らの時刻で同期信号をPDIとNSPへ送り続ける。 */ }
            action <'F-CT-INST-09'> F_CT_INST_09 { doc /* 2台のSSRはOI系のデジタル音声とPCMデータを記録・ダンプし、MMUに内蔵されているためパネルA1ではMMU1・MMU2と表示され、乗員の操作器はなく地上指令だけで制御される。 */ }
            action <'F-CT-INST-10'> F_CT_INST_10 { doc /* ペイロード通信系のPI、PSP、PDI、PCMMUは前方アビオニクスベイにあり、ペイロード通信系への指令はペイロードMDM 1・2からGCILCを経て送られる。 */ }
            action <'F-CT-INST-11'> F_CT_INST_11 { doc /* PIは分離したペイロードとの全二重のRF通信を行う送受信機・トランスポンダで、PSPと互換のテレメトリはPSPが副搬送波から復調してPDIへ送り、互換でないものはKu帯系へ直接送る（ベントパイプ）。 */ }
            action <'F-CT-INST-12'> F_CT_INST_12 { doc /* PDIは付属・分離したペイロードからの最大6入力と地上支援装置の1入力を受け、4台のデコミュテータで最大4つのデータ流を処理してPCMMUへ送る。 */ }
        }
        package <'SSD-FD-CT-KU-001'> FN_CT_KU {
            action <'F-CT-KU-01'> F_CT_KU_01 { doc /* Ku帯系はペイロードベイドアを開いた後に展開するアンテナでTDRSを介して地上と送受信し、ランデブではレーダとしても使えるが、通信とレーダを同時には使えない。 */ }
            action <'F-CT-KU-02'> F_CT_KU_02 { doc /* 通信モードでは、NSPがリターンリンクのデータをKu帯信号処理器とS帯PMトランスポンダの両方へ送り、フォワードリンクはKu帯とS帯PMの一方だけをNSPが処理する。 */ }
            action <'F-CT-KU-03'> F_CT_KU_03 { doc /* モード1のリターンリンクは3チャネルで、チャネル1は192 kbpsの運用データ、チャネル2は2 Mbpsの低データレート源（ペイロードインタロゲータ、OCA、MMU 1・2のSSR）、チャネル3は50 MbpsのPL MAX（DTVなど）である。 */ }
            action <'F-CT-KU-04'> F_CT_KU_04 { doc /* モード2ではチャネル3が4 Mbpsの高データレート源となり、ペイロードのデータのほか実時間のCCTV映像のダウンリンクを選べる。 */ }
            action <'F-CT-KU-05'> F_CT_KU_05 { doc /* モード1のフォワードリンクは72 kbpsの運用データのほか128 kbpsのOCAのアップリンクを含み、COMMモードではEA1を経たKu帯信号処理器が音声とコマンドをNSPへ送る。 */ }
            action <'F-CT-KU-06'> F_CT_KU_06 { doc /* 展開アンテナ組立は右舷のシルロンジロンに取り付けられ、2軸ジンバルの高利得アンテナ（直径3 ftのグラファイトエポキシ製パラボラ）、ジャイロ組立、RF電子箱から成り、組立の質量は180 lb、系全体は304 lbである。 */ }
            action <'F-CT-KU-07'> F_CT_KU_07 { doc /* ベータジンバルの動きが162°に限られるため、極の周りに直径4°、ペイロードベイ側に直径32°の非カバー域があり、アンテナはパネルA1Uの手動またはSMソフトウェアで指向する。 */ }
            action <'F-CT-KU-08'> F_CT_KU_08 { doc /* MCCは、ペイロード、EVA乗員、ISSをKu帯の放射から守るため、ベータ角によるマスク（beta MASK・beta + MASK）やEVA防護域で送信機を止めるマスキングを地上指令で設定する。 */ }
            action <'F-CT-KU-09'> F_CT_KU_09 { doc /* アンテナの展開・格納は通常23秒かかり、突入に備えてペイロードベイドアを閉じる前に格納しなければならず、通常の格納とDIRECT STOWができないときは組立を投棄する（約4秒）。 */ }
            action <'F-CT-KU-10'> F_CT_KU_10 { doc /* ランデブではレーダがGNC計算機のランデブ航法データを更新するセンサとして目標の角度・角速度・距離変化率を与え、受動（RDR PASSIVE）と協力（RDR COOP）のモードがあるが、これまでRDR PASSIVEだけが使われた。 */ }
            action <'F-CT-KU-11'> F_CT_KU_11 { doc /* GPCモードでは、GNC SPEC 33の2つの指令によりGNCの目標位置をSMのアンテナ管理プログラムへ送り、指向角と距離をペイロード1データバスとPF1 MDMを経てKu帯系へ送って探索・自動追尾させる。 */ }
            action <'F-CT-KU-12'> F_CT_KU_12 { doc /* SM COMMUNICATIONS表示（SPEC 76）は、Ku帯の温度（PA・GMBL・GYRO）、出力電力、フレーム同期、モード（COMM・RDR）を示す。 */ }
        }
        package <'SSD-FD-CT-OPS-001'> FN_CT_OPS {
            action <'F-CT-OPS-01'> F_CT_OPS_01 { doc /* GCIL（GCILC）はS帯PM・S帯FM・Ku帯・ペイロード通信・CCTVの選択した機能を制御し、各系のCONTROLスイッチがPANELなら乗員のパネルスイッチ、COMMANDならGCIL経由の地上指令で制御する。 */ }
            action <'F-CT-OPS-02'> F_CT_OPS_02 { doc /* 地上からの指令はすべてS帯のアップリンクまたはKu帯のフォワードリンクでNSPとFF MDMを経てGPCへ送られ、GCILで制御する通信系を組み替える指令はGPCからPF MDMを経てGCILへ送られる。 */ }
            action <'F-CT-OPS-03'> F_CT_OPS_03 { doc /* S帯PM系は系統2のLRUを飛行全体を通じてコマンドで選び（機上のスイッチは系統1の構成）、地上が運用の主体となってTDRS・GSTDN・SGLSのモードを切り替え、アンテナはGPCの自動選択で管理する。 */ }
            action <'F-CT-OPS-04'> F_CT_OPS_04 { doc /* 上昇中に飛行を打ち切る通信の故障はなく、打上げではS帯PMの音声を主とし、UHFを送受信モードでS帯PMのバックアップに構成する。 */ }
            action <'F-CT-OPS-05'> F_CT_OPS_05 { doc /* SMが使えるときは、サイトインビューの旗がなければSMソフトウェアがアップリンクの指令を自動で遮断し、SMも暗号化も使えないときは乗員がパネルC3のUPLINKスイッチで遮断する。 */ }
            action <'F-CT-OPS-06'> F_CT_OPS_06 { doc /* Ku帯系は、ペイロードがペイロードベイドアの包絡域を超えない限り21度の「beta plus mask」モードで運用し、ベイのどの部分も10 V/m（ICDの限度）を超える放射を受けないようにする。 */ }
            action <'F-CT-OPS-07'> F_CT_OPS_07 { doc /* Ku帯のベータマスクまたはオービタ構造の遮蔽で守られる区域でのEVAでは、Ku帯をAOS中は指向の制約なしに運用し、LOS中は待機にして、EVA乗員の被曝をEMUの仕様の20 V/m未満に保つ。 */ }
            action <'F-CT-OPS-08'> F_CT_OPS_08 { doc /* 記録器は地上から管理して各LOSの間に1台が記録しているようにし、運用データと音声（192 kbps）は活動の多い期間か乗員の音声記録が要るときに記録し、それ以外はデータ（128 kbps）だけを記録する。 */ }
            action <'F-CT-OPS-09'> F_CT_OPS_09 { doc /* 通信のGo/No-Go基準（A11-1001）は、2-way音声（A/G 1・2・UHFの3系統）、コマンド、テレメトリ、NSP・トランスポンダのアップリンク・ダウンリンク、ACCU、PCMMUなどの喪失ごとにMDFと次のPLSの判断を定める。 */ }
            action <'F-CT-OPS-10'> F_CT_OPS_10 { doc /* PCMMUは実時間・記録のテレメトリと乗員表示・クラス3アラートのための機上データを供給し、故障の回避策がないため、1台を失うとMDF、2台を失うと次のPLSとする。 */ }
            action <'F-CT-OPS-11'> F_CT_OPS_11 { doc /* ACCUを1台失ったときはACCUバイパスIFMの半分（J4）をなるべく早く行って飛行を続け、それが失敗すれば次のPLSとし、2台とも失ったときはIFMを完了してMDFとする。 */ }
            action <'F-CT-OPS-12'> F_CT_OPS_12 { doc /* 全音声を失ったときは、ACCUバイパスコネクタを取り付け、コマンドが使えればKu帯を展開・起動してOCAの通話を試み、なお音声が得られなければ次の日のPLSへ軌道離脱し、スクラッチパッド行でMCCへ知らせる（MAL COMM SSR-1）。 */ }
        }
        package <'SSD-FD-CT-SBD-001'> FN_CT_SBD {
            action <'F-CT-SBD-01'> F_CT_SBD_01 { doc /* S帯PM系は、地上局またはTDRSを経由してオービタと地上の間の双方向通信を行い、コマンド、音声、テレメトリ、トーン測距、2-wayドップラ追跡の5つの機能のチャネルを持つ。 */ }
            action <'F-CT-SBD-02'> F_CT_SBD_02 { doc /* フォワードリンクの高データレートは72 kbps（A/G音声2チャネル各32 kbpsとコマンド8 kbps）、リターンリンクの高データレートは192 kbps（A/G音声2チャネル各32 kbpsとテレメトリ128 kbps）で、2-way測距はTDRSを経由しては働かない。 */ }
            action <'F-CT-SBD-03'> F_CT_SBD_03 { doc /* 電力モードはSGLS、STDN LO・HI、TDRS DATA・RNGから選び、高電力モード（TDRSとSTDN HI）では受信信号を前置増幅器、送信信号を電力増幅器に通し、低電力モード（STDN LOとSGLS）では増幅しない。 */ }
            action <'F-CT-SBD-04'> F_CT_SBD_04 { doc /* 前方胴体の外板に約90°おきに4基のクワッドアンテナがあり、各アンテナが前方・後方の2つのビームを持つため実質8つのアンテナとして働き、GPC制御（PASS SMまたはBFS）、アップリンクコマンド、パネルC3の手動で選択する。 */ }
            action <'F-CT-SBD-05'> F_CT_SBD_05 { doc /* 前置増幅器はTDRSとSTDN HIのモードで使う2台の冗長な装置で、一度に1台を使い、約25 dBのRF利得を与える。 */ }
            action <'F-CT-SBD-06'> F_CT_SBD_06 { doc /* 電力増幅器は2台の冗長（公称利得約17 dB）で進行波管を使い、コールドスタートからOPERATEを選ぶと140秒のタイマで予熱し、STANDBYではフィラメントを暖めておく。 */ }
            action <'F-CT-SBD-07'> F_CT_SBD_07 { doc /* トランスポンダは2台の冗長で一度に1台が働き、フォワードリンクのコマンドと音声をNSPへ渡してNSPからリターンリンクのテレメトリと音声を受け、2-wayドップラと2-wayトーン測距の信号をコヒーレントに折り返す。 */ }
            action <'F-CT-SBD-08'> F_CT_SBD_08 { doc /* NSPは2台の冗長で、ACCUからのA/G音声をデジタル化してPCMMUのテレメトリと時分割多重してトランスポンダへ送り、フォワードリンクでは音声をACCUへ戻し、地上コマンドを解読してFF MDM（NSP 1はFF 1、NSP 2はFF 3）へ送る。 */ }
            action <'F-CT-SBD-09'> F_CT_SBD_09 { doc /* COMSEC装置はNSPと組んで運用データの暗号化・復号を行い、現在はSELECT/RCVモードでアップリンク（音声とコマンド）だけを暗号化する。 */ }
            action <'F-CT-SBD-10'> F_CT_SBD_10 { doc /* S帯FM系は受信できない送信専用の系で、2,250 MHzに同調した2台の冗長な送信機の一方から最大7つの源のうち1つのデータを地上局へ直接送り、TDRSは経由しない。 */ }
            action <'F-CT-SBD-11'> F_CT_SBD_11 { doc /* FM信号処理器は一度に1台を使い、現在のS帯FM系は主に上昇中の主エンジンデータと軌道上のMMU1・MMU2の記録器のダンプの送信に使われる。 */ }
            action <'F-CT-SBD-12'> F_CT_SBD_12 { doc /* 2基のヘミアンテナは前方胴体の上下に約180°離れてS帯FMのリターンリンクを放射し、GPCモードではSM計算機がSTDNまたはAFSCFの地上局への見通しからアンテナを選ぶ。 */ }
        }
        package <'SSD-FD-CT-UHF-001'> FN_CT_UHF {
            action <'F-CT-UHF-01'> F_CT_UHF_01 { doc /* UHF系は能力の異なる2つの系、UHFシンプレックス（SPLX）系とUHF SSOR系から成り、パネルO6の5位置のUHF MODEロータリスイッチで電源を入れる。 */ }
            action <'F-CT-UHF-02'> F_CT_UHF_02 { doc /* SPLXは259.7 MHz（予備296.8 MHz）の送受信機を働かせ、SPLX + G RCVではガードの243.0 MHz緊急受信機も働き、G T/Rでは243.0 MHzの送受信機で非常時の音声通信を行う。 */ }
            action <'F-CT-UHF-03'> F_CT_UHF_03 { doc /* UHFシンプレックス（ATC）系は上昇・再突入でS帯PMのバックアップとしてSTDN地上局経由でMCCと通信し、送信と受信を同時にはできない。 */ }
            action <'F-CT-UHF-04'> F_CT_UHF_04 { doc /* SPLX・GUARDモードでは、UHF送受信機はACCUのA/Aループの音声を前方胴体下面の外部UHFアンテナから送信し、受信した信号を復調してA/Aループへ戻す。 */ }
            action <'F-CT-UHF-05'> F_CT_UHF_05 { doc /* SPLX PWR AMPLスイッチをONにすると10 W、OFFにすると電力増幅回路を迂回して0.25 Wで送信し、XMIT FREQスイッチで259.7 MHz（主）か296.8 MHz（副）を選ぶ。 */ }
            action <'F-CT-UHF-06'> F_CT_UHF_06 { doc /* UHF MODEのEVAはSSORを働かせてSPLXを止め、SSORは宇宙間通信系（SSCS）の一部で、SSCSは414.2または417.1 MHzで動作する。 */ }
            action <'F-CT-UHF-07'> F_CT_UHF_07 { doc /* SSORの主アンテナはエアロックトラスの右舷側にあり、出入り前のEVA点検のためエアロック内のアンテナにもつながる。 */ }
            action <'F-CT-UHF-08'> F_CT_UHF_08 { doc /* SSORは主・予備の2組の無線機（EVA STRINGで1・2を選び、1が主）を持ち、送信電力は低電力19.1 dBm（約80 mW）と高電力31.6 dBm（約1.44 W）で、高電力はFCCの限度を超えるため使わない。 */ }
            action <'F-CT-UHF-09'> F_CT_UHF_09 { doc /* SSORの状態（主・予備、フレーム同期、処理器の状態）は、SM COMMUNICATIONS（SPEC 76）とSM OIU（SPEC 212）の2つのDPS表示に示される。 */ }
            action <'F-CT-UHF-10'> F_CT_UHF_10 { doc /* EVA乗員との会話はパネルA1RのUHFスイッチの構成に応じてA/G 1またはA/G 2でS帯PMまたはKu帯系からMCCへ送られ、EVAの生体・宇宙服データはUHF/SSORの搬送波から取り出された後にOI系を経て送られる。 */ }
            action <'F-CT-UHF-11'> F_CT_UHF_11 { doc /* EVA通信の構成では、パネルR14のMNA UHF EVAとMNC UHF EVAの遮断器が閉であることを確かめ、送信周波数を259.7/414.2、EVA STRINGを1、UHF MODEをEVAにする（EVAチェックリスト4-10）。 */ }
            action <'F-CT-UHF-12'> F_CT_UHF_12 { doc /* STS-4では、軌道上で初めてUHFの周波数を296.8 MHzから259.7 MHzに変え、地上アンテナの高い利得を利用した。 */ }
        }
        package <'SSD-FD-CW-001'> FN_CW {
            action <'F-CW-01'> F_CW_01 { doc /* C/W系は、オービタの運用または乗員に危険を生じうる状態を乗員に警告し、時間的に切迫した（5分未満の）処置が必要な状況を知らせる。 */ }
            action <'F-CW-02'> F_CW_02 { doc /* 温度・圧力・流量・スイッチ位置などのデータから警報状態を判定し、所定の運用限界を超えた系を視覚と聴覚の合図で乗員に示す。 */ }
            action <'F-CW-03'> F_CW_03 { doc /* 警報は、クラス1（緊急）、クラス2（C/W）、クラス3（アラート）、クラス0（限界監視）の4区分から成る。 */ }
            action <'F-CW-04'> F_CW_04 { doc /* クラス1は煙検知・消火と急減圧の2つで、MDMやソフトウェアを介さないハードウェアのみの系である。 */ }
            action <'F-CW-05'> F_CW_05 { doc /* 主C/W（ハードウェア）は最大120の入力を監視し、限界値はアビオニクスベイ3のC/W電子ユニットに記憶する。乗員はパネルR13Uで限界値を変更できる。 */ }
            action <'F-CW-06'> F_CW_06 { doc /* バックアップC/W（ソフトウェア）は、システム管理の故障検出・表示（FDA）、GNC、バックアップ飛行システムのソフトウェアの一部である。 */ }
            action <'F-CW-07'> F_CW_07 { doc /* C/W電子ユニットの電源A・Bは、それぞれ必須母線ESS 1BCとESS 2CAから給電される。 */ }
        }
        package <'SSD-FD-CW-ALT-001'> FN_CW_ALT {
            action <'F-CW-ALT-01'> F_CW_ALT_01 { doc /* クラス3アラートはSMソフトウェアが動かすソフトウェアの系で、クラス2に至る前の状況や、5分を超える長い処置が要る状況を乗員に知らせる。 */ }
            action <'F-CW-ALT-02'> F_CW_ALT_02 { doc /* アラートのパラメータが限界を外れると、F7の青いSM ALERT灯が点灯し、主C/Wへ離散信号が送られてアラートトーンが鳴り、故障メッセージが出る。 */ }
            action <'F-CW-ALT-03'> F_CW_ALT_03 { doc /* SMアラートトーンは、搭載計算機の入力でC/W電子装置が発生する、所定の長さの連続音である。 */ }
            action <'F-CW-ALT-04'> F_CW_ALT_04 { doc /* 各アラートパラメータは1〜3組の限界を持ち、複数の組を持つものはセンサ入力や系の状態で使う組を選ぶ（前提条件付け）。 */ }
            action <'F-CW-ALT-05'> F_CW_ALT_05 { doc /* 例えば水ループ2のポンプ出口圧は、ポンプが動いていれば故障したポンプを、止まっていれば漏れを検出する限界を使う。 */ }
            action <'F-CW-ALT-06'> F_CW_ALT_06 { doc /* クラス0の限界表示は、DPS表示のパラメータの隣に上・下の矢印を出すソフトウェアの系で、警報音は出さない。 */ }
            action <'F-CW-ALT-07'> F_CW_ALT_07 { doc /* 下向き矢印は下限への到達のほか、通常の状態と異なる状態（通常は動いているファンの停止など）も示す。 */ }
        }
        package <'SSD-FD-CW-ANN-001'> FN_CW_ANN {
            action <'F-CW-ANN-01'> F_CW_ANN_01 { doc /* 視覚の合図は、4つの赤いMASTER ALARM灯、パネルF7の40灯の表示盤、R13Uの120灯、GPCの故障メッセージ、青いSM ALERT灯である。 */ }
            action <'F-CW-ANN-02'> F_CW_ANN_02 { doc /* MASTER ALARMの押しボタン表示器はパネルF2・F4・A7・MO52Jにあり、どれか1つを押すとSMトーンを含むすべてのトーンがリセットされる。 */ }
            action <'F-CW-ANN-03'> F_CW_ANN_03 { doc /* F7の表示灯は、駆動するすべてのパラメータが限界内に戻るか抑止されるまで消えない（BACKUP C/W ALARM灯はMSG RESETで消える）。 */ }
            action <'F-CW-ANN-04'> F_CW_ANN_04 { doc /* クラス1（緊急）の警報音は、煙検知系が作動させるサイレンと、急減圧を検知するΔP/Δtセンサが作動させるクラクソンで、ハードウェアで発報する。 */ }
            action <'F-CW-ANN-05'> F_CW_ANN_05 { doc /* C/W電子装置には2つのトーン発生器（A・B）があり、それぞれクラクソン・サイレン・C/Wトーン・アラートトーンを発生する。 */ }
            action <'F-CW-ANN-06'> F_CW_ANN_06 { doc /* 各トーン発生器の出力の1つはR13Uの音量調整を経てACCUへ送られ、ヘッドセットと中甲板・飛行甲板のスピーカに分配される。 */ }
            action <'F-CW-ANN-07'> F_CW_ANN_07 { doc /* 上昇モードは通常モードと同じだが、コマンダのMASTER ALARM灯は点灯しない。 */ }
            action <'F-CW-ANN-08'> F_CW_ANN_08 { doc /* 各表示灯は冗長のため2個の電球を並列に持ち、F7の表示盤の電源はESS 1BCのC&W A遮断器を経る。 */ }
        }
        package <'SSD-FD-CW-BKP-001'> FN_CW_BKP {
            action <'F-CW-BKP-01'> F_CW_BKP_01 { doc /* バックアップC/W（クラス2）は、SMの故障検知・警報（FDA）、GNC、バックアップ飛行系（BFS）のソフトウェアの一部である。 */ }
            action <'F-CW-BKP-02'> F_CW_BKP_02 { doc /* 限界外れを検知すると、4つのMASTER ALARM灯とF7の赤いBACKUP C/W ALARM灯を点灯し、故障メッセージ行と故障要約頁にメッセージを出す。 */ }
            action <'F-CW-BKP-03'> F_CW_BKP_03 { doc /* GPCは前方またはペイロードのMDMを経てC/W系A・Bの両方に信号を送り、MASTER ALARM灯・B/U C&W灯・C/Wトーンを作動させる。 */ }
            action <'F-CW-BKP-04'> F_CW_BKP_04 { doc /* GNCソフトウェアが限界外れを検知するとGNC警報インタフェース（GAX）へ信号を送り、GAXが警報の要否を決める。 */ }
            action <'F-CW-BKP-05'> F_CW_BKP_05 { doc /* BFSが待機（STANDBY）のときはペイロードバスを制御しないため、表示灯・トーンは出さず、故障メッセージと状態表示だけとなる。 */ }
            action <'F-CW-BKP-06'> F_CW_BKP_06 { doc /* 故障メッセージはACKキーを押すまで点滅し、MSG RESETキーで消える。 */ }
            action <'F-CW-BKP-07'> F_CW_BKP_07 { doc /* 同じ故障メッセージが4.8秒以内に重ねて出るときは、FDAの論理が新しいメッセージを抑止する。 */ }
        }
        package <'SSD-FD-CW-OPS-001'> FN_CW_OPS {
            action <'F-CW-OPS-01'> F_CW_OPS_01 { doc /* パネルR13Uは主C&Wとの乗員のインタフェースで、限界の確認・変更、パラメータの有効化・抑止、状態の確認、記憶の読出しを行う。 */ }
            action <'F-CW-OPS-02'> F_CW_OPS_02 { doc /* 一部の限界と監視するパラメータの一覧は飛行段階で変わり、乗員はR13UのPARAM ENABLE/INHIBITとLIMITのスイッチで現在の構成に合わせる。 */ }
            action <'F-CW-OPS-03'> F_CW_OPS_03 { doc /* SPEC 60 SM TABLE MAINTはPASS SMのパラメータとの乗員のインタフェースで、バックアップC/W・アラートの各パラメータの上下限・ノイズフィルタ値・有効/抑止を読み、変えられる。 */ }
            action <'F-CW-OPS-04'> F_CW_OPS_04 { doc /* 限界の変更はSPEC 60で乗員が入力するか、地上からテーブル保守ブロック更新（TMBU）でアップリンクする。 */ }
            action <'F-CW-OPS-05'> F_CW_OPS_05 { doc /* 運用していない主C&Wのパラメータは、同じ灯を使うほかのパラメータを隠さないよう抑止し、迷惑警報を出すバックアップC&Wのパラメータも抑止する。 */ }
            action <'F-CW-OPS-06'> F_CW_OPS_06 { doc /* 主C&WとバックアップC&Wの限界値は、安全化の再構成を促す警報をフェイルセーフに行うため同じ値に保つ。 */ }
            action <'F-CW-OPS-07'> F_CW_OPS_07 { doc /* 電源A・Bの両方を失うと主・バックアップ・SMのすべてのC&W灯とトーンを失ったとみなし、電源Aの喪失や自己試験の失敗では主C&Wを失ったとみなす。 */ }
            action <'F-CW-OPS-08'> F_CW_OPS_08 { doc /* 軌道上の系統Go/No-Go基準では、主C&WとバックアップC&Wの両方を失うと次のPLSで帰還する。 */ }
            action <'F-CW-OPS-09'> F_CW_OPS_09 { doc /* R13Uを使わないときは、PARAMETER SELECTのつまみを119より大きい値にしておく。 */ }
        }
        package <'SSD-FD-CW-PRI-001'> FN_CW_PRI {
            action <'F-CW-PRI-01'> F_CW_PRI_01 { doc /* 主C/Wは120の入力を監視でき、入力は変換器から信号調整器または前方MDMを経て受ける。 */ }
            action <'F-CW-PRI-02'> F_CW_PRI_02 { doc /* 120入力のうち95は変換器から直接、5はGPCの入出力処理装置から、18はGPCソフトウェアからMDMを経て入り、2は予備である。 */ }
            action <'F-CW-PRI-03'> F_CW_PRI_03 { doc /* 入力はアナログ（0〜5 V DC）または2値の離散信号で、すべて上限・下限の検出ができるように作られている。 */ }
            action <'F-CW-PRI-04'> F_CW_PRI_04 { doc /* 各入力は80 Hzで標本化され、連続8標本（100 ms）限界を外れるとC/Wトーン・MASTER ALARM灯・F7の表示灯が作動し、パラメータ番号が記憶される。 */ }
            action <'F-CW-PRI-05'> F_CW_PRI_05 { doc /* 基準の限界値はアビオニクスベイ3のC/W電子装置に格納され、パネルR13Uで変えられるが、電源を失って回復すると元の値に戻る。 */ }
            action <'F-CW-PRI-06'> F_CW_PRI_06 { doc /* C/W電子装置は内部の電源A・Bで給電され、電源AはESS 1BCからC/W A遮断器、電源BはESS 2CAからC/W B遮断器（パネルO13）を経て受電する。 */ }
            action <'F-CW-PRI-07'> F_CW_PRI_07 { doc /* 電源Aを失うと、BACKUP C/W ALARMを除くF7の全灯が点灯し、R13Uの状態灯・機能や主C/Wの限界監視を失う。 */ }
            action <'F-CW-PRI-08'> F_CW_PRI_08 { doc /* C/W系Aには自己試験専用の8パラメータ（120〜127）があり、自己試験に失敗するとPRI C&W灯・MASTER ALARM灯・C/Wトーンが出る。 */ }
        }
        package <'SSD-FD-DPS-001'> FN_DPS {
            action <'F-DPS-01'> F_DPS_01 { doc /* DPSのハードウェアは、5台のGPC、大容量記憶用の2台のモジュラメモリユニット（MMU）、GPCと機体各系の間のデータを運ぶシリアルデジタルデータバス網、オービタ用20台・SRB用4台のMDM、SSMEへ指令する3台のSSMEインタフェースユニット、多機能電子表示系（MEDS）などから成る。 */ }
            action <'F-DPS-02'> F_DPS_02 { doc /* 5台のGPCはいずれもIBM AP-101Sで、中央処理装置（CPU）と入出力プロセッサ（IOP）で構成される。 */ }
            action <'F-DPS-03'> F_DPS_03 { doc /* 上昇・再突入などの飛行重要フェーズでは、4台のGPCが同一コードを同時に実行して入出力を同期する冗長セットを構成し、5台目はRockwellが独立に開発したバックアップ飛行システム（BFS）用に確保される。 */ }
            action <'F-DPS-04'> F_DPS_04 { doc /* BFSは、乗員の操作によってのみ起動（エンゲージ）できる。 */ }
            action <'F-DPS-05'> F_DPS_05 { doc /* 機上の全サブシステムは少なくとも2本のデータバスに冗長接続され、データバスは24本あり、マルチプレクサを介して各系が共用する。 */ }
        }
        package <'SSD-FD-DPS-ASC-001'> FN_DPS_ASC {
            action <'F-DPS-ASC-01'> F_DPS_ASC_01 { doc /* DPSは、GSE・打上げ処理システムとSRBとのインタフェースのための2台のデータバス絶縁増幅器と、2台のマスターイベントコントローラ（MEC）を含む（SCOM 2.6節）。 */ }
            action <'F-DPS-ASC-02'> F_DPS_ASC_02 { doc /* 各SSME制御器は専用のEIU（GPCおよび制御器とつながる特殊なMDM）を通じてGPCの指令を受け、各EIUは1基のSSMEの制御器とだけ通信し、3台のEIUの間にインタフェースはない。 */ }
            action <'F-DPS-ASC-03'> F_DPS_ASC_03 { doc /* 冗長セットの各GPCは割り当てられた飛行重要バス（公称はGPC 1〜4がFC5〜8）でエンジン指令を出すため、各EIUは4つの指令を受ける。 */ }
            action <'F-DPS-ASC-04'> F_DPS_ASC_04 { doc /* EIUは受けたエンジン指令の伝送誤りを検査し、検証した指令だけをCIAへ渡し、CIA 3の選択論理で4つの入力指令を3つの出力指令にする。 */ }
            action <'F-DPS-ASC-05'> F_DPS_ASC_05 { doc /* EIUはパネルO17のEIUスイッチで給電され、EIUが電力を失うと対応するエンジンはスロットル・停止・ダンプの指令を受けられず、GPCとも通信できない。 */ }
            action <'F-DPS-ASC-06'> F_DPS_ASC_06 { doc /* BFS（GPC 5）はSSMEハードウェアインタフェースプログラムを持ち、エンゲージ時はFC5〜8でEIUに指令してデータを要求し、EIUとエンジン制御器を通る指令の流れは4台の冗長セットのときと同じである。 */ }
            action <'F-DPS-ASC-07'> F_DPS_ASC_07 { doc /* 固体ロケットモータの点火指令はGPCがMECを通じて各SRBのS&A装置のNSI起爆器へ送り、PICの発火に要するarm・fire 1・fire 2の3信号はGPCで生じ、MECが28 VDCの信号に整形する。 */ }
            action <'F-DPS-ASC-08'> F_DPS_ASC_08 { doc /* MECは、SRBを外部タンクから、外部タンクをオービタから切り離す火工品の起爆を開始する（SCOM 2.16節）。 */ }
            action <'F-DPS-ASC-09'> F_DPS_ASC_09 { doc /* 打上げデータバス2本は主に地上点検と打上げ段階に使い、5台のGPCをGSE・打上げ処理システム、オービタのLF1・LM1・LA1 MDM、左右のSRBのMDM（LL1・LL2・LR1・LR2）に結ぶ。 */ }
            action <'F-DPS-ASC-10'> F_DPS_ASC_10 { doc /* SRB MDMはSRB内にあって受動のコールドプレートで冷やされ、MECの回路で制御されるSRBバスA・Bから給電されて乗員の操作器はなく、LF・LM・LA MDMは打上げ前試験バスから給電される。 */ }
            action <'F-DPS-ASC-11'> F_DPS_ASC_11 { doc /* 打上げMDMのポートは乗員が切り替えられないが、打上げ前にLF1またはLA1で入出力エラーを検出すると自動で切り替わる。 */ }
            action <'F-DPS-ASC-12'> F_DPS_ASC_12 { doc /* 軌道投入後はパネルO17のスイッチで4台のATVC、3台のEIU、2台のMECの電源をすべて切る（SCOM 2.16節）。 */ }
        }
        package <'SSD-FD-DPS-BUS-001'> FN_DPS_BUS {
            action <'F-DPS-BUS-01'> F_DPS_BUS_01 { doc /* データバス網はGPCと機体各系の間でシリアルデジタルの指令とデータを運び、飛行重要・ペイロード・打上げ・大容量記憶・表示/キーボード・計装/PCMMU・計算機間通信の7群から成る。 */ }
            action <'F-DPS-BUS-02'> F_DPS_BUS_02 { doc /* 計装/PCMMUバスを除く各群のバスは5台のGPCすべてにつながるが、各バスで指令を送るのは一度に1台のGPCで、受信は複数のGPCが同時にできる。 */ }
            action <'F-DPS-BUS-03'> F_DPS_BUS_03 { doc /* 飛行重要（FC）バスは8本で2本ずつFCストリングを作り、FC1〜4はFF MDM 4台・FA MDM 4台・IDP 4台・HUD 2台に、FC5〜8は同じFF・FA MDMとMEC 2台・EIU 3台につながる。 */ }
            action <'F-DPS-BUS-04'> F_DPS_BUS_04 { doc /* 同種のGNC機器は複数台が別々のMDMと飛行重要バスに配線され、1本のストリングを失っても通常の運用を続け、2本目を失っても安全に帰還できるよう機器を分けている。 */ }
            action <'F-DPS-BUS-05'> F_DPS_BUS_05 { doc /* 上昇・再突入では冗長セットの4台のPASS GNC GPCにそれぞれ別のストリングを割り当て、各GPCは自分のストリングの指令元となり、他のGPCは聴取して4本すべてのデータの写しを得る。 */ }
            action <'F-DPS-BUS-06'> F_DPS_BUS_06 { doc /* ペイロードバス2本は5台のGPCをペイロードMDM 2台とPDIに結び、計装/PCMMUバス5本は各GPCに1本ずつ専用で、2台のPCMMUへダウンリストを送る。 */ }
            action <'F-DPS-BUS-07'> F_DPS_BUS_07 { doc /* 計算機間通信（ICC）バスは5本で、PASSのGPCは入出力エラー、故障メッセージ、GPC STATUSマトリクスのデータ、キーボード入力、MTUの時刻、状態ベクトルなどを交換する。 */ }
            action <'F-DPS-BUS-08'> F_DPS_BUS_08 { doc /* MDMはGPCのシリアルデジタル指令を離散・デジタル・アナログの並列指令に変換し、逆に機体各系のデータをシリアルデジタルに変換してGPCへ送り、各MDMは別々のバスにつながる2つの冗長なMIAを持つ。 */ }
            action <'F-DPS-BUS-09'> F_DPS_BUS_09 { doc /* オービタのMDMは20台で、DPSのMDM 13台（FF 1〜4、FA 1〜4、PL 1・2、LF1・LM1・LA1）はGPCに直結し、残る7台は計装系のOI MDM（OF1〜4、OA1〜3）でPCMMUへ計装データを送る。 */ }
            action <'F-DPS-BUS-10'> F_DPS_BUS_10 { doc /* ポートモードはMDMの使うMIAポートをソフトウェアで切り替える方法で、FC MDMは通常ポート1で動作し、ポート1が故障すると乗員がポート2を選び、ストリングの2台のMDMを同時に切り替える。 */ }
            action <'F-DPS-BUS-11'> F_DPS_BUS_11 { doc /* MDMはパネルO6のMDM PL1・PL2・FLT CRIT AFT・FLT CRIT FWDスイッチで2つの主母線から冗長に給電され、どちらの主母線または電源を失っても機能を失わず、電源を切るとサブシステムへの離散・アナログ指令がリセットされる。 */ }
            action <'F-DPS-BUS-12'> F_DPS_BUS_12 { doc /* FF・PL・LF・LM MDMは前方アビオニクスベイで水冷却ループの、LA・FA MDMは後部アビオニクスベイでフレオン冷却ループのコールドプレートで冷やされ、MDMは13×11×7 in、約38.5 lb、消費電力80 W未満である。 */ }
        }
        package <'SSD-FD-DPS-FSW-001'> FN_DPS_FSW {
            action <'F-DPS-FSW-01'> F_DPS_FSW_01 { doc /* PASSは全飛行段階で機体を飛ばし機体・ペイロード系を管理するための全プログラムを持つ主ソフトウェアで、上昇・再突入では5台中4台のGPCに同じPASSを搭載してGNC機能を同時・冗長に実行する。 */ }
            action <'F-DPS-FSW-02'> F_DPS_FSW_02 { doc /* BFSはPASSと別の会社が作った別のソフトウェアで、PASSの共通的な誤りや多重の誤りで機体の制御を失ったときに制御を引き継ぐ。 */ }
            action <'F-DPS-FSW-03'> F_DPS_FSW_03 { doc /* システムソフトウェア（FCOS・ユーザインタフェースプログラム・システム制御プログラム）は常にGPC主記憶にあって入出力、メモリ構成のロード、計時、離散入力の監視を行い、データバスの指令元・聴取の割当ても管理する。 */ }
            action <'F-DPS-FSW-04'> F_DPS_FSW_04 { doc /* 応用ソフトウェアはGNC・SM・ペイロード（PL）の3つの主機能に分かれ、冗長セットの同期はGNCだけで起こり、SMは一度に1台のGPCだけが処理する単独の主機能である。 */ }
            action <'F-DPS-FSW-05'> F_DPS_FSW_05 { doc /* 主機能はOPSに、OPSはメジャーモードに分かれ、上昇用のメモリ構成1はOPS 1（上昇）とOPS 6（RTLS）を併せ持つ（RTLSで新しいソフトウェアをロードする時間がないため）。 */ }
            action <'F-DPS-FSW-06'> F_DPS_FSW_06 { doc /* OPS遷移ではMMUから応用ソフトウェアをロードし、同じ主機能の中の遷移では主機能ベース（MFB）を残してOPSオーバレイだけを書き替え、メモリ構成はIPL直後のCONFIG 0のほかに8種類ある。 */ }
            action <'F-DPS-FSW-07'> F_DPS_FSW_07 { doc /* MMUは2台あって1台に128 Mbitを記憶でき、重要なプログラムとデータは両方のMMUに消去保護して格納する。 */ }
            action <'F-DPS-FSW-08'> F_DPS_FSW_08 { doc /* MMUは基本の飛行ソフトウェアのほか、一部の表示の背景書式とコードと、SM GPCの故障に備えて選んだデータを定期的に書くチェックポイントを格納する。 */ }
            action <'F-DPS-FSW-09'> F_DPS_FSW_09 { doc /* MMU 1はパネルO14のスイッチでMNA、MMU 2はパネルO15のスイッチでMNBから給電され、MMU 1はアビオニクスベイ1、MMU 2はベイ2にあって水冷却ループのコールドプレートで冷やされ、消費電力は83 W（うちSSMMが9 W）である。 */ }
            action <'F-DPS-FSW-10'> F_DPS_FSW_10 { doc /* IPLではパネルO6のIPL SOURCEスイッチでソフトウェア源のMMUを選び、OPS遷移では主機能ごとに割り当てたMMU（SPEC 1 DPS UTILITY）を使い、選んだMMUが使用中か2回失敗すればもう一方を自動で試す。 */ }
            action <'F-DPS-FSW-11'> F_DPS_FSW_11 { doc /* BFSのソフトウェアは全体が1台のGPCに収まって大容量記憶を使う必要がないが、BFS GPCが故障して新しいBFS GPCをIPLする場合に備えてMMUにも格納する。 */ }
            action <'F-DPS-FSW-12'> F_DPS_FSW_12 { doc /* エンゲージ前のBFSは飛行重要バスでPASSの要求と応答を聴取してPASSに同期し、2本以上のストリングを聴取している間（PASSの追従）は状態ベクトルなど機体を飛ばすための情報を保つ。 */ }
            action <'F-DPS-FSW-13'> F_DPS_FSW_13 { doc /* BFSのエンゲージは、OUTPUTスイッチがBACKUPのときにCDRまたはPLTのRHCのBFS ENGAGE押しボタン（3接点すべてが必要）を押して行い、PASSは制御を明け渡す。 */ }
        }
        package <'SSD-FD-DPS-GPC-001'> FN_DPS_GPC {
            action <'F-DPS-GPC-01'> F_DPS_GPC_01 { doc /* オービタには同一のIBM AP-101S型GPCが5台あり、データバス網を通じて接続機器とデータを送受信し、機上のデータ処理の主体となるソフトウェアを収める（SCOM 2.6節）。 */ }
            action <'F-DPS-GPC-02'> F_DPS_GPC_02 { doc /* GPC 1・4は中デッキ前方のアビオニクスベイ1、GPC 2・5はベイ2、GPC 3は中デッキ後方のベイ3にあり、アビオニクスベイのファン（各ベイ2台、同時に使うのは1台）による強制空冷を受ける。 */ }
            action <'F-DPS-GPC-03'> F_DPS_GPC_03 { doc /* アビオニクスベイのファンが2台とも故障すると、GPCは25分（14.7 psi）または17分（10.2 psi）で過熱し、以後の動作は保証されない（SCOM 2.6節の注意）。 */ }
            action <'F-DPS-GPC-04'> F_DPS_GPC_04 { doc /* 各GPCは中央処理装置（CPU）と入出力プロセッサ（IOP）を1つの筐体に収め、筐体は19.55×7.62×10.2 in、質量は約60 lbである。 */ }
            action <'F-DPS-GPC-05'> F_DPS_GPC_05 { doc /* 主記憶は揮発性であるが、GPCの電源断の間は電池パックが内容を保持し、記憶容量256 kフルワードのうち通常は下位128 kフルワードをソフトウェアの処理に使う。 */ }
            action <'F-DPS-GPC-06'> F_DPS_GPC_06 { doc /* IOPはバス制御素子（BCE）で24本のデータバスにつながり、機体各系への指令を整形・送信し、応答データを受信・検証して、CPUや他のGPCとのインタフェースの状態を保つ。 */ }
            action <'F-DPS-GPC-07'> F_DPS_GPC_07 { doc /* 各GPCのGENERAL PURPOSE COMPUTER POWERスイッチ（パネルO6）はESS 1BC・2CA・3ABの電力でRPCを働かせてMN A・B・Cの直流で給電し、GPCごとにRPCが3個あるため主母線または必須母線を2つ失っても正常に動作し、1台の消費電力は560 Wである。 */ }
            action <'F-DPS-GPC-08'> F_DPS_GPC_08 { doc /* OUTPUTスイッチ（BACKUP・NORMAL・TERMINATE）はGPCが飛行重要バスへ出力するのをハードウェアで禁止でき、PASSのGNC GPCはNORMAL、BFSのGPC 5はBACKUP、軌道上のSM GPCはTERMINATEとする。 */ }
            action <'F-DPS-GPC-09'> F_DPS_GPC_09 { doc /* MODEスイッチ（RUN・STBY・HALT）でGPCがソフトウェアを処理できるかを決め、他と同期できないGPCは誤った指令を出さないようできるだけ早く電源を切るかHALTにする。 */ }
            action <'F-DPS-GPC-10'> F_DPS_GPC_10 { doc /* GPCの運用モードには冗長セット・共通セット・単独（simplex）があり、冗長セットでは2台以上のGPCが同じ入力で同じGNCソフトウェアを実行して同じ出力を出し、SMとペイロードの主機能は常に単独のGPCで処理する。 */ }
            action <'F-DPS-GPC-11'> F_DPS_GPC_11 { doc /* 冗長セットの各GPCは同期した段階で動作して処理結果を毎秒数百回照合し、同期点を満たさないGPCは残りのGPCが直ちに冗長セットから票決で外す。 */ }
            action <'F-DPS-GPC-12'> F_DPS_GPC_12 { doc /* GPC STATUSマトリクス（パネルO1の5×5の灯）は各GPCの故障票を示し、黄色の対角灯（自己故障）が点灯するとパネルF7のGPC警報灯とMASTER ALARMが点灯し、DPS表示にGPCの故障メッセージが出る。 */ }
        }
        package <'SSD-FD-DPS-MEDS-001'> FN_DPS_MEDS {
            action <'F-DPS-MEDS-01'> F_DPS_MEDS_01 { doc /* MEDSはIDP 4台、MDU 11台、ADC 4台、キーボード3台から成り、DKデータバスでGPCと通信する。 */ }
            action <'F-DPS-MEDS-02'> F_DPS_MEDS_02 { doc /* 各IDPは飛行重要バス1〜4と1本のDKバス、パネルのスイッチとキーボードにつながり、MEDS側では1本の1553BデータバスでMDUと2台のADCを結ぶ。 */ }
            action <'F-DPS-MEDS-03'> F_DPS_MEDS_03 { doc /* IDPはMN A/FPC1（IDP 1）、MN B/FPC2（IDP 2）、MN C/FPC3（IDP 3・4）の28 VDCで動作し、電源スイッチはパネルC2とR11にあってCRT MDUにも給電し、強制空冷される。 */ }
            action <'F-DPS-MEDS-04'> F_DPS_MEDS_04 { doc /* IDPはMEDSとGPCの間のインタフェースで、GPCとADCのデータをMDU用に整形し、スイッチ・エッジキー・キーボードの入力を受け、自身と他のMEDS LRUの状態をBITEと自己試験で監視する。 */ }
            action <'F-DPS-MEDS-05'> F_DPS_MEDS_05 { doc /* MDUは11台（パネルF6・F7・F8・R12と後部操縦席）あり、各MDUは2つのポートで2台のIDPにつながるが、CRT MDUは主ポートだけを使い、1台のIDPと1本のDKバスに対応する。 */ }
            action <'F-DPS-MEDS-06'> F_DPS_MEDS_06 { doc /* ADCはMPS・HYD・APU・OMS・SPIのアナログデータを12ビットのデジタルデータに変換してIDPに渡し、ADC 1A・1BがMPS・OMS・SPI、ADC 2A・2BがAPU・HYDの信号を受け持つ。 */ }
            action <'F-DPS-MEDS-07'> F_DPS_MEDS_07 { doc /* キーボードは32個の押しボタンキーを持ち、前方のパネルC2に2台、後部操縦席のR11Lに1台あり、各キーは二重接点で2台のIDPと別々の経路で通信する。 */ }
            action <'F-DPS-MEDS-08'> F_DPS_MEDS_08 { doc /* DPS表示はOPS（メジャーモード表示）・SPEC・DISPの3階層で、SPECは乗員がキーボードで系のパラメータを監視・変更でき、DISPは監視専用である。 */ }
            action <'F-DPS-MEDS-09'> F_DPS_MEDS_09 { doc /* IDPごとのMAJ FUNCスイッチ（GNC・SM・PL）で、どの主機能のソフトウェアをそのIDPのDPS表示に出すかをGPCに知らせ、その主機能の応用ソフトウェアを持つGPCがDPS表示を駆動する。 */ }
            action <'F-DPS-MEDS-10'> F_DPS_MEDS_10 { doc /* PASSが同時に駆動できるのは4台のIDPのうち3台までで、どのGPCからも駆動されないIDPはDPS表示に大きな「X」を出し、POLL FAILメッセージを表示する。 */ }
            action <'F-DPS-MEDS-11'> F_DPS_MEDS_11 { doc /* 故障メッセージはDPS表示の故障メッセージ行に出て、PASSのFAULT表示（DISP 99）には最新の15件が新しい順に残る。 */ }
            action <'F-DPS-MEDS-12'> F_DPS_MEDS_12 { doc /* MDUは通常主ポートで自動ポート再構成モードとし、選択中のIDPとの通信を失うと自動で他方のポートに切り替わり、両ポートとも通信を失うと「MDU IS AUTONOMOUS」を表示する。 */ }
        }
        package <'SSD-FD-DPS-MTU-001'> FN_DPS_MTU {
            action <'F-DPS-MTU-01'> F_DPS_MTU_01 { doc /* GPC群のソフトウェアはGMTで処理の予定を立てるため安定で正確な時刻源を要し、各GPCはMTUで内部時計を更新する。 */ }
            action <'F-DPS-MTU-02'> F_DPS_MTU_02 { doc /* MTUはGPC群をはじめ多くのオービタの系に計時と同期のための精密な周波数出力を与え、3つの時刻累算器がGMTとMETを示す（外部から更新でき、1年まで計時する）。 */ }
            action <'F-DPS-MTU-03'> F_DPS_MTU_03 { doc /* MTUは2台の発振器を冗長に持つ水晶制御の周波数源で、一方の発振器の信号を整形器と周波数ドライバを通して3つのGMT/MET累算器へ送る。 */ }
            action <'F-DPS-MTU-04'> F_DPS_MTU_04 { doc /* MTUは累算器を通じて要求に応じてシリアルデジタルの時刻データ（GMT/MET）をGPCへ出し、GPCはこれを基準時刻とし、GNCとSMの処理の時刻付けに間接的に使う。 */ }
            action <'F-DPS-MTU-05'> F_DPS_MTU_05 { doc /* MTUは乗員室の4つのデジタル計時器（ミッションタイマ2台・イベントタイマ2台）を駆動し、PCMMU、COMSEC、ペイロード信号処理器、FM信号処理器と各種ペイロードにも信号を送る。 */ }
            action <'F-DPS-MTU-06'> F_DPS_MTU_06 { doc /* GPCはまずMTUの累算器1を時刻源とし、毎秒自身の内部時刻と照合して差が1 ms未満なら内部時計を累算器の時刻に合わせ、許容外なら他の累算器、さらに番号の最も小さいGPCを試す。 */ }
            action <'F-DPS-MTU-07'> F_DPS_MTU_07 { doc /* PASSのGPCはMTUから受け取るMETを使わず、現在のGMTとリフトオフ時刻からMETを計算する。 */ }
            action <'F-DPS-MTU-08'> F_DPS_MTU_08 { doc /* MTUはパネルO13の遮断器ESS 1BC MTU AとESS 2CA MTU Bで冗長に給電され、パネルO6のMASTER TIMING UNITスイッチがAUTOのとき、一方の発振器の時刻信号が許容外になると自動で他方に切り替わり、通常は発振器2を使う。 */ }
            action <'F-DPS-MTU-09'> F_DPS_MTU_09 { doc /* MTUは中デッキのアビオニクスベイ3Bにあり、水冷却ループのコールドプレートで冷やされる。 */ }
            action <'F-DPS-MTU-10'> F_DPS_MTU_10 { doc /* MISSION TIME表示はパネルO3・A4にあってGMTまたはMETを示し、前方のEVENT TIME表示はパネルF7（操作はC2）、後部のEVENT TIME表示はA4（操作はA6U）にある。 */ }
            action <'F-DPS-MTU-11'> F_DPS_MTU_11 { doc /* 各GPCは内部の発振器で内部時計を保ち、MTUの時刻信号の予備としてGMTとMETを計時する（SCOM 2.6節）。 */ }
            action <'F-DPS-MTU-12'> F_DPS_MTU_12 { doc /* MTUは運用前に12時間の暖機を要し、運用温度に達するまで所定の精度と安定度が得られない（SODB 3.4.5.5節）。 */ }
        }
        package <'SSD-FD-DPS-OPS-001'> FN_DPS_OPS {
            action <'F-DPS-OPS-01'> F_DPS_OPS_01 { doc /* 軌道上の公称のGPC構成は、GPC 1がGNC 2、GPC 2がGNC 2（電力節約のためフリーズドライ可）、GPC 3がGNC 2（またはGNC 3）のフリーズドライ、GPC 4がSM 2、GPC 5がBFSである（A7-13A）。 */ }
            action <'F-DPS-OPS-02'> F_DPS_OPS_02 { doc /* 上昇・再突入の動的段階で冗長セットが故障した場合は、機体の制御を取り戻すためBFSをエンゲージする（A7-8）。 */ }
            action <'F-DPS-OPS-03'> F_DPS_OPS_03 { doc /* 故障したGPCは、上昇（MM 102〜104）・再突入（MM 304・305・601〜603）ではできるだけ早くHALTにし、それ以外ではできるだけ早く電源を切り、軌道上ではA7-13・A7-102に従ってDPSを構成して回復を試みる（A7-3）。 */ }
            action <'F-DPS-OPS-04'> F_DPS_OPS_04 { doc /* IPLに応答しないGPC、原因不明で2回以上故障したGPC、FCまたはICCのBCE受信器が故障したGPCは回復不能とし、冗長セット・共通セットにもBFSにも使わない（A7-2）。 */ }
            action <'F-DPS-OPS-05'> F_DPS_OPS_05 { doc /* 一時故障のGPCは、軌道上では安全上重要な運用を除いて冗長なGNC GPCに使い、電力節約のためフリーズドライのGNC 2にもでき、再突入に使うときはストリング4を割り当てる（A7-13C）。 */ }
            action <'F-DPS-OPS-06'> F_DPS_OPS_06 { doc /* ランデブー・近傍運用、ペイロード回収、有人自由飛行体を伴うEVA、安全上重要なOMS/RCS噴射には冗長なGNC GPCを要し、BFSはPASSのDPS冗長度要求に数えない（A7-11・A7-12）。 */ }
            action <'F-DPS-OPS-07'> F_DPS_OPS_07 { doc /* 2台のGNC GPCでの軌道上の公称のストリング割当ては、ストリング1・3を一方、2・4を他方とし、一方のGNC GPCが故障しても連続して機体を制御できるようにする（A7-102C）。 */ }
            action <'F-DPS-OPS-08'> F_DPS_OPS_08 { doc /* MM 102ではFC・ペイロードMDMのポートモードは重要な系の能力を回復するために必要な場合だけ行い、MM 102後〜MECO前は重要な能力の回復か2つ目の故障の後に行える（A7-105A・B）。 */ }
            action <'F-DPS-OPS-09'> F_DPS_OPS_09 { doc /* EOMまで続けるには、回復不能と宣言したGPCが1台以内であること、必要なLRUと表示の冗長度を支えるデータ経路、軌道離脱用PASSソフトウェアの独立した2つの源（MMU 2台、またはG3アーカイブ／G3フリーズドライのGPCとMMU 1台）を要する（A7-201）。 */ }
            action <'F-DPS-OPS-10'> F_DPS_OPS_10 { doc /* DPSのGo/No-Go表の根拠では、多重故障は一般的な故障の兆候でありうるとしてGPC 2台・IDP 2台（MEDSの機体）の喪失でMDFとし、MMU 2台の喪失も以後のGPC・DEUの回復ができなくなるためMDFとする（A7-1001）。 */ }
            action <'F-DPS-OPS-11'> F_DPS_OPS_11 { doc /* 軌道上で単独のGPCが故障した場合は、動作中のPASS GPCのソフトウェアダンプと故障GPCのハードウェアダンプ（HISAM）を取ってIPLで回復を試み、回復したGPCを冗長なG2・G2FD・SMのいずれかにする（GPC FRP-1）。 */ }
            action <'F-DPS-OPS-12'> F_DPS_OPS_12 { doc /* アビオニクスベイの冷却を失った場合は、GPCの過熱を防ぐためG2・SM・BFSの機能を冷却の効くベイのGPCへ移し、冷却のないベイのGPCにはG3FD・G2FDを置いてHALTにする（GPC FRP-7）。 */ }
            action <'F-DPS-OPS-13'> F_DPS_OPS_13 { doc /* STS-135では乗員睡眠中にSM GPCであったGPC 4が故障してMASTER ALARMが出たため、GPC 2をPASSのSM GPCに割り当て直してDPSを安定な構成に戻した（IFA STS-135-V-08）。 */ }
        }
        package <'SSD-FD-ECLSS-001'> FN_ECLSS {
            action <'F-ECLSS-01'> F_ECLSS_01 { doc /* ECLSSは、圧力制御系、大気再生系、能動熱制御系、給水・廃水系の4系統から成り、乗員とアビオニクスに与圧された居住環境を提供するとともに、オービタの熱的安定を保ち、水と乗員の廃棄物の貯蔵・処分を管理する。 */ }
            action <'F-ECLSS-02'> F_ECLSS_02 { doc /* ECLSSは、機体の熱的安定を維持し、乗員と搭載アビオニクスに与圧された居住環境を提供するとともに、水と乗員廃棄物の貯蔵・処理を担い、機能的に4つの系に分けられる。 */ }
            action <'F-ECLSS-03'> F_ECLSS_03 { doc /* 乗員室は14.7±0.2 psiaに与圧され、平均で窒素80%・酸素20%の混合気に維持される。 */ }
            action <'F-ECLSS-04'> F_ECLSS_04 { doc /* 乗員室の空気は水酸化リチウム／活性炭キャニスタを通され、二酸化炭素が除去される。 */ }
            action <'F-ECLSS-05'> F_ECLSS_05 { doc /* フラッシュエバポレータ（FES）は上昇・再突入時の主冷却源で、軌道上では放熱器の補助として使われる。 */ }
            action <'F-ECLSS-06'> F_ECLSS_06 { doc /* 再突入で高度約100,000 ft以下になるとFESでは十分に冷却できなくなり、以降は地上冷却が接続されるまでアンモニアボイラがフレオンループの熱を排出する。 */ }
        }
        package <'SSD-FD-ECL-ALS-001'> FN_ECL_ALS {
            action <'F-ECL-ALS-01'> F_ECL_ALS_01 { doc /* 外部エアロックは、EMUを着用した乗員がミッドデッキの乗員室から短いトンネルを通り、乗員室を減圧せずにペイロードベイへ出られるようにする。 */ }
            action <'F-ECL-ALS-02'> F_ECL_ALS_02 { doc /* エアロック支援は、減圧・再与圧、EVA機器の補給、液冷服の水冷却、EVA機器の点検、着用、通信を提供する。 */ }
            action <'F-ECL-ALS-03'> F_ECL_ALS_03 { doc /* オービタは、サービス・冷却アンビリカル（SCU）を介して、EVA準備時と終了後のEMUへ電力、酸素、液冷服の冷却、水を供給する。 */ }
            action <'F-ECL-ALS-04'> F_ECL_ALS_04 { doc /* EVA前は、クイックドンマスクを着けてプレブリーズを始め、乗員室を14.7 psiから10.2 psiへ減圧する。 */ }
            action <'F-ECL-ALS-05'> F_ECL_ALS_05 { doc /* エアロックは2段階（5 psia、0 psia）で減圧し、エアロック減圧弁から船外へ排気する。 */ }
            action <'F-ECL-ALS-06'> F_ECL_ALS_06 { doc /* EMUの携帯生命維持装置は、酸素、電力用バッテリ、冷却用の水、CO2除去用の水酸化リチウムを7時間分持つ。 */ }
            action <'F-ECL-ALS-07'> F_ECL_ALS_07 { doc /* シャトルの段階減圧プロトコルでは、乗員室を14.7から10.2 psiaへ下げて空気を酸素26.5%に富化し、最初の適用はSTS-41B（1984年2月）である。 */ }
            action <'F-ECL-ALS-08'> F_ECL_ALS_08 { doc /* 外部エアロックには内側・EV・ドッキングの3枚のハッチがあり、各ハッチは2個の均圧弁と両側の差圧計を持ち、乗員室側へ開いて閉じたときに圧力で密着する。 */ }
            action <'F-ECL-ALS-09'> F_ECL_ALS_09 { doc /* エアロックには換気口がないため、乗員がミッドデッキ床の継手からダクトを張り、ブースタファン（2台、1台ずつ使用）でオービタの調整空気を送って湿度を制御し、CO2・O2・N2のよどみを防ぐ。 */ }
            action <'F-ECL-ALS-10'> F_ECL_ALS_10 { doc /* 与圧区画の外を通るEMU補給・ISS給水用の6本の水配管は2区域に分かれ、各配管に巻いた3系統のヒータ（1系統ずつ使用）で加温する。 */ }
            action <'F-ECL-ALS-11'> F_ECL_ALS_11 { doc /* エアロックの圧力、水配管の圧力と温度、構造温度、ベスティビュール弁の状態は、SM OPS 2のSPEC 177 EXTERNAL AIRLOCKに表示される。 */ }
        }
        package <'SSD-FD-ECL-ALS-DEP-001'> FN_ECL_ALS_DEP {
            action <'F-ECL-ALS-DEP-01'> F_ECL_ALS_DEP_01 { doc /* 外部エアロックはペイロードベイにあり、Xo 576隔壁のミッドデッキハッチからトランスファトンネル、エアロック、トンネルアダプタへ通じ、ドッキングやEVAの作業中も乗員を与圧された乗員室にとどめる（訓練マニュアル6.0節）。 */ }
            action <'F-ECL-ALS-DEP-02'> F_ECL_ALS_DEP_02 { doc /* 外部エアロックは直径63インチ、長さ83インチ強で、直径40インチのD字形開口が3つあり、内側ハッチ・EVハッチ・ドッキングハッチの3枚のハッチを持つ（SCOM 2.11節）。 */ }
            action <'F-ECL-ALS-DEP-03'> F_ECL_ALS_DEP_03 { doc /* 各ハッチはギアボックス・アクチュエータ付きのラッチ、窓、保持装置付きのヒンジ、両側の差圧計、2個の均圧弁、二重の圧力シールを持ち、主な圧力源の乗員室側へ開いて閉じたときに圧力で密着する（SCOM 2.11節）。 */ }
            action <'F-ECL-ALS-DEP-04'> F_ECL_ALS_DEP_04 { doc /* ミッドデッキハッチは常にB型、上部ハッチはEVA用では通常B型でドッキング用ではD型のこともあり、後部ハッチは与圧モジュールがなければB型、あればD型で、トンネルアダプタ上部のCハッチはB型である（訓練マニュアル6.6節）。 */ }
            action <'F-ECL-ALS-DEP-05'> F_ECL_ALS_DEP_05 { doc /* 均圧弁はキャップと3位置スイッチ（OFF・NORM・EMER）を持ち、14.5 psidでNORMは240 lb/hr、EMERは1,278 lb/hrを流して、エアロックを乗員室と均圧し、ハッチを閉じれば隔離し、減圧の予備手段にもなる（訓練マニュアル6.2節）。 */ }
            action <'F-ECL-ALS-DEP-06'> F_ECL_ALS_DEP_06 { doc /* エアロック減圧弁は押してから回す3位置（CLOSED・5・0）の回転スイッチで、「5」位置は0.59インチのオリフィスでエアロックを5 psiaへ（乗員室の14.7 psiaから10.2 psiaへの減圧にも使う）、「0」位置は1.02インチのオリフィスで0 psiaへ減圧し、外部エアロックでは非推進のT字管からペイロードベイへ直接排気する（訓練マニュアル6.2節）。 */ }
            action <'F-ECL-ALS-DEP-07'> F_ECL_ALS_DEP_07 { doc /* 通常はハッチを開けたままで、エアロックの圧力は均圧弁で乗員室と等しく保たれ、減圧弁は乗員室の10.2 psiaへの減圧とEVAのためのエアロックの減圧に使う（SCOM 2.9節）。 */ }
            action <'F-ECL-ALS-DEP-08'> F_ECL_ALS_DEP_08 { doc /* 乗員室の10.2 psiaへの減圧では、O2濃度を適正に保ちながら減圧弁を通常2回開き、「5」位置で約30分かかり、減圧中はdP/dtセンサのクラクソンが鳴る（訓練マニュアル6.9.3.2節）。 */ }
            action <'F-ECL-ALS-DEP-09'> F_ECL_ALS_DEP_09 { doc /* ドッキング前は内側ハッチと均圧弁を閉じてエアロックを隔離し、ドッキング後にエアロック圧力が下がらないことで漏れがないことを確かめ、分離前はベスティビュールをフライトデッキから減圧して漏れを確かめる（訓練マニュアル6.9.3.1節）。 */ }
            action <'F-ECL-ALS-DEP-10'> F_ECL_ALS_DEP_10 { doc /* トンネルアダプタを搭載する場合は、後部ハッチのトンネルアダプタ側のダクトにペイロード隔離弁を設け、トンネルアダプタを真空にするときに後方のモジュールからダクトを通して漏れるのを防ぐ（訓練マニュアル6.2節）。 */ }
            action <'F-ECL-ALS-DEP-11'> F_ECL_ALS_DEP_11 { doc /* 運用飛行規則は、乗員室の気密を保ったままエアロックを減圧・再与圧できない場合（いずれかのハッチの漏れによるエアロック圧力の低下が0.2 psi/minを超える場合）にEVA能力を喪失とみなす（A15-101）。 */ }
            action <'F-ECL-ALS-DEP-12'> F_ECL_ALS_DEP_12 { doc /* EVA乗員を与圧したエアロックの外に締め出すのは、乗員が大きく離れていて再与圧の時間が重要なアボートEVAの場合に限る。その場合も、離れた乗員は外側ハッチの均圧弁でエアロックを減圧して入れる（A15-13）。 */ }
        }
        package <'SSD-FD-ECL-ALS-HTR-001'> FN_ECL_ALS_HTR {
            action <'F-ECL-ALS-HTR-01'> F_ECL_ALS_HTR_01 { doc /* 与圧区画の外を通る6本の水配管（EMU 1・2のLCG供給・戻り各1本、飲料水供給1本、廃水戻り1本）はQDパネルで2区域に分かれ、各配管に3系統のヒータ（1系統ずつ使用）を巻き、区域ごとのサーモスタットで6本のヒータをまとめて入切りする（訓練マニュアル6.5節）。 */ }
            action <'F-ECL-ALS-HTR-02'> F_ECL_ALS_HTR_02 { doc /* エアロック外殻の3区域（上部隔壁の前・後半分と下部隔壁のキール金具）の構造パッチヒータは、特に真空時にエアロック内部を氷点以上に保って内部の水配管の凍結を防ぎ、壁・ハッチとドッキング用アビオニクスベイの結露も防ぐ。構造ヒータは二重冗長である（訓練マニュアル6.5節）。 */ }
            action <'F-ECL-ALS-HTR-03'> F_ECL_ALS_HTR_03 { doc /* ベスティビュールヒータはドッキング機構の一部でECLSSには含まれないが、構造ヒータと同じ形式の二重冗長・3区域のヒータである。すべてのヒータはパネルML86Bの遮断器で操作する（訓練マニュアル6.5節）。 */ }
            action <'F-ECL-ALS-HTR-04'> F_ECL_ALS_HTR_04 { doc /* 各ヒータ系統（水配管・構造・ベスティビュール）は単独で熱調整できるため1系統ずつ運転し、軌道投入後に主母線AのMNA系統を入れ、飛行中盤のヒータ再構成でMNB系統に切り替え、MNCの水配管ヒータは通常使わない（訓練マニュアル6.9.2節）。 */ }
            action <'F-ECL-ALS-HTR-05'> F_ECL_ALS_HTR_05 { doc /* 外部エアロックの構造・水配管ヒータは、打上げ前はペイロードベイの熱調整で不要なため入れず、軌道上でできるだけ早く入れる（A18-301）。 */ }
            action <'F-ECL-ALS-HTR-06'> F_ECL_ALS_HTR_06 { doc /* 軌道上のヒータ再構成（CONFIG B）では、パネルML86BのMNAの外部エアロックヒータ（配管区域1・2と構造区域1〜3）の遮断器を開き、MNBの遮断器を閉じる（Orbit Ops Checklist 6-5）。 */ }
            action <'F-ECL-ALS-HTR-07'> F_ECL_ALS_HTR_07 { doc /* 外部エアロックの水配管は、区域1・2のいずれかで配管温度を32°F（40°F）超に保てない場合に喪失とみなす（A18-60A）。 */ }
            action <'F-ECL-ALS-HTR-08'> F_ECL_ALS_HTR_08 { doc /* EVA中でダクトを外している間は、エアロック内部の能動的な熱制御は構造ヒータだけで、機体姿勢によってはヒータ区域の故障で水配管が凍るおそれがある（A18-60B）。 */ }
            action <'F-ECL-ALS-HTR-09'> F_ECL_ALS_HTR_09 { doc /* EVA中は上部・後部ハッチの断熱カバーを閉じておき、開いた場合はEVA乗員がエアロックに戻って閉じる。カバーとハッチが開くと、深宇宙を見る内部の水配管が構造より速く冷えて凍るおそれがある（A15-201）。 */ }
            action <'F-ECL-ALS-HTR-10'> F_ECL_ALS_HTR_10 { doc /* 冗長のヒータ系統の計測を失った場合は両系統を同時に運転し、水配管ヒータは3系統のうち2系統を使う（A18-304）。 */ }
            action <'F-ECL-ALS-HTR-11'> F_ECL_ALS_HTR_11 { doc /* 水配管ヒータまたは構造ヒータを失った場合は、機体姿勢の管理で外部エアロック内外の水配管の凍結を防ぐ。水配管を失うとEMU補給とISSへの給水移送の能力を失う（A18-306）。 */ }
            action <'F-ECL-ALS-HTR-12'> F_ECL_ALS_HTR_12 { doc /* SMのEXT A/L H2O LN T警報では、温度の変化からヒータの電源喪失やサーモスタットの開故障・閉故障を切り分け、代わりのヒータ電源・系統に切り替える（MAL 6.7a）。 */ }
        }
        package <'SSD-FD-ECL-ALS-LCG-001'> FN_ECL_ALS_LCG {
            action <'F-ECL-ALS-LCG-01'> F_ECL_ALS_LCG_01 { doc /* LCVGの冷却水はEMUごとの2本の閉ループでエアロックに出入りし、SCUにつないだ状態でLCVGを冷やす。この水はLCVG熱交換器でオービタの水ループにより冷却される（訓練マニュアル6.3節）。 */ }
            action <'F-ECL-ALS-LCG-02'> F_ECL_ALS_LCG_02 { doc /* LCVG熱交換器は、EVAの前後にLCVGを冷やす水ループを冷却するもので、エアロック内にある（訓練マニュアル3.3.7節）。 */ }
            action <'F-ECL-ALS-LCG-03'> F_ECL_ALS_LCG_03 { doc /* オービタの水冷却ループの冷えた水は、液冷服熱交換器、飲料水チラー、キャビン熱交換器、IMU熱交換器を通って各ループのポンプパッケージへ戻る（SCOM 2.9節）。 */ }
            action <'F-ECL-ALS-LCG-04'> F_ECL_ALS_LCG_04 { doc /* EMUの液体輸送系は遠心ポンプでLCVGに約240 lb/hrの水を循環させ、船内活動中はSCUを通してオービタの熱交換器にも水を流す（SCOM 2.11節）。 */ }
            action <'F-ECL-ALS-LCG-05'> F_ECL_ALS_LCG_05 { doc /* LCG配管は外部エアロック・オービタの外を通り、機体姿勢による加熱やヒータの故障で圧力・温度が上がりやすい。ループにはアキュムレータ・遮断弁・調圧器がなくEMUから外すと液封状態になり、SCU接続時はEMUの水タンクのアレージ（公称1 lb）がアキュムレータとして働く（A15-202）。 */ }
            action <'F-ECL-ALS-LCG-06'> F_ECL_ALS_LCG_06 { doc /* SCUをEMUにつないだ状態でLCG配管の圧力が上がる場合は、18（16.6）psigに達する前にEMUのファン・ポンプを最大2分運転してLCG熱交換器で冷やし、その後はEMUの水タンクの公称のアレージダンプを行う（A15-202B）。 */ }
            action <'F-ECL-ALS-LCG-07'> F_ECL_ALS_LCG_07 { doc /* LCG配管は、SCUを外した状態で圧力を28.1（26.4）psig以下に、SCUをEMUにつなぎEMUが非通電の状態で18（16.6）psig以下に保てない場合に喪失とみなす。28.1 psigはSCUの認定最大使用圧力である（A18-61）。 */ }
            action <'F-ECL-ALS-LCG-08'> F_ECL_ALS_LCG_08 { doc /* LCG配管の予期しない圧力・温度上昇には、水配管ヒータの停止、機体姿勢の変更、EMUのファン・ポンプによる循環の順で対処する。配管の熱膨張の逃げ場は、外したSCUの可とう部か、EMUの水タンクのアレージしかない（A18-62）。 */ }
            action <'F-ECL-ALS-LCG-09'> F_ECL_ALS_LCG_09 { doc /* 有人のEMUにLCGの水を循環させるのはLCG2配管の温度が両区域で92°F以下のとき、無人のEMUでは110°F以下のときとする（A15-204B・C）。 */ }
            action <'F-ECL-ALS-LCG-10'> F_ECL_ALS_LCG_10 { doc /* EVA中は、EMUの冷却故障に備えてLCGの冷却をいつでも使えるよう、LCG供給配管の温度を両区域で92°F以下に保つ（A15-204F）。 */ }
            action <'F-ECL-ALS-LCG-11'> F_ECL_ALS_LCG_11 { doc /* STS-108では、EVA中の機体姿勢が穏やかだったため、外部エアロックの補給配管は限界内に十分収まった。 */ }
        }
        package <'SSD-FD-ECL-ALS-MON-001'> FN_ECL_ALS_MON {
            action <'F-ECL-ALS-MON-01'> F_ECL_ALS_MON_01 { doc /* エアロックと付属機器の各所のセンサが、空気と水の圧力、水と構造の温度、ベスティビュール弁の状態を乗員とMCCに提供し、専用の信号調整器（DSC）はない（訓練マニュアル6.8.1節）。 */ }
            action <'F-ECL-ALS-MON-02'> F_ECL_ALS_MON_02 { doc /* 構造温度センサはヒータ系統のサーモスタットの作動を監視する位置にあり、実際の構造温度やエアロック内の空気温度を測るものではない（訓練マニュアル6.8.1節）。 */ }
            action <'F-ECL-ALS-MON-03'> F_ECL_ALS_MON_03 { doc /* 各ハッチの差圧は、ミッドデッキの乗員とEVA乗員の両方が読めるよう、ハッチの両側の差圧計に表示される（訓練マニュアル6.8.2節）。 */ }
            action <'F-ECL-ALS-MON-04'> F_ECL_ALS_MON_04 { doc /* SPEC 177 EXTERNAL AIRLOCKはSM OPS 2だけで使え、エアロックの雰囲気、ベスティビュール減圧弁、水配管、構造ヒータの情報を示す。機器は全機にあり、ソフトウェアを共通に保つため表示は全飛行に載せる（訓練マニュアル6.8.3節）。 */ }
            action <'F-ECL-ALS-MON-05'> F_ECL_ALS_MON_05 { doc /* SPEC 177は、EXT A/L PRESS（0〜20 psia）、エアロック・ベスティビュール間差圧（±20 psia）、隔壁・構造の温度、配管区域1・2の給水・LCG2供給温度、LCG供給圧1・2と水移送圧（0〜40 psig）、ベスティビュールの減圧弁・隔離弁の開閉を表示する（訓練マニュアル図6-20）。 */ }
            action <'F-ECL-ALS-MON-06'> F_ECL_ALS_MON_06 { doc /* エアロック圧力（AIRLK P）はSM DISP 66 ENVIRONMENTにも表示される（SCOM 2.9節）。 */ }
            action <'F-ECL-ALS-MON-07'> F_ECL_ALS_MON_07 { doc /* 乗員室圧力トランスデューサの故障時は、SM 66のAIRLK PまたはSPEC 177のEXT A/L PRESSを乗員室圧力の予備として使う（MAL 6.2b）。 */ }
            action <'F-ECL-ALS-MON-08'> F_ECL_ALS_MON_08 { doc /* エアロック・船外間の差圧トランスデューサから求める乗員室圧力には最大±2.0 psiの誤差があり、10.2 psia運用で乗員室の圧力とO2濃度を管理するには精度が足りない（A17-302A）。 */ }
            action <'F-ECL-ALS-MON-09'> F_ECL_ALS_MON_09 { doc /* 外部エアロックの圧力はドッキング機構のアビオニクス箱（DMCU・DSCU・LACU・PACU）内の雰囲気圧を代表し、8.0 psia未満ではPSUを含むこれらの箱を運転しない（A10-342A）。 */ }
            action <'F-ECL-ALS-MON-10'> F_ECL_ALS_MON_10 { doc /* 水配管の区域1・2には2個ずつの温度トランスデューサがあり、流れのないときの6本の配管の温度を代表するよう配置され、区域2の3個目（V64T0185A）は応答が遅いため故障検知に使わない（A18-60）。 */ }
            action <'F-ECL-ALS-MON-11'> F_ECL_ALS_MON_11 { doc /* SPEC 177の故障メッセージ（177 EXT A/L PRESS、177 A/L VEST DP、177 AL H2O LCG P1(2)、177 AL H2O XFER P）には、対応するMAL手順がない（MAL 6章）。 */ }
            action <'F-ECL-ALS-MON-12'> F_ECL_ALS_MON_12 { doc /* OI MDM（OF1）を失うと、外部エアロックのLCG EV1供給配管圧、トラスフランジ温度、水配管ヒータ温度、水遮断弁の位置の計測を失う（MAL COMM SSR-10）。 */ }
        }
        package <'SSD-FD-ECL-ALS-SCU-001'> FN_ECL_ALS_SCU {
            action <'F-ECL-ALS-SCU-01'> F_ECL_ALS_SCU_01 { doc /* エアロックのEMUマウントはEMUの背面を壁の3つの取付具に固定して収納と着脱を支え、下部胴体拘束袋が打上げ・再突入時にEMUの下部胴体を拘束する（SCOM 2.11節）。 */ }
            action <'F-ECL-ALS-SCU-02'> F_ECL_ALS_SCU_02 { doc /* SCUは3本の水ホース、高圧O2ホース、電線、水圧調整器、張力保持テザーから成り、EMUとエアロックを結んで電力、有線通信、O2、廃水排出、水冷却と、PLSSのO2タンク・水リザーバ・バッテリの再充電を提供する（SCOM 2.11節）。 */ }
            action <'F-ECL-ALS-SCU-03'> F_ECL_ALS_SCU_03 { doc /* エアロックを通るO2配管はEMUの補給に900 psiのO2を供給し、PCSのO2クロスオーバマニホールドから給気され、パネルAW82BのEMU OXYGENスイッチでPCS 1・2系のO2を使えるようにする（訓練マニュアル6.3節）。 */ }
            action <'F-ECL-ALS-SCU-04'> F_ECL_ALS_SCU_04 { doc /* エアロック床のEMU O2隔離弁は、エアロック内やペイロードベイへの移送配管の漏れを防ぐ手動の遮断弁で、その上流のEVLSS O2圧力センサがAW82Bの圧力計を駆動する。EVAで緊急分離する場合に備え、エアロック外側（AW64）にEVAでだけ操作できる手動隔離弁がある（訓練マニュアル6.3節）。 */ }
            action <'F-ECL-ALS-SCU-05'> F_ECL_ALS_SCU_05 { doc /* EMUの給水（EVA中の昇華冷却用と飲用）は給水系のA・B出口系統から取り、途中のフィルタと逆止弁でEMUからオービタへ汚染が入るのを防ぎ、下流の給水遮断弁で漏れを隔離する。給水後は廃水戻りラインから廃水タンクへアレージダンプを行う（訓練マニュアル6.3節）。 */ }
            action <'F-ECL-ALS-SCU-06'> F_ECL_ALS_SCU_06 { doc /* PLSSの一次O2系は1.217 lbのO2を850 psiaで蓄え、SCUを通してオービタECLSSから850±50 psigで充填される（SCOM 2.11節）。 */ }
            action <'F-ECL-ALS-SCU-07'> F_ECL_ALS_SCU_07 { doc /* EMUの給水タンク（約9 lb、15 psig）は、オービタECLSSの飲料水で充填・再充填する（SCOM 2.11節）。 */ }
            action <'F-ECL-ALS-SCU-08'> F_ECL_ALS_SCU_08 { doc /* EMU 1・2の電源・バッテリ充電器はパネルAW18Hで主母線A・Bのどちらかを選んで給電され、主母線A（MNA DA1）を失ったときにバッテリ充電中であれば主母線Bに切り替える（MAL EPS SSR-10）。 */ }
            action <'F-ECL-ALS-SCU-09'> F_ECL_ALS_SCU_09 { doc /* エアロックのオーディオ端末装置（ATU）は、パネルAW18DのMASTER VOLUME 1・2でエアロック内のCCU 1・2出力口の音量を調整する（SCOM 2.4節）。 */ }
            action <'F-ECL-ALS-SCU-10'> F_ECL_ALS_SCU_10 { doc /* EMUの消耗品のいずれかが残り30分になったEVA乗員はエアロックに入ってSCUに接続する。SCUはEMUのどの消耗品の喪失にも対応でき、O2と水は真空中でも再充填できる（A15-152）。 */ }
            action <'F-ECL-ALS-SCU-11'> F_ECL_ALS_SCU_11 { doc /* EMUのO2補給は、原則としてO2供給ラインの温度が80°F（指示値）以下のときに行い、EMUへ流れるO2を90°F未満に保つ（A15-204A）。 */ }
            action <'F-ECL-ALS-SCU-12'> F_ECL_ALS_SCU_12 { doc /* EMUの給水の再充填は、外部エアロックの給水配管の温度が両区域で95°F以下のときに行う（A15-204D）。 */ }
        }
        package <'SSD-FD-ECL-ALS-VNT-001'> FN_ECL_ALS_VNT {
            action <'F-ECL-ALS-VNT-01'> F_ECL_ALS_VNT_01 { doc /* エアロックにはキャビンファンの空気を回す吹出口がないため、乗員がダクトを手で張り、オービタARSの調整空気による湿度制御と、CO2・O2・N2のよどみの防止を行う（訓練マニュアル6.4節）。 */ }
            action <'F-ECL-ALS-VNT-02'> F_ECL_ALS_VNT_02 { doc /* ダクトは、エアロックと上部ハッチ窓（ドッキングカメラ取付け部）の結露防止、床下のエアロック用アビオニクスベイの熱調整、ドッキングしたISSやペイロードベイのモジュールへの調整空気の供給にも使う（訓練マニュアル6.4節）。 */ }
            action <'F-ECL-ALS-VNT-03'> F_ECL_ALS_VNT_03 { doc /* ブースタファンは2台で1台ずつ使い、トンネルアダプタ（ない場合や後方搭載時はトンネルエクステンション）に取り付けられ、三相115 V AC・180 Wの電動機で541〜767 lb/hrを流す。与圧モジュールもISSとのドッキングもない飛行では搭載しなくてよい（訓練マニュアル6.4節）。 */ }
            action <'F-ECL-ALS-VNT-04'> F_ECL_ALS_VNT_04 { doc /* ARSとのインタフェースはミッドデッキ床の継手で、外部エアロック構成では継手をXo 576隔壁寄りに移している。ファンはパネルMO13Qで操作し、フィルタは軌道上で手が届きにくいが、飛行実績から飛行中の清掃は不要とされる（訓練マニュアル6.4節）。 */ }
            action <'F-ECL-ALS-VNT-05'> F_ECL_ALS_VNT_05 { doc /* 訓練マニュアル図6-7は、ミッドデッキまたはブースタファンからの空気の入口、ハローダクト、ドッキング窓の曇り止め・ISSへの送気、モジュールへの送気からなるダクト構成の例を示す。 */ }
            action <'F-ECL-ALS-VNT-06'> F_ECL_ALS_VNT_06 { doc /* 外部エアロックのハッチを開けた後、乗員がミッドデッキ床の継手からハッチ越しにダクトを張ってブースタファンにつなぎ、減圧のためにハッチを閉じる前にダクトを外す（SCOM 2.11節）。 */ }
            action <'F-ECL-ALS-VNT-07'> F_ECL_ALS_VNT_07 { doc /* 軌道投入後の作業で、ミッドデッキの乗員がエアロックに入れるよう準備し、ダクトとブースタファンを設置してエアロックへ送気する（SCOM 5.2節）。 */ }
            action <'F-ECL-ALS-VNT-08'> F_ECL_ALS_VNT_08 { doc /* ドッキングの最終接近の前に、内側のエアロックハッチを閉じ、エアロックファンの作動を確かめる（SCOM 2.19節）。 */ }
            action <'F-ECL-ALS-VNT-09'> F_ECL_ALS_VNT_09 { doc /* EVA後の乗員室大気の除染では、エアロックのハッチを開けた後、ブースタファンとダクトをできるだけ早く設置・起動する（A15-203B）。 */ }
            action <'F-ECL-ALS-VNT-10'> F_ECL_ALS_VNT_10 { doc /* AC1母線を失うとエアロック・トンネルのファンAを失うため、稼働中であればファンAを止めてファンBを運転する（MAL EPS SSR-110）。 */ }
            action <'F-ECL-ALS-VNT-11'> F_ECL_ALS_VNT_11 { doc /* キャビン・アビオニクスベイ・ブースタファンのフィルタ清掃は、MCCの指示がない限り行わない（IFM 4-2）。 */ }
            action <'F-ECL-ALS-VNT-12'> F_ECL_ALS_VNT_12 { doc /* STS-108では、ブースタファンAが3相とも正常に起動し、飛行中はファンAだけを運転した。 */ }
        }
        package <'SSD-FD-ECL-ARS-001'> FN_ECL_ARS {
            action <'F-ECL-ARS-01'> F_ECL_ARS_01 { doc /* ARSは相対湿度を30〜75%に制御し、二酸化炭素と一酸化炭素を無害な濃度に保ち、乗員室の温度と換気を制御し、フライトデッキとミッドデッキの電子機器を冷却する。 */ }
            action <'F-ECL-ARS-02'> F_ECL_ARS_02 { doc /* キャビンファンが吸い込んだ空気はフィルタで粒子を除かれ、一部は水酸化リチウムキャニスタでCO2と臭気を除去された後、キャビン熱交換器で水冷却ループにより冷却される。 */ }
            action <'F-ECL-ARS-03'> F_ECL_ARS_03 { doc /* 熱交換器で凝縮した水分は湿度分離器（ファンセパレータ）で吸い出されて廃水タンクへ送られ、その量は最大で毎時約4 lbである。 */ }
            action <'F-ECL-ARS-04'> F_ECL_ARS_04 { doc /* キャビン熱交換器を出た空気の一部は一酸化炭素除去装置へ送られ、一酸化炭素が二酸化炭素に変換される。 */ }
            action <'F-ECL-ARS-05'> F_ECL_ARS_05 { doc /* 乗員室容積2,300 ft³に対して毎分330 ft³の空気を循環させ、約7分で室内空気が1回入れ替わる。 */ }
            action <'F-ECL-ARS-06'> F_ECL_ARS_06 { doc /* 独立した2系統の水冷却ループがあり、ループ1はポンプ2台、ループ2はポンプ1台を持つ。 */ }
            action <'F-ECL-ARS-07'> F_ECL_ARS_07 { doc /* 水冷却ループは、キャビン熱交換器、3つのアビオニクスベイの熱交換器とコールドプレート、IMU熱交換器、液冷服熱交換器、飲料水チラーの熱を集め、水／フレオン熱交換器でATCSへ渡す。 */ }
            action <'F-ECL-ARS-08'> F_ECL_ARS_08 { doc /* 長期滞在（EDO）飛行では、水酸化リチウムの代わりに再生式CO2除去装置（RCRS）を使う場合がある。 */ }
            action <'F-ECL-ARS-09'> F_ECL_ARS_09 { doc /* RCRSは固体アミンでCO2と水蒸気を吸着して真空へ脱着し、30分周期でベッドを切り替える。 */ }
        }
        package <'SSD-FD-ARS-AVB-001'> FN_ARS_AVB {
            action <'F-ARS-AVB-01'> F_ARS_AVB_01 { doc /* キャビン空気は3つのアビオニクス機器ベイとベイ内の一部の機器の冷却にも使われ、各ベイのクローズアウトカバーは気密ではないが、実質的にベイ内の閉ループで空気が循環する。 */ }
            action <'F-ARS-AVB-02'> F_ARS_AVB_02 { doc /* 3ベイは同一の空冷系を持ち、ベイごとに2台のファンをパネルL1のAV BAY 1・2・3 FAN A・Bスイッチで個別に制御し、通常は1台ずつ使う。 */ }
            action <'F-ARS-AVB-03'> F_ARS_AVB_03 { doc /* ファンはベイの床から空冷機器と300ミクロンフィルタを通して空気を吸い込み、ファン出口空気はミッドデッキ床下のベイ熱交換器で水冷却ループにより冷却されてベイへ戻り、非運転ファンの出口の逆止弁が逆流を防ぐ。 */ }
            action <'F-ARS-AVB-04'> F_ARS_AVB_04 { doc /* 各ベイのファン出口温度はパネルO1のロータリスイッチ（AV BAY 1・2・3）でAIR TEMP計器に表示され、いずれかが130°Fを超えるとパネルF7の黄色AV BAY/CABIN AIR警報灯が点灯する。 */ }
            action <'F-ARS-AVB-05'> F_ARS_AVB_05 { doc /* Av Bay 3Aのファンダクトは、ISSミッションでミッドデッキに収納するペイロードの追加冷却のため、より大型のキャビンファンを受け入れるよう改修されており、必要になるまでは標準のベイファンを使う。 */ }
            action <'F-ARS-AVB-06'> F_ARS_AVB_06 { doc /* GPC 1・4はベイ1、GPC 2・5はベイ2、GPC 3はベイ3にあってベイファンで強制空冷され、ベイの両ファンが故障すると14.7 psiで25分、10.2 psiで17分以内に過熱して動作を信頼できなくなる。 */ }
            action <'F-ARS-AVB-07'> F_ARS_AVB_07 { doc /* ベイファン差圧が2.5 in H2O未満または4.3 in H2O超でファン喪失とし、キャビンファンと同型の改良型ファン（1999年1月時点でOV-104のAv Bay 3Aに搭載）では4.5 in H2O未満または7.8 in H2O超とする（A17-103）。 */ }
            action <'F-ARS-AVB-08'> F_ARS_AVB_08 { doc /* 上昇・再突入でベイ空気出口温度を130（125）°F未満に保てない場合、軌道上14.7 psiでは稼働GPC 2台・1台・0台に応じて120（115）・108（103）・100（95）°F未満に保てない場合などにアビオニクスベイ冷却の喪失とする（A17-105）。 */ }
            action <'F-ARS-AVB-09'> F_ARS_AVB_09 { doc /* 改良型アビオニクスベイファンは起動過渡電流が従来型より大きい（7.4 A/相、従来型は2.0 A/相）ため、MECO前には切り替えない（A17-151F）。 */ }
            action <'F-ARS-AVB-10'> F_ARS_AVB_10 { doc /* 1ベイの両ファン喪失は軌道到達可とし、単一の電気故障（AC母線）で2ベイの空冷を失いうる場合は次のPLSに入る（A17-1001 注[4]・[7]）。 */ }
            action <'F-ARS-AVB-11'> F_ARS_AVB_11 { doc /* ベイファンは交流で動くGould製TACANも冷却し、冷却を失ったTACANは5分以内に短絡しうるため、上昇中でもベイファンは切り替えてよい交流負荷とされる（A9-154）。 */ }
            action <'F-ARS-AVB-12'> F_ARS_AVB_12 { doc /* 3個のAv Bay信号調整器が、各ベイの温度センサとファン差圧センサに給電する（訓練マニュアル3.5節）。 */ }
        }
        package <'SSD-FD-ARS-AVB-CIR-001'> FN_ARS_AVB_CIR {
            action <'F-ARS-AVB-CIR-01'> F_ARS_AVB_CIR_01 { doc /* 微小重力では対流による冷却が起きないため、ベイファンがベイ内に空気を循環させ、連続した強制空冷で置き換える（訓練マニュアル3.2.7節）。 */ }
            action <'F-ARS-AVB-CIR-02'> F_ARS_AVB_CIR_02 { doc /* ファンはベイの床から、該当する空冷機器と300ミクロンフィルタを通して空気を吸い込む（SCOM 2.9節）。 */ }
            action <'F-ARS-AVB-CIR-03'> F_ARS_AVB_CIR_03 { doc /* 各ベイのクローズアウトカバーはベイと乗員室の間の空気の出入りと温度勾配を抑えるが気密ではなく、実質的にはベイ内の閉ループで空気が循環する（SCOM 2.9節）。 */ }
            action <'F-ARS-AVB-CIR-04'> F_ARS_AVB_CIR_04 { doc /* 訓練マニュアルの表3-2〜3-5は、各ベイ（1・2・3A・3B）の機器を強制空冷・自由流空冷・水冷に分けて示し、Av Bay 3Bには空冷の機器がない。 */ }
            action <'F-ARS-AVB-CIR-05'> F_ARS_AVB_CIR_05 { doc /* GPC 1・4はベイ1、GPC 2・5はベイ2、GPC 3はベイ3にあってベイファンで強制空冷され、ベイの両ファンが故障すると14.7 psiで25分、10.2 psiで17分以内に過熱する（SCOM 2.6節）。 */ }
            action <'F-ARS-AVB-CIR-06'> F_ARS_AVB_CIR_06 { doc /* 運用飛行規則は、ベイ入口温度95°F以下という設計要求の下で各LRUが最高運用温度を超えないようにベイ内の気流が配分されているとし、軌道上ではGPCが最大の熱負荷で、各GPCがベイの気流の約3分の1に影響するとする（A17-105）。 */ }
            action <'F-ARS-AVB-CIR-07'> F_ARS_AVB_CIR_07 { doc /* SODBはアビオニクス機器に入る空気を95°F未満、機器の出口を130°F未満とすることを求め、ベイでGPCを1台追加して稼働させると計測される出口温度は約10〜15°F上がる（A18-205）。 */ }
            action <'F-ARS-AVB-CIR-08'> F_ARS_AVB_CIR_08 { doc /* 前方ベイ1〜3のインバータ分配組立は空冷である（SCOM 2.8節）。 */ }
            action <'F-ARS-AVB-CIR-09'> F_ARS_AVB_CIR_09 { doc /* 交流で動くGould製TACANは冷却を失うと5分以内に短絡しうることが示されており、ベイファンで冷却する必要がある（A9-154）。 */ }
            action <'F-ARS-AVB-CIR-10'> F_ARS_AVB_CIR_10 { doc /* ベイファンのフィルタ清掃はMCCの指示があるときだけ行い、ベイ1・2は収納区画Vol E（MD76C）、ベイ3AはVol G（MD80R）またはVol H（MD23R）を外して下部機器ベイからフィルタに近づく（IFM 4-9）。 */ }
            action <'F-ARS-AVB-CIR-11'> F_ARS_AVB_CIR_11 { doc /* IOAのCIL評価（1988年）は、ベイ冷却用ダクト区間の流れの制限（ARS-2561X）の原因の一つを300ミクロンフィルタの目詰まり（ARS-234）とし、一次故障の影響として扱って指摘を取り下げた。 */ }
        }
        package <'SSD-FD-ARS-AVB-FAN-001'> FN_ARS_AVB_FAN {
            action <'F-ARS-AVB-FAN-01'> F_ARS_AVB_FAN_01 { doc /* ベイ1・2・3Aにはそれぞれ2台のファンがあって常に1台を使い、ファンはミッドデッキ床下のECLSSベイで各ベイの下にある（訓練マニュアル3.2.7節）。 */ }
            action <'F-ARS-AVB-FAN-02'> F_ARS_AVB_FAN_02 { doc /* ベイ1・2の各ファンは三相115 V ACの111 W電動機で駆動されてベイ内に通常875 lb/hrを流し、交流2相でも起動・運転できる（訓練マニュアル3.2.7節）。 */ }
            action <'F-ARS-AVB-FAN-03'> F_ARS_AVB_FAN_03 { doc /* 各ファン出口のフラッパ式逆止弁は非運転ファンを通る逆流を防ぎ、ファンが弁の前後に1 psiの差圧を生じると開く（訓練マニュアル3.2.7節）。 */ }
            action <'F-ARS-AVB-FAN-04'> F_ARS_AVB_FAN_04 { doc /* 各ベイの2台のファンはパネルL1のAV BAY 1・2・3 FAN A・Bスイッチで個別に制御して通常は1台ずつ使い、OFF位置でそのファンの電源を断つ（SCOM 2.9節）。 */ }
            action <'F-ARS-AVB-FAN-05'> F_ARS_AVB_FAN_05 { doc /* 各ファンはパネルL4の3個の遮断器から三相交流を受け、ベイ1のファンA・BはAC1・AC2、ベイ2はAC2・AC3、ベイ3はAC3・AC1につながる（訓練マニュアル表3-6）。 */ }
            action <'F-ARS-AVB-FAN-06'> F_ARS_AVB_FAN_06 { doc /* 故障処置手順の通常構成では、ベイ1とベイ3はファンB、ベイ2はファンAを運転する（MAL 6.1b）。 */ }
            action <'F-ARS-AVB-FAN-07'> F_ARS_AVB_FAN_07 { doc /* Av Bay 3Aのファンを三相115 V AC・495 Wのキャビンファンに換え、ミッドデッキのロッカーに収めるペイロードの追加冷却のためにベイに1,400 lb/hrを流す計画があり、換装までは標準のファンを使う（訓練マニュアル3.2.7節）。 */ }
            action <'F-ARS-AVB-FAN-08'> F_ARS_AVB_FAN_08 { doc /* 改良型ファンはハウジングを除いてキャビンファンと同じで、1999年1月時点でOV-104のAv Bay 3Aに搭載され、OV-103・OV-105は将来搭載、OV-102は搭載予定がない（A17-103B）。 */ }
            action <'F-ARS-AVB-FAN-09'> F_ARS_AVB_FAN_09 { doc /* IFMチェックリストの下部機器ベイ配置図（OV-104）は、Av Bay 3Aのファンパッケージを大型（キャビンファン）ファン用に改修したと注記する。 */ }
            action <'F-ARS-AVB-FAN-10'> F_ARS_AVB_FAN_10 { doc /* 従来型のベイファンは2相で再起動できるが、改良型ファンはキャビンファンと同じく2相では再起動できない（A17-154A）。 */ }
            action <'F-ARS-AVB-FAN-11'> F_ARS_AVB_FAN_11 { doc /* 交流の位相ずれでは、燃料電池ポンプ・フレオンポンプ・水ポンプとともにベイファンなど複数の三相モータが停止する（SCOM付録C）。 */ }
            action <'F-ARS-AVB-FAN-12'> F_ARS_AVB_FAN_12 { doc /* 1ベイの両ファンが故障し、そのうち1台の故障が電源によらない場合は、ファン組立（ファンと逆止弁）を他のベイの2台の良品の1台と交換する（IFM A-17）。 */ }
        }
        package <'SSD-FD-ARS-AVB-HX-001'> FN_ARS_AVB_HX {
            action <'F-ARS-AVB-HX-01'> F_ARS_AVB_HX_01 { doc /* ファンは機器の熱を受け取った空気をベイ熱交換器へ吹き出し、ベイの熱はそこでARSの水冷却ループへ移される（訓練マニュアル3.2.7節）。 */ }
            action <'F-ARS-AVB-HX-02'> F_ARS_AVB_HX_02 { doc /* ベイファンの出口空気は、ミッドデッキ乗員室の床下にあるそのベイの熱交換器で水冷却ループにより冷やされ、ベイへ戻る（SCOM 2.9節）。 */ }
            action <'F-ARS-AVB-HX-03'> F_ARS_AVB_HX_03 { doc /* 各水冷却ループはポンプの下流で3つの並列経路に分かれ、ベイ1とベイ2の空気/水熱交換器とコールドプレート、および乗員室のMDMコールドプレート・Av Bay 3Aの空気/水熱交換器とコールドプレート・Av Bay 3Bのコールドプレートを通る。ベイ2の経路は乗員室の窓の熱調整も行う（SCOM 2.9節）。 */ }
            action <'F-ARS-AVB-HX-04'> F_ARS_AVB_HX_04 { doc /* ベイ1の経路では、水はまずベイ1の空気/水熱交換器を通ってベイの空気から熱を受け、次に25 ft²のコールドプレートを通る。ベイ2の経路は熱交換器と30 ft²のコールドプレートを冷やす（訓練マニュアル3.3.2・3.3.3節）。 */ }
            action <'F-ARS-AVB-HX-05'> F_ARS_AVB_HX_05 { doc /* ベイ3の経路は一部がMDMのコールドプレートを冷やし（大部分はバイパスする）、その後Av Bay 3Aと3Bに分かれ、3Aは熱交換器と32 ft²のコールドプレートを、水冷の機器だけを収める別区画の3Bは5 ft²のコールドプレートを冷やす（訓練マニュアル3.3.4節）。 */ }
            action <'F-ARS-AVB-HX-06'> F_ARS_AVB_HX_06 { doc /* ベイへの供給空気の温度は14.7 psiで最高95°Fが設計仕様で、ベイ熱交換器を出る空気は水冷却ループのポンプ出口温度より約10°F高いため、ポンプ出口温度を85°F未満に保てないとベイの機器が過熱するおそれがある（A18-101C）。 */ }
            action <'F-ARS-AVB-HX-07'> F_ARS_AVB_HX_07 { doc /* 2つの水冷却ループを同時に運転するとインターチェンジャの能力を超えて水温が上がり、インターチェンジャ出口が63°Fに近づくとAv Bayの経路の冷却能力も失われる（訓練マニュアル3.3.6節）。 */ }
            action <'F-ARS-AVB-HX-08'> F_ARS_AVB_HX_08 { doc /* 水冷却ループが故障するとキャビン熱交換器出口温度とベイの空気出口温度が目に見えて上がり、新しいループへの切替後はそれらが安定または低下することを確かめる（訓練マニュアル付録B.4）。 */ }
            action <'F-ARS-AVB-HX-09'> F_ARS_AVB_HX_09 { doc /* ベイを通る水冷却ループの経路の流れの制限でも、そのベイの温度が上がることがある（訓練マニュアル付録B.6）。 */ }
            action <'F-ARS-AVB-HX-10'> F_ARS_AVB_HX_10 { doc /* 故障処置手順は、複数のベイで温度が高く上がり続けるかを確かめ、水冷却ループを切り替えて温度が下がる場合を水冷却ループの劣化とする（MAL 6.1b）。 */ }
        }
        package <'SSD-FD-ARS-AVB-MON-001'> FN_ARS_AVB_MON {
            action <'F-ARS-AVB-MON-01'> F_ARS_AVB_MON_01 { doc /* 3個のAv Bay信号調整器が、各ベイの温度センサとファン差圧センサに給電する（訓練マニュアル3.5節）。 */ }
            action <'F-ARS-AVB-MON-02'> F_ARS_AVB_MON_02 { doc /* 信号調整器にはパネルL4の遮断器を通して、ベイ1がAC3、ベイ2がAC1、ベイ3がAC2のB相から給電される（MAL 6.1b）。 */ }
            action <'F-ARS-AVB-MON-03'> F_ARS_AVB_MON_03 { doc /* 温度センサはミッドデッキ床下のファンプレナムで、ベイの空気/水熱交換器の近くにある。気流を失うとセンサは水冷却ループの温度に近づくため、ファンが故障するとベイ温度の表示は下がる（訓練マニュアル付録B.6）。 */ }
            action <'F-ARS-AVB-MON-04'> F_ARS_AVB_MON_04 { doc /* ファン下流の温度センサのデータはAIR TEMP計器に直接送られ、計器は75〜110°Fを通常範囲、130°Fをベイ空気温度の上限（クラス2 C&W）として示す（SCOM 4.1節）。 */ }
            action <'F-ARS-AVB-MON-05'> F_ARS_AVB_MON_05 { doc /* ベイの空気出口温度はAV BAY/CABIN AIR灯（黄）の入力で、ハードウェアチャネル84・94・104がベイ1・2・3の温度に割り当てられている（SCOM 2.2節）。 */ }
            action <'F-ARS-AVB-MON-06'> F_ARS_AVB_MON_06 { doc /* 温度と差圧はBFSとPASS SM OPS 2・4のSM SYS SUMM 2（DISP 79）に表示され、表示範囲は温度45〜145°F、差圧0〜5 in H2Oである（訓練マニュアル3.5.1節）。 */ }
            action <'F-ARS-AVB-MON-07'> F_ARS_AVB_MON_07 { doc /* C&W訓練マニュアルのFDA表は、ベイファン差圧のSM警報を2.5 in H2O未満・4.3 in H2O超（改良型ファンは4.5・7.8）、ベイ温度の上限を130°Fとする。 */ }
            action <'F-ARS-AVB-MON-08'> F_ARS_AVB_MON_08 { doc /* 差圧の限界外はSM警報となり、故障処置手順6.1cで処置する。10.2 psi運用では上限を3.3 in H2O（改良型ファンは5.9）とする（MAL 6.1c）。 */ }
            action <'F-ARS-AVB-MON-09'> F_ARS_AVB_MON_09 { doc /* 信号調整器の故障はBFSのSM SYS SUMM 2でベイ温度45 L・ファン差圧0.00 Lとして現れる。ファンの状態は差圧だけで監視するため、差圧警報を伴わずに空気循環が劣化していることもありうる（訓練マニュアル付録B.6）。 */ }
            action <'F-ARS-AVB-MON-10'> F_ARS_AVB_MON_10 { doc /* 運用飛行規則は、差圧はベイ冷却性能の粗い指標で、ベイ空気出口温度、稼働中の水冷却ループ熱交換器の入口・出口温度と水流量も冷却の有効性の判断に使うとし、差圧の計測誤差は喪失判定に使わない（A17-103）。 */ }
            action <'F-ARS-AVB-MON-11'> F_ARS_AVB_MON_11 { doc /* OI MDM OF1を失うとAv Bay 3のファン差圧と温度が得られなくなり、Av Bay 3の両ファンを運転する。OF2・OF3ではAv Bay 1・2が同様となる（MAL COMM SSR-10〜12、PDF p87〜89）。 */ }
            action <'F-ARS-AVB-MON-12'> F_ARS_AVB_MON_12 { doc /* STS-54では、ベイ1〜3の空気出口温度は最高104・105・87°F、水コールドプレート温度は最高89・90・79°Fで、ARSの性能は正常であった。 */ }
        }
        package <'SSD-FD-ARS-AVB-OPS-001'> FN_ARS_AVB_OPS {
            action <'F-ARS-AVB-OPS-01'> F_ARS_AVB_OPS_01 { doc /* ファン差圧が2.5 in H2O未満（2相運転時の推定差圧に相当）または4.3 in H2O超（GPCの温度超過に基づく最小流量に相当）でベイファンを喪失とし、改良型ファンでは4.5 in H2O未満または7.8 in H2O超とする（A17-103）。 */ }
            action <'F-ARS-AVB-OPS-02'> F_ARS_AVB_OPS_02 { doc /* 上昇・再突入ではベイ空気出口温度を130（125）°F未満に保てない場合、軌道上ではキャビン圧（14.7・10.2・8 psi）と稼働中のGPCの台数に応じた出口温度を保てない場合に、ベイ冷却を喪失とする（A17-105）。 */ }
            action <'F-ARS-AVB-OPS-03'> F_ARS_AVB_OPS_03 { doc /* 上昇中は、電源の入ったGould製TACANがあるベイのファンを失った場合は3分以内に予備のファンへ切り替え、Av Bay 3Aを改良型ファンにした機体ではそのファンを切り替えない（A9-154A）。 */ }
            action <'F-ARS-AVB-OPS-04'> F_ARS_AVB_OPS_04 { doc /* 改良型ファンは起動過渡電流が大きい（1相あたり7.4 A、従来型は2.0 A）ため、主エンジン制御器への電圧過渡を避けてMECO前には切り替えない（A17-151F）。 */ }
            action <'F-ARS-AVB-OPS-05'> F_ARS_AVB_OPS_05 { doc /* ファン差圧トランスデューサを失った場合は、ファンの停止を検知できないため2台目のファンを入れて飛行終了まで運転する。改良型ファンでも音で停止に気づけないおそれがあるため同じとする（A17-153A）。 */ }
            action <'F-ARS-AVB-OPS-06'> F_ARS_AVB_OPS_06 { doc /* 1相を失った回転機器は予備に切り替える。改良型ファンは1台を失っても飛行期間に影響しないため、2相のまま運転を続けない（A17-154A）。 */ }
            action <'F-ARS-AVB-OPS-07'> F_ARS_AVB_OPS_07 { doc /* ベイファンを止めてよい時間は、GPCの冷却の制約から最大26分である（A18-501）。 */ }
            action <'F-ARS-AVB-OPS-08'> F_ARS_AVB_OPS_08 { doc /* ベイの火災では、そのベイのHalonボトルを放出してベイファンを止める。ファンの気流は火に酸化剤を送るためである（A17-53A）。 */ }
            action <'F-ARS-AVB-OPS-09'> F_ARS_AVB_OPS_09 { doc /* 1ベイの両ファン喪失は軌道到達可とし、MECO後にTACAN・MLSを、OMS-1後にすべての空冷機器を再構成する。単一の電気故障（AC母線）で2つのベイの空冷を失いうる場合は次のPLSに入る（A17-1001 注[4]・[7]）。 */ }
            action <'F-ARS-AVB-OPS-10'> F_ARS_AVB_OPS_10 { doc /* Go/No-Go基準は、ベイ1・2の冷却喪失を2台のGPCの冷却喪失としてMDFとし、ベイ3の冷却喪失を空気流の喪失による煙検知の喪失としてMDF、C&Wの冷却喪失として次のPLSの対象とする（A17-1001 B.2・注[6]・[8]・[9]）。 */ }
            action <'F-ARS-AVB-OPS-11'> F_ARS_AVB_OPS_11 { doc /* 故障処置手順6.1bは、ベイ温度が130°Fを超えた場合の処置として、両ファンの運転、水冷却ループの切替（5分待って温度の低下を確かめる）と、MCCと交信できずに130°F以上が続くかMCCの指示があるときのDPSの再構成（ベイ冷却喪失時のGPC FRP-7）を示す。 */ }
            action <'F-ARS-AVB-OPS-12'> F_ARS_AVB_OPS_12 { doc /* GPCをRUNにする前（G2のセット拡張など）には、そのGPCのあるベイのファンがONであることを確かめる（軌道運用チェックリスト4-4）。 */ }
        }
        package <'SSD-FD-ARS-CAC-001'> FN_ARS_CAC {
            action <'F-ARS-CAC-01'> F_ARS_CAC_01 { doc /* 循環空気は臭気・CO2・デブリ・電子機器の熱を拾い、乗員室容積2,300 ft³と毎分330 ft³の循環量から、約7分で1回、1時間に約8.5回室内空気が入れ替わる。 */ }
            action <'F-ARS-CAC-02'> F_ARS_CAC_02 { doc /* 暖まったキャビン空気は300ミクロンフィルタを通って2台のキャビンファン（A・B）の1台に吸引され、各ファンはパネルL1のCABIN FANスイッチで制御し、通常は1台だけを使う。 */ }
            action <'F-ARS-CAC-03'> F_ARS_CAC_03 { doc /* 各キャビンファンは三相115 V AC・495 Wの電動機で駆動され、キャビン空気ダクトに公称1,400 lb/hrの流量を生む。 */ }
            action <'F-ARS-CAC-04'> F_ARS_CAC_04 { doc /* 各ファン出口のフラッパ式逆止弁は非運転ファンを通る逆流を防ぎ、2 in H2O（0.0723 psi）の差圧で開く。 */ }
            action <'F-ARS-CAC-05'> F_ARS_CAC_05 { doc /* キャビンファンはAC 2相では起動できないが、運転中に1相を失っても2相で運転を続け、同じAC母線の他の回転機器の誘起電圧で2-1/2相となれば起動できるが、短絡で相を失った場合は起動できない。 */ }
            action <'F-ARS-CAC-06'> F_ARS_CAC_06 { doc /* キャビンファン差圧はパネルF7の黄色AV BAY/CABIN AIR警報灯の入力の一つで、4.2 in H2O未満または6.8 in H2O超で点灯する。 */ }
            action <'F-ARS-CAC-07'> F_ARS_CAC_07 { doc /* 運用飛行規則A17-101は、ファン差圧が4.20（4.49）in H2O未満または6.80（6.51）in H2O超で、かつ乗員が気流の喪失を確認した場合にキャビンファン喪失とし、4.2 in H2Oで約1,575 lb/hr、適切な冷却に必要な最低流量は1,400 lb/hrとする。 */ }
            action <'F-ARS-CAC-08'> F_ARS_CAC_08 { doc /* キャビンファンはMECO前には切り替えない（起動電流8.0 Aによる電圧過渡が主エンジン制御器に影響しうるため）（A17-151E）。 */ }
            action <'F-ARS-CAC-09'> F_ARS_CAC_09 { doc /* キャビンファン差圧トランスデューサを失った場合は、就寝中のファン停止を検知できないため、就寝期間は両キャビンファンを運転する（A17-153B）。 */ }
            action <'F-ARS-CAC-10'> F_ARS_CAC_10 { doc /* 1相を失ったキャビンファンは、停止すると再起動できない可能性があり、キャビンファン1台の喪失はMDFとなるため、2相のまま運転を続ける（A17-154A）。 */ }
            action <'F-ARS-CAC-11'> F_ARS_CAC_11 { doc /* キャビンファンは還流空気を乗員室の電子機器のそばに通して強制空冷し、対象の機器（CRT、DEU、IDP、CCTVモニタ、RCU/VSUなど）は訓練マニュアル表3-1に示される。 */ }
        }
        package <'SSD-FD-CAC-DCT-001'> FN_CAC_DCT {
            action <'F-CAC-DCT-01'> F_CAC_DCT_01 { doc /* キャビンファンを出た約1,400 lb/hrの空気のうち、ダクト内のオリフィスで約120 lb/hrずつを2個のLiOHキャニスタへ流す（SCOM 2.9節）。 */ }
            action <'F-CAC-DCT-02'> F_CAC_DCT_02 { doc /* 残りの主流は、キャビン熱交換器のすぐ上流でキャビン温度制御弁により熱交換器とバイパスに分けられる（訓練マニュアル3.2節）。 */ }
            action <'F-CAC-DCT-03'> F_CAC_DCT_03 { doc /* 乗員室容積2,300 ft³に対し毎分330 ft³を循環させ、約7分で1回、1時間に約8.5回空気が入れ替わる（SCOM 2.9節）。 */ }
            action <'F-CAC-DCT-04'> F_CAC_DCT_04 { doc /* 1979年の飛行運用マニュアルは、キャビンの公称の気流速度を25 ft/min、キャビン空気流量を約1,400 lb/hrとする。 */ }
            action <'F-CAC-DCT-05'> F_CAC_DCT_05 { doc /* 8 psiでの再突入でLiOHキャニスタを外すと、ファン1台の流量は820 lb/hr（装着時）から870 lb/hrに増える（A17-151B）。 */ }
            action <'F-CAC-DCT-06'> F_CAC_DCT_06 { doc /* エアロックにはキャビンファンの空気を回す吹出口がないため、乗員がダクトを張ってオービタの調整空気を送り、湿度を制御してCO2・O2・N2のよどみを防ぐ（訓練マニュアル6.4節）。 */ }
            action <'F-CAC-DCT-07'> F_CAC_DCT_07 { doc /* ARSとエアロックのブースタファン・ダクトとの接続はミッドデッキ床の継手で行い、ブースタファン（2台、1台ずつ使用、三相115 V AC・180 W）は541〜767 lb/hrを流す（訓練マニュアル6.4節）。 */ }
            action <'F-CAC-DCT-08'> F_CAC_DCT_08 { doc /* 外部エアロックのハッチを開けた後、乗員が床の継手からハッチ越しにダクトを張ってブースタファンにつなぎ、ハッチを閉じる前にダクトを外す（SCOM 2.11節）。 */ }
            action <'F-CAC-DCT-09'> F_CAC_DCT_09 { doc /* Spacehab・ドッキング飛行では、エアロック前方左のミッドデッキ床にARSホースのスクリーンがあり、フィルタ清掃の対象になる（IFM 4-4）。 */ }
            action <'F-CAC-DCT-10'> F_CAC_DCT_10 { doc /* IOAのCIL評価（1988年）は、還流・供給ダクト（ARS-3601X、NASA臨界度2/2）の外部漏れをダクト自体では起こりにくい故障とし、気流中の部品の故障と同じ影響として扱って指摘を取り下げた。 */ }
            action <'F-CAC-DCT-11'> F_CAC_DCT_11 { doc /* 故障処置手順は、ダクトの漏れや閉塞は、すべての吸込口と吹出口の気流を確かめれば見つけられる場合があるとする（MAL 6.1a）。 */ }
        }
        package <'SSD-FD-CAC-FAN-001'> FN_CAC_FAN {
            action <'F-CAC-FAN-01'> F_CAC_FAN_01 { doc /* キャビンファンは2台あって常に1台を使い、ミッドデッキ床下のECLSSベイにあり、パネルMD79Gから点検する（訓練マニュアル3.2.1節）。 */ }
            action <'F-CAC-FAN-02'> F_CAC_FAN_02 { doc /* 各ファンは三相115 V AC・495 Wの電動機で駆動され、キャビン空気ダクトに公称1,400 lb/hrを流す（SCOM 2.9節）。 */ }
            action <'F-CAC-FAN-03'> F_CAC_FAN_03 { doc /* ファンの回転数は11,200 rpmで、ファン前後の通常の差圧は0.1〜0.3 psidである（1979年の飛行運用マニュアル）。 */ }
            action <'F-CAC-FAN-04'> F_CAC_FAN_04 { doc /* SCOMのECLSSの構成品一覧は、キャビンファンと逆止弁を組立（cabin fans and check valve assemblies）として挙げる。 */ }
            action <'F-CAC-FAN-05'> F_CAC_FAN_05 { doc /* キャビンファンAはAC3、BはAC2の三相電力を、パネルL4の各3個の遮断器からパネルL1のCABIN FANスイッチを通して受ける（訓練マニュアル表3-6）。 */ }
            action <'F-CAC-FAN-06'> F_CAC_FAN_06 { doc /* パネルL1のCABIN FAN A・Bスイッチ（ON–OFF）は2個あり、同時に使うのは1個である（訓練マニュアル表3-6）。 */ }
            action <'F-CAC-FAN-07'> F_CAC_FAN_07 { doc /* ファンは2相では起動できないが、運転中に1相を失っても運転を続け、同じAC母線の他の回転機器の誘起電圧で2-1/2相となれば起動できる。短絡で相を失った場合は起動できない（訓練マニュアル3.2.1節）。 */ }
            action <'F-CAC-FAN-08'> F_CAC_FAN_08 { doc /* JSCとRockwellの試験では、2相で起動したキャビンファンがファンの3 A遮断器を作動させた（A17-154A）。 */ }
            action <'F-CAC-FAN-09'> F_CAC_FAN_09 { doc /* 相を失った母線での起動には3個の遮断器をすべて閉じる必要があり、運転中は電力のない相の遮断器を開いておく（MAL EPS 7.5b）。 */ }
            action <'F-CAC-FAN-10'> F_CAC_FAN_10 { doc /* IOAのCIL評価（1988年）は、キャビンファン組立（ARS-3061X、NASA臨界度2/2）の外部への空気漏れで最初に現れるのはアビオニクスベイの冷却低下で、検知して飛行を終了できるとして、指摘を取り下げた。 */ }
        }
        package <'SSD-FD-CAC-MON-001'> FN_CAC_MON {
            action <'F-CAC-MON-01'> F_CAC_MON_01 { doc /* CABIN AIR信号調整器が、キャビンファン差圧・キャビン湿度（MCCのみ監視）・CO2分圧の各トランスデューサに給電する（訓練マニュアル3.5節）。 */ }
            action <'F-CAC-MON-02'> F_CAC_MON_02 { doc /* 差圧の圧力取出し口は、フィルタとファンの間と、ファンの下流のダクトにある（訓練マニュアル図3-12）。 */ }
            action <'F-CAC-MON-03'> F_CAC_MON_03 { doc /* 差圧は、OPS 1・3ではBFS SM SYS SUMM 1、OPS 2・4ではPASS SM SYS SUMM 1とSPEC 66 ENVIRONMENTに表示される（訓練マニュアル3.5.1節）。 */ }
            action <'F-CAC-MON-04'> F_CAC_MON_04 { doc /* キャビンファン差圧（V61R2556A、単位in H2O）はAV BAY/CABIN AIR灯の入力の一つで、訓練マニュアルのC&W表は限界を2.8〜7.04 in H2Oとする。 */ }
            action <'F-CAC-MON-05'> F_CAC_MON_05 { doc /* 主C&Wのハードウェアチャネル74がキャビンファン差圧に割り当てられている（SCOM 2.2節）。 */ }
            action <'F-CAC-MON-06'> F_CAC_MON_06 { doc /* AV BAY/CABIN AIR灯（黄）は、チャネル74（キャビンファン差圧）・84・94・104（Av Bay 1〜3温度）・114（キャビン熱交換器温度）のいずれかの限界外で点灯する（SCOM 2.2節）。 */ }
            action <'F-CAC-MON-07'> F_CAC_MON_07 { doc /* 差圧の計測精度はフルスケール（8 in H2O）の±3.6%（0.288 in H2O）である（A17-101）。 */ }
            action <'F-CAC-MON-08'> F_CAC_MON_08 { doc /* 差圧の限界外は、SMの「SM1 CABIN FAN」「S66 CABIN FAN」メッセージとAV BAY/CABIN AIRのバックアップC&W警報で知らせ、故障処置手順6.1a CABIN FAN ∆Pで処置する（MAL 6.1a）。 */ }
            action <'F-CAC-MON-09'> F_CAC_MON_09 { doc /* OI MDM（OF1）を失うとキャビンファン差圧などの計測が得られなくなり、ファンの気流を手で感じて監視し、就寝中は両ファンを運転する（MAL COMM SSR-10）。 */ }
            action <'F-CAC-MON-10'> F_CAC_MON_10 { doc /* AC1を失ってCABIN AIR信号調整器が止まるとCO2分圧と差圧のセンサが失われ、起床中はストリーマ（搭載時）か手の感覚で気流を監視する（MAL EPS SSR-110）。 */ }
            action <'F-CAC-MON-11'> F_CAC_MON_11 { doc /* STS-59では、キャビンファン差圧が前回のOV-105の飛行（STS-61）より低く、乗員室内のペイロードへの追加冷却によるものとされた。 */ }
            action <'F-CAC-MON-12'> F_CAC_MON_12 { doc /* STS-122では、粉塵対策のテープ覆いを付けたままの新しいLiOHキャニスタを装着した後、ファン起動後の差圧が交換前よりわずかに高くなった。 */ }
        }
        package <'SSD-FD-CAC-OPS-001'> FN_CAC_OPS {
            action <'F-CAC-OPS-01'> F_CAC_OPS_01 { doc /* キャビンファンは、差圧が4.20（4.49）in H2O未満または6.80（6.51）in H2O超で、かつ乗員が気流の喪失を確かめたときに喪失とし、適切な冷却に必要な最低流量は1,400 lb/hrとする（A17-101）。 */ }
            action <'F-CAC-OPS-02'> F_CAC_OPS_02 { doc /* MECO前はキャビンファンを切り替えない。第1段では交流負荷がほぼ最大で、起動電流8.0 Aによる電圧過渡が主エンジン制御器に影響しうる（A17-151E）。 */ }
            action <'F-CAC-OPS-03'> F_CAC_OPS_03 { doc /* 訓練マニュアルは、MECO前の切替では新しいファンの起動時のAC過渡で同じ母線の主エンジン制御器2台を失うおそれがあると警告し、軌道上では気流を確かめてファンの停止と予備ファンの起動を判定するとする（付録B.5）。 */ }
            action <'F-CAC-OPS-04'> F_CAC_OPS_04 { doc /* 差圧の異常時は予備のファンに切り替え、表示の変化から計測器の故障、ファンの故障または逆止弁の開閉固着、デブリトラップ・フィルタの目詰まり、ダクトの漏れ・閉塞を切り分ける（MAL 6.1a）。 */ }
            action <'F-CAC-OPS-05'> F_CAC_OPS_05 { doc /* 差圧トランスデューサを失った場合は、就寝中のファン停止を検知できないため就寝期間に両ファンを運転する。起床中は音でファンの停止に気づける（A17-153B）。 */ }
            action <'F-CAC-OPS-06'> F_CAC_OPS_06 { doc /* 1相を失ったキャビンファンは、止めると再起動できないおそれがあり、1台の喪失はMDFとなるため2相のまま運転を続ける。残るファンも失った場合は電源を入れ替えるIFMがある（A17-154A）。 */ }
            action <'F-CAC-OPS-07'> F_CAC_OPS_07 { doc /* AC2またはAC3の1相を失い停止中のファンが影響を受ける場合は、残る2相で起動できることを軌道上で実証しなければ喪失とみなす（地上試験での2相起動は際どかった）（A9-156C）。 */ }
            action <'F-CAC-OPS-08'> F_CAC_OPS_08 { doc /* 2相起動の手順では、同じ母線の三相機器を運転して誘起電圧を作ってから大型ファンを起動し、ファンの停止は表示装置の冷却のため20分以内とする（MAL EPS SSR-7）。 */ }
            action <'F-CAC-OPS-09'> F_CAC_OPS_09 { doc /* 冗長のファンが使えずに交流電力移送ケーブルでファンに給電する場合は、コンセントの3 A遮断器の制約から、キャビンファンとアビオニクスベイファンを同時には給電できない（MAL EPS SSR-200）。 */ }
            action <'F-CAC-OPS-10'> F_CAC_OPS_10 { doc /* 冷却機器の最大停止時間は、キャビンファンでは旧DDUを搭載する場合20分、MDUの場合30分である（A18-501）。 */ }
            action <'F-CAC-OPS-11'> F_CAC_OPS_11 { doc /* キャビン火災ではキャビンファンを止める。ファンの気流が火に酸化剤を送るためである（A17-53B）。 */ }
            action <'F-CAC-OPS-12'> F_CAC_OPS_12 { doc /* 両キャビンファンを失った場合は、軌道到達と再突入のために直ちに電力を下げ、機器を大幅に入切りする必要がある（A2-301 注[39]）。 */ }
        }
        package <'SSD-FD-CAC-RTN-001'> FN_CAC_RTN {
            action <'F-CAC-RTN-01'> F_CAC_RTN_01 { doc /* 循環空気はミッドデッキとフライトデッキの還流ダクトからフィルタへ引き込まれ、糸くずや毛髪などの粒子が除かれる（1979年の飛行運用マニュアル）。 */ }
            action <'F-CAC-RTN-02'> F_CAC_RTN_02 { doc /* キャビンファンは電子機器のそばを通して空気を吸い込み、それらの機器を強制空冷する（訓練マニュアル3.2.1節）。 */ }
            action <'F-CAC-RTN-03'> F_CAC_RTN_03 { doc /* 訓練マニュアル表3-1は、キャビン空気で強制空冷する機器（CRT、DEU、IDP、CCTVモニタ、RCU/VSUなど）と、自然対流で冷える機器を分けて示す。 */ }
            action <'F-CAC-RTN-04'> F_CAC_RTN_04 { doc /* 暖まったキャビン空気は300ミクロンフィルタを通って、2台のキャビンファンの1台に吸い込まれる（SCOM 2.9節）。 */ }
            action <'F-CAC-RTN-05'> F_CAC_RTN_05 { doc /* IFMチェックリストの下部機器ベイ配置図（OV-103）は、キャビンファンの付近にデブリトラップとMD79Gのフィルタ点検口を、還流ダクトとしてフライトデッキからの還流空気とWCSからの還流空気を示す。 */ }
            action <'F-CAC-RTN-06'> F_CAC_RTN_06 { doc /* 軌道上のフィルタ清掃は、空気中の汚染を抑え、過熱による機器の損傷を防ぐために行い、キャビンファンのフィルタはMCCの指示があるときだけ清掃する（IFM 4-2）。 */ }
            action <'F-CAC-RTN-07'> F_CAC_RTN_07 { doc /* キャビンファンのフィルタ清掃は、ファンを止めてMD79Gとフィルタ点検口を開け、専用工具で3枚のフィルタを清掃し、ファン再起動後にAV BAY/CAB AIR灯の消灯を確かめる。ファンが5分を超えて止まると電子機器が過熱するおそれがある（IFM 4-11）。 */ }
            action <'F-CAC-RTN-08'> F_CAC_RTN_08 { doc /* WCS区画の後部隔壁にキャビン空気の吸込口があり、そのスクリーンは外さずに清掃する（IFM 4-4）。 */ }
            action <'F-CAC-RTN-09'> F_CAC_RTN_09 { doc /* STS-8では浮遊するデブリが次第に増え、キャビンファンのフィルタを3回清掃して毎回青灰色の物質が捕集されたが、ろ過能力は保たれていた。 */ }
            action <'F-CAC-RTN-10'> F_CAC_RTN_10 { doc /* RCRS搭載時は、キャビンファンの上流からキャビン空気の一部（ARSの全流量の約6%）をRCRSに通し、除去後の空気をファンのフィルタのすぐ上流に戻す（訓練マニュアル付録C.2.1）。 */ }
            action <'F-CAC-RTN-11'> F_CAC_RTN_11 { doc /* IOAのCIL評価（1988年）は、還流ダクト（ARS-3604X、NASA臨界度2/2）の流れの制限を、気流中の部品が目詰まりしたときと同じ影響として扱い、指摘を取り下げた。 */ }
            action <'F-CAC-RTN-12'> F_CAC_RTN_12 { doc /* 両キャビンファンが故障して乗員室の空気が循環しない場合は、乗員室の煙検知を喪失とみなす（A17-2B）。 */ }
        }
        package <'SSD-FD-ARS-CO2-001'> FN_ARS_CO2 {
            action <'F-ARS-CO2-01'> F_ARS_CO2_01 { doc /* キャビンファンを出た約1,400 lb/hrの空気のうち、ダクト内のオリフィスで約120 lb/hrずつを2個のLiOHキャニスタへ分流し、LiOHがCO2を、活性炭が臭気と微量汚染物質を除去するもので、LiOHキャニスタはオービタのCO2制御の主手段である。 */ }
            action <'F-ARS-CO2-02'> F_ARS_CO2_02 { doc /* キャニスタは所定のスケジュールで通常1日1〜2回（大人数の乗員ではより頻繁に）、ミッドデッキ床のアクセスドアから交換する。 */ }
            action <'F-ARS-CO2-03'> F_ARS_CO2_03 { doc /* 各キャニスタの定格は48 man-hoursで、予備は最大30個をキャビン熱交換器と水タンクの間の床下ロッカーに収納する。 */ }
            action <'F-ARS-CO2-04'> F_ARS_CO2_04 { doc /* キャニスタ交換中はキャビンファンを止める（ファンが巻き上げたLiOH粉塵で目や鼻の刺激が生じた例があり、湿度分離器故障の一因の可能性もある）。 */ }
            action <'F-ARS-CO2-05'> F_ARS_CO2_05 { doc /* キャビン熱交換器を出た再生・調整済み空気の一部はCO除去装置ATCO（常温触媒酸化器）へ送られ、COがCO2に変換される。 */ }
            action <'F-ARS-CO2-06'> F_ARS_CO2_06 { doc /* 火災の鎮火後はWCSのチャコールフィルタ、ATCO、LiOHキャニスタで燃焼生成物をキャビン大気から除去する。 */ }
            action <'F-ARS-CO2-07'> F_ARS_CO2_07 { doc /* LiOHキャニスタは通常、就寝前と起床後、またはPPCO2が7.6（6.1）mmHg以上と確認されたときに交換する（A17-151C）。 */ }
            action <'F-ARS-CO2-08'> F_ARS_CO2_08 { doc /* 未使用のLiOHキャニスタを最低2日分予備に保持してPPCO2 7.6 mmHgを上限として守り、目安として7.6 mmHgで2日分に要する個数は乗員数に等しい（1個で約50 man-hours）（A17-157）。 */ }
            action <'F-ARS-CO2-09'> F_ARS_CO2_09 { doc /* ARSがPPCO2を15 mmHg未満に保てない場合は乗員がQDMを着用して次のPLSで飛行を終了し、7.6〜15 mmHgでは全作業計画をFCRの航空医官が評価する（A13-52）。 */ }
            action <'F-ARS-CO2-10'> F_ARS_CO2_10 { doc /* CO2・湿度制御の代替手段は、エアロック減圧弁によるキャビンのパージ（または部分排気）である（A17-1001 注[10]）。 */ }
            action <'F-ARS-CO2-11'> F_ARS_CO2_11 { doc /* キャビン空気のCO2分圧（PPCO2）は、LiOHキャニスタへの分岐の手前のダクトに接続したトランスデューサで測り、SM OPS 2・4のSM表示DISP 66（ENVIRONMENT）に表示する（訓練マニュアル3.5節・図3-12）。 */ }
        }
        package <'SSD-FD-CO2-ABS-001'> FN_CO2_ABS {
            action <'F-CO2-ABS-01'> F_CO2_ABS_01 { doc /* キャビンファン出口のダクトでは2個のLiOHキャニスタとオリフィスが並列に並び、オリフィスによって各キャニスタに約120 lb/hrの空気が流れる（訓練マニュアル3.2.2節）。 */ }
            action <'F-CO2-ABS-02'> F_CO2_ABS_02 { doc /* LiOHキャニスタはECLSSベイにあり、ミッドデッキ床の開口MD54Gから交換する（訓練マニュアル3.2.2節）。 */ }
            action <'F-CO2-ABS-03'> F_CO2_ABS_03 { doc /* CO2吸収器の使用位置はMD54G、搭載時の収納位置はMD52Mである（SCOM 2.24節）。 */ }
            action <'F-CO2-ABS-04'> F_CO2_ABS_04 { doc /* IFMチェックリストの下部機器ベイ配置図（OV-103）は、CO2吸収器をMD54Gの付近に示す。 */ }
            action <'F-CO2-ABS-05'> F_CO2_ABS_05 { doc /* 8 psiでの再突入では時間が許せばLiOHキャニスタを取り外し、キャビンファン1台の流量を820 lb/hr（装着時）から870 lb/hr（取外し時）に増やして、減圧下で重要な冷却の効率を上げる（A17-151B）。 */ }
            action <'F-CO2-ABS-06'> F_CO2_ABS_06 { doc /* A17-151Bの取外しは、乗員が打上げ・再突入用与圧服（LES）のヘルメットを着用しているか、PPCO2が管理下にあることを前提とする。 */ }
            action <'F-CO2-ABS-07'> F_CO2_ABS_07 { doc /* RCRS搭載機では打上げ用と再突入用にLiOHキャニスタを1個ずつ使い、もう一方のCO2吸収器スロットには臭気を除く活性炭キャニスタを入れる。 */ }
            action <'F-CO2-ABS-08'> F_CO2_ABS_08 { doc /* STS-135では交換口（ARS LiOHサービスドア）のラッチの1個が外れずキャニスタを交換できなくなり、軌道上の保守手順（IFM）でドアを開けた（IFA STS-135-V-05）。 */ }
        }
        package <'SSD-FD-CO2-ATCO-001'> FN_CO2_ATCO {
            action <'F-CO2-ATCO-01'> F_CO2_ATCO_01 { doc /* キャビン熱交換器を出た再生・調整済み空気の一部をATCOへ送り、COをCO2に変換する（SCOM 2.9節）。 */ }
            action <'F-CO2-ATCO-02'> F_CO2_ATCO_02 { doc /* ATCOは乗員が出すCOと、キャビン内の非金属材料のガス放出によるCOを除去し、生じたCO2はLiOHキャニスタで除かれる（訓練マニュアル3.2.6節）。 */ }
            action <'F-CO2-ATCO-03'> F_CO2_ATCO_03 { doc /* ATCOはキャビン熱交換器のすぐ下流にあり、触媒は白金2%・炭素担体である（訓練マニュアル3.2.6節）。 */ }
            action <'F-CO2-ATCO-04'> F_CO2_ATCO_04 { doc /* IFMチェックリストの下部機器ベイ配置図（OV-103）は、ATCOをキャビン熱交換器の近くに示す。 */ }
            action <'F-CO2-ATCO-05'> F_CO2_ATCO_05 { doc /* 1979年の飛行運用マニュアルの時点では、CO除去装置は採用が承認されたばかりで設計が完了しておらず、「Ambient Temperature Catalytic Oxidizer」と呼ぶ予定とされていた。 */ }
            action <'F-CO2-ATCO-06'> F_CO2_ATCO_06 { doc /* ATCOはSTS-4で初めて飛行し、性能評価の飛行試験要求（FTR 61VV002）は触媒の化学分析と飛行中のキャビン大気の試料で一部達成され、完了にはさらに2回の飛行を要するとされた（STS-4報告）。 */ }
            action <'F-CO2-ATCO-07'> F_CO2_ATCO_07 { doc /* STS-4報告は、キャビン大気試料で検出された化合物の数が減ったのはATCOを搭載した効果である可能性が高いとしている。 */ }
            action <'F-CO2-ATCO-08'> F_CO2_ATCO_08 { doc /* 火災の鎮火後はWCSのチャコールフィルタ、ATCO、LiOHキャニスタで燃焼生成物をキャビン大気から除去する（SCOM 6.8節）。 */ }
            action <'F-CO2-ATCO-09'> F_CO2_ATCO_09 { doc /* Monje（2015年）はシャトルのATCO触媒を白金2%・炭素担体とし、COの宇宙機最大許容濃度（SMAC）を7日で55 ppm、30日・180日で15 ppmと示す。 */ }
            action <'F-CO2-ATCO-10'> F_CO2_ATCO_10 { doc /* NASAは1970年代にシャトルの常温CO酸化触媒として白金2%・炭素担体を選び、シャトルの設計空間速度での新しい触媒の試験から、現行のATCO反応器には大きな余裕があると結論された（Nalette他、抄録で確認）。 */ }
        }
        package <'SSD-FD-CO2-CAN-001'> FN_CO2_CAN {
            action <'F-CO2-CAN-01'> F_CO2_CAN_01 { doc /* キャニスタ内の活性炭が臭気を抑え、CO2はLiOHと反応して炭酸リチウムになることで空気から除かれる（訓練マニュアル3.2.2節）。 */ }
            action <'F-CO2-CAN-02'> F_CO2_CAN_02 { doc /* LiOHとCO2の反応では、CO2 1 lbあたり875 Btuの熱が出る（1979年の飛行運用マニュアル）。 */ }
            action <'F-CO2-CAN-03'> F_CO2_CAN_03 { doc /* 廃水タンクの増加率は、代謝による水とLiOHとCO2の反応で生じる水を合わせて、過去の飛行で乗員1人あたり約0.25 lb/hr（6 lb/日）である（A17-102C）。 */ }
            action <'F-CO2-CAN-04'> F_CO2_CAN_04 { doc /* キャニスタ1個の定格は48 man-hoursである（SCOM 2.9節）。 */ }
            action <'F-CO2-CAN-05'> F_CO2_CAN_05 { doc /* LiOHによるCO2除去量の設計値は乗員1人1日あたり2.11 lbである（訓練マニュアル3.6.5節）。 */ }
            action <'F-CO2-CAN-06'> F_CO2_CAN_06 { doc /* キャニスタは直径6.68 in、長さ11.3 in、質量6.73 lbである（飛行運用マニュアル第12巻）。 */ }
            action <'F-CO2-CAN-07'> F_CO2_CAN_07 { doc /* キャニスタの外殻は6061系アルミニウム合金で、内側のNomexの袋が外殻が割れてもLiOHを保持する。使用後は地上のLiOH施設で再充填し、外殻は再充填の回数に制限のない、故障まで使う品目である（IFA STS-114-V-35）。 */ }
            action <'F-CO2-CAN-08'> F_CO2_CAN_08 { doc /* STS-59では同じ製造ロットの外殻2個が割れ（STS-51・STS-56でも同ロットで発生）、化学ミリング加工の削り過ぎと孔食による薄肉化が原因とされたが、Nomexの袋がLiOHを保持するため、そのまま飛行させる判断がなされた。 */ }
            action <'F-CO2-CAN-09'> F_CO2_CAN_09 { doc /* LiOHキャニスタはHF・HBr・HCl・フッ素・臭素を吸収するが、活性炭は1/4 lbしかなくHCNの除去は約15分が限度で、活性炭キャニスタ（活性炭5 lb、RCRS搭載飛行で搭載）は最大約2時間もつ（A13-152）。 */ }
            action <'F-CO2-CAN-10'> F_CO2_CAN_10 { doc /* 臭気対策として、STS-3以降は活性炭キャニスタを搭載し、臭気が問題になれば2つのLiOHキャニスタスロットの1つに装着することとした（STS-2報告）。 */ }
            action <'F-CO2-CAN-11'> F_CO2_CAN_11 { doc /* 火災後は、HClが5 ppm未満になるか軌道離脱噴射まで3時間未満になったら、LiOHキャニスタ1個をATCOキャニスタに替えてCOを除去する（A13-152C）。 */ }
            action <'F-CO2-CAN-12'> F_CO2_CAN_12 { doc /* EVA後のキャビン除染ではATCOキャニスタ2個を装着してヒドラジン類とアンモニアを除去し、各ATCOキャニスタは公称のキャビンファン流量で約90分ごとにキャビン1容積分を処理する（A15-203）。 */ }
        }
        package <'SSD-FD-CO2-MON-001'> FN_CO2_MON {
            action <'F-CO2-MON-01'> F_CO2_MON_01 { doc /* CABIN AIR信号調整器が、キャビンファン差圧・キャビン湿度（MCCのみ監視）・CO2分圧の各トランスデューサに給電する（訓練マニュアル3.5節）。 */ }
            action <'F-CO2-MON-02'> F_CO2_MON_02 { doc /* PPCO2トランスデューサは、キャビンファン下流でLiOHキャニスタへ分かれる手前のダクトに接続されている（訓練マニュアル図3-12）。 */ }
            action <'F-CO2-MON-03'> F_CO2_MON_03 { doc /* IFMチェックリストの下部機器ベイ配置図（OV-103）は、PPCO2センサをキャビンファンの近くに示す。 */ }
            action <'F-CO2-MON-04'> F_CO2_MON_04 { doc /* PPCO2はSM OPS 2・4のSM表示DISP 66（ENVIRONMENT）に表示される（訓練マニュアル3.5.1節）。 */ }
            action <'F-CO2-MON-05'> F_CO2_MON_05 { doc /* PPCO2の上限は長期で7.6 mmHg、最大2時間で15 mmHgである（SODB 3.4.6.1節）。 */ }
            action <'F-CO2-MON-06'> F_CO2_MON_06 { doc /* RCRS搭載機でPPCO2を把握できなくなった場合は、LiOHキャニスタを定期的に装着・交換してCO2を管理する（A17-155）。 */ }
            action <'F-CO2-MON-07'> F_CO2_MON_07 { doc /* IOAのCIL評価（1988年）では、PPCO2センサ（1個）の臨界度をNASAは2/2、IOAは3/3としたが、NASAが乗員の措置や定常保守によるPPCO2の管理を考慮しない保守的な定義を用いたことを理由に、IOAは指摘を取り下げた（ARS-320）。 */ }
            action <'F-CO2-MON-08'> F_CO2_MON_08 { doc /* オービタ・Spacehab・宇宙服（EMU）のPPCO2計測用に、応答が遅く電解液の信頼性に懸念のある電気化学式センサに代わる赤外線吸収式のトランスデューサが開発された（SAE 932145、抄録で確認）。 */ }
            action <'F-CO2-MON-09'> F_CO2_MON_09 { doc /* STS-108では、キャビン圧を10.2 psiaとしていた間のセンサ表示6.02 mmHgが、Hamilton Sundstrandの換算値で9.35 mmHg相当とされた。 */ }
            action <'F-CO2-MON-10'> F_CO2_MON_10 { doc /* COなどの燃焼生成物はCSA-CP（CO・HCN・HClを実時間で分析する携帯型分析器）で測り、通常は飛行1日目に取り出してセンサを確認し、必要ならゼロ校正する（SCOM 2.5節）。 */ }
            action <'F-CO2-MON-11'> F_CO2_MON_11 { doc /* CSA-CPより前に使われた燃焼生成物分析器（CPA）はCO・HF・HCl・HCNを測る携帯型分析器で、STS-41（1990年10月）から搭載された。 */ }
            action <'F-CO2-MON-12'> F_CO2_MON_12 { doc /* 携帯型のCO2モニタ（CDM）は電池で約10時間動作し、キャビン内のCO2を計測できる（Orbit Opsチェックリスト3-32）。 */ }
        }
        package <'SSD-FD-CO2-STW-001'> FN_CO2_STW {
            action <'F-CO2-STW-01'> F_CO2_STW_01 { doc /* 予備のLiOHキャニスタは最大30個を、ECLSSベイのパネルMD52Mの下に収める（訓練マニュアル3.2.2節）。 */ }
            action <'F-CO2-STW-02'> F_CO2_STW_02 { doc /* LiOHキャニスタ区画の寸法は22.25×39.12×30.08 in、収納ラックは21×7.30×12.52 in・28 lbである（飛行運用マニュアル第12巻）。 */ }
            action <'F-CO2-STW-03'> F_CO2_STW_03 { doc /* キャニスタは床下の収納区画から取り出して、ファン下流の環境制御系に装着し、定期的に交換する（飛行運用マニュアル第12巻）。 */ }
            action <'F-CO2-STW-04'> F_CO2_STW_04 { doc /* LiOHキャニスタは通常、就寝前と起床後、またはPPCO2が7.6（6.1）mmHg以上と確認されたときに交換し、1個交換か2個交換かは乗員数に応じてLiOHの利用を最大にする解析で決める（A17-151C）。 */ }
            action <'F-CO2-STW-05'> F_CO2_STW_05 { doc /* 就寝前と起床後のミッドデッキ作業では、それぞれ2個のうち1個のキャニスタを交換する（SCOM）。 */ }
            action <'F-CO2-STW-06'> F_CO2_STW_06 { doc /* 打上げ前はL-5:30に始まるASPチェックリストでLiOHキャニスタを装着する（SCOM）。 */ }
            action <'F-CO2-STW-07'> F_CO2_STW_07 { doc /* 交換中は両方のキャビンファンを止める。キャニスタの粉塵がファンで舞い上がり、目や鼻の刺激を起こした例がある（訓練マニュアル3.2.2節）。 */ }
            action <'F-CO2-STW-08'> F_CO2_STW_08 { doc /* ISSに備蓄したキャニスタを使うときは、LiOH粉塵への暴露を減らすため保護具を着用する（Orbit Opsチェックリスト）。 */ }
            action <'F-CO2-STW-09'> F_CO2_STW_09 { doc /* 未使用のLiOHキャニスタを最低2日分予備に保持し、使用済み（袋詰め）キャニスタは能力を解析でしか評価できないためレッドラインに数えない。LiOHを使い切った後のCO2制御手段はキャビン空気の船外パージだけで、2時間程度しかもたない（A17-157）。 */ }
            action <'F-CO2-STW-10'> F_CO2_STW_10 { doc /* 飛行延長で使用済みキャニスタを使う場合は、LiOHが1 lbm以上残るものだけを対象とし、なるべく早く使い、新しいキャニスタ1個と組み合わせ、PPCO2を通常7.6 mmHg未満に管理する（A17-158）。 */ }
            action <'F-CO2-STW-11'> F_CO2_STW_11 { doc /* LiOHキャニスタの数と乗員数が飛行終了（EOM）の時期を決める（A17-1001注[11]）。 */ }
            action <'F-CO2-STW-12'> F_CO2_STW_12 { doc /* STS-108では係留中にISSの装置が両機のPPCO2の大部分を管理し、交換計画より12個のLiOHキャニスタを節約したため、以後のシャトルの搭載数を減らすこととした。 */ }
        }
        package <'SSD-FD-ARS-IMU-001'> FN_ARS_IMU {
            action <'F-ARS-IMU-01'> F_ARS_IMU_01 { doc /* 3台のIMUは、3台のファンの1台がキャビン空気を300ミクロンフィルタを通して吸い込み3台のIMUに流すことで冷却され、ファンはAv Bay 1にある。 */ }
            action <'F-ARS-IMU-02'> F_ARS_IMU_02 { doc /* ファン出口空気はフライトデッキのIMU熱交換器を通って水冷却ループで冷却されてから乗員室へ戻る。 */ }
            action <'F-ARS-IMU-03'> F_ARS_IMU_03 { doc /* 各ファンはパネルL1のIMU FANスイッチでON/OFFし、1台で3台のIMUすべてを冷却できるため通常は1台で足り、各ファン出口の逆止弁が非運転ファンの逆流を防ぐ。 */ }
            action <'F-ARS-IMU-04'> F_ARS_IMU_04 { doc /* 強制空冷は3台のIMUすべてに供する3台のファンで構成され、同時に使うのは1台で、3台は冗長のために設けられている。 */ }
            action <'F-ARS-IMU-05'> F_ARS_IMU_05 { doc /* 上昇中は、主エンジン制御器を失いうるAC母線間短絡を防ぐため、湿度分離器とIMUファンの信号調整器を断電する（STS-6でこれらの信号調整器へ電力を送る配線束が短絡した）。 */ }
            action <'F-ARS-IMU-06'> F_ARS_IMU_06 { doc /* IMUファン差圧はBFSのSM SYS SUMM 1（DISP 78）にIMU FAN DPとして表示される。 */ }
            action <'F-ARS-IMU-07'> F_ARS_IMU_07 { doc /* ファン差圧が3.70（3.94）in H2O未満または4.95（4.71）in H2O超、あるいは選択時の回転数表示が10,000±240〜12,720±700 rpmの範囲外の場合にIMUファン喪失とし、適切な冷却に必要な最低流量は144 lb/hrである（A17-104）。 */ }
            action <'F-ARS-IMU-08'> F_ARS_IMU_08 { doc /* キャビンファン以外の回転機器（IMUファンを含む）は1相を失ったら代替機に切り替える（A17-154A）。 */ }
            action <'F-ARS-IMU-09'> F_ARS_IMU_09 { doc /* IMUファン3台すべての喪失はIMUのサイクル運用で軌道到達可とし、軌道上で掃除機のファンを取り付け、初日のPLSに入る（A17-1001 注[5]）。 */ }
            action <'F-ARS-IMU-10'> F_ARS_IMU_10 { doc /* IMUファンを止めておける時間は、IMUの冷却の制約から45分までである（A18-501C）。 */ }
            action <'F-ARS-IMU-11'> F_ARS_IMU_11 { doc /* 冷却空気の流路は、吸込みスクリーン・デブリトラップの目詰まりにはIMUフィルタの清掃（IFM）で、空気ダクトの閉塞にはIMUの緊急冷却（IFM）で回復する（MAL 6.1d）。 */ }
        }
        package <'SSD-FD-ARS-IMU-FAN-001'> FN_ARS_IMU_FAN {
            action <'F-ARS-IMU-FAN-01'> F_ARS_IMU_FAN_01 { doc /* IMUファンは3台あって通常は1台を運転し、各ファンは三相115 V ACの50 Wの電動機で駆動されて公称144 lb/hrを流し、2相の交流でも起動・運転できる（訓練マニュアル3.2.8節）。 */ }
            action <'F-ARS-IMU-FAN-02'> F_ARS_IMU_FAN_02 { doc /* ファンはアビオニクスベイ1にあり、1台で3台のIMUすべてを冷却できるため通常は1台で足りる（SCOM 2.9節）。 */ }
            action <'F-ARS-IMU-FAN-03'> F_ARS_IMU_FAN_03 { doc /* 3台のファンは並列で、どの1台でも必要な流量が得られる（1979年の飛行運用マニュアル）。 */ }
            action <'F-ARS-IMU-FAN-04'> F_ARS_IMU_FAN_04 { doc /* SCOMのGNCの節は、強制空冷は3台のIMUに共通の3台のファンから成り、同時に使うのは1台で、3台は冗長のために設けるとする。 */ }
            action <'F-ARS-IMU-FAN-05'> F_ARS_IMU_FAN_05 { doc /* 各ファン出口の逆止弁が非運転ファンを通る逆流を防ぎ、フラッパ式の逆止弁はファンが弁の前後に1 psiの差圧を生じると開く（訓練マニュアル3.2.8節）。 */ }
            action <'F-ARS-IMU-FAN-06'> F_ARS_IMU_FAN_06 { doc /* パネルL1にIMU FAN A・B・Cの3個のスイッチ（ON–OFF）があってファンに電力を加え、同時に使うのは1個である（訓練マニュアル表3-6）。 */ }
            action <'F-ARS-IMU-FAN-07'> F_ARS_IMU_FAN_07 { doc /* ファンA・B・Cは、パネルL4の各3個の遮断器からそれぞれAC1・AC2・AC3の三相電力をL1のスイッチを通して受ける（訓練マニュアル表3-6）。 */ }
            action <'F-ARS-IMU-FAN-08'> F_ARS_IMU_FAN_08 { doc /* IMUワークブックは、各IMUファンが別々の交流電源から給電され、スイッチはパネルL1、遮断器はパネルL4にあるとする。 */ }
            action <'F-ARS-IMU-FAN-09'> F_ARS_IMU_FAN_09 { doc /* 運用飛行規則A17-154Aは、キャビンファンと改修型のアビオニクスファンを除く機器は2相で再起動できるとする。 */ }
            action <'F-ARS-IMU-FAN-10'> F_ARS_IMU_FAN_10 { doc /* IFMチェックリストのアビオニクスベイ1の配置図には、IMUファンのダクト（IMU FAN DUCTS）が示されている（IFM 3-4）。 */ }
            action <'F-ARS-IMU-FAN-11'> F_ARS_IMU_FAN_11 { doc /* IOAのCIL評価（1988年）は、非運転ファン2台の逆止弁が故障するとIMU熱交換器を完全に迂回する空気の循環ループができ、2つの故障で乗員・機体の喪失に至るとして、NASAの臨界度に同意し指摘を取り下げた（ARS-277、逆止弁3個）。 */ }
            action <'F-ARS-IMU-FAN-12'> F_ARS_IMU_FAN_12 { doc /* 消音器の追加でIMUファンの2,000 Hz付近の騒音は大きく下がり、その後4個の消音器は4室を持つ一体型の消音器に改められた（Goodman、NOISE-CON 2010）。 */ }
        }
        package <'SSD-FD-ARS-IMU-HEX-001'> FN_ARS_IMU_HEX {
            action <'F-ARS-IMU-HEX-01'> F_ARS_IMU_HEX_01 { doc /* 暖まった空気はIMU熱交換器へ送られてARSの水冷却ループに熱を渡し、冷えた空気は乗員室へ戻る（訓練マニュアル3.2.8節）。 */ }
            action <'F-ARS-IMU-HEX-02'> F_ARS_IMU_HEX_02 { doc /* ファン出口の空気はフライトデッキにあるIMU熱交換器を通り、水冷却ループで冷やされてから乗員室へ戻る（SCOM 2.9節）。 */ }
            action <'F-ARS-IMU-HEX-03'> F_ARS_IMU_HEX_03 { doc /* 1979年の飛行運用マニュアルも、空気は乗員室へ戻る前にIMU熱交換器で冷やされるとする。 */ }
            action <'F-ARS-IMU-HEX-04'> F_ARS_IMU_HEX_04 { doc /* 水冷却ループでは、インターチェンジャで冷えた水がLCG熱交換器、ギャレーの水チラー、キャビン熱交換器、IMU熱交換器の順に流れてからバイパス流と合流し、ポンプへ戻る（訓練マニュアル3.3節）。 */ }
            action <'F-ARS-IMU-HEX-05'> F_ARS_IMU_HEX_05 { doc /* 水冷却ループは、キャビン熱交換器、IMU熱交換器、アビオニクスベイのコールドプレートと熱交換器から熱を集め、ATCSへ渡す（SCOM 2.9節）。 */ }
            action <'F-ARS-IMU-HEX-06'> F_ARS_IMU_HEX_06 { doc /* 2系統の水冷却ループを長時間同時に運転してインターチェンジャの熱移送能力を超えると、インターチェンジャの系統の水温が上がり、LCVG・水チラー・キャビン熱交換器・IMU熱交換器の冷却能力が下がる（訓練マニュアル3.3.6節）。 */ }
            action <'F-ARS-IMU-HEX-07'> F_ARS_IMU_HEX_07 { doc /* STS-1の消耗品・熱解析の表VIは、IMU冷却空気の出口温度の解析値108.2°Fを仕様上限130°Fと比べた（JSC-16720）。 */ }
            action <'F-ARS-IMU-HEX-08'> F_ARS_IMU_HEX_08 { doc /* 運用飛行規則A17-104は、ΔP 3.7 in H2Oで流量が約185 lb/hrとなり、これが健全な系でファンが出せる最大の流量であるため、それより低いΔPは健全性（漏れ）が疑わしい系で生じるとする。 */ }
            action <'F-ARS-IMU-HEX-09'> F_ARS_IMU_HEX_09 { doc /* 故障処置手順6.1dでは、空気ダクトの漏れがΔPの低下を招いた場合に、IMUのダクトの漏れを点検し、パッチキットのアルミテープで補修する（MAL 6.1d）。 */ }
            action <'F-ARS-IMU-HEX-10'> F_ARS_IMU_HEX_10 { doc /* 空気ダクトが閉塞した場合は、IFMのIMU緊急冷却で冷却を回復する（MAL 6.1d）。 */ }
            action <'F-ARS-IMU-HEX-11'> F_ARS_IMU_HEX_11 { doc /* IOAのCIL評価（1988年）は、IMU熱交換器（ARS-221）について、NASAのFMEAは熱交換器へのダクトを扱っており、熱交換器内の流れの制限には新しいFMEAを設け、ダクトを切ってキャビン空気を直接循環させれば空気の流れを回復できる（任務は失うが生命・機体への脅威ではない）ため、いずれも臨界度2/2とすると記す。 */ }
            action <'F-ARS-IMU-HEX-12'> F_ARS_IMU_HEX_12 { doc /* IOAは、IMU熱交換器自体からの外部漏れ（ARS-2211X、NASA臨界度2/2）は起こりえない故障とみなしつつ、熱交換器の前後の部品から空気が漏れる故障と影響が同じであるとして、指摘を取り下げた。 */ }
        }
        package <'SSD-FD-ARS-IMU-INL-001'> FN_ARS_IMU_INL {
            action <'F-ARS-IMU-INL-01'> F_ARS_IMU_INL_01 { doc /* IMUファンはキャビン空気をIMUの上に引き込み、IMUが発生した熱を空気に移して冷却する（訓練マニュアル3.2.8節）。 */ }
            action <'F-ARS-IMU-INL-02'> F_ARS_IMU_INL_02 { doc /* 3台のIMUは、3台のファンの1台がキャビン空気を300ミクロンフィルタを通して吸い込み、3台のIMUを横切って流すことで冷却される（SCOM 2.9節）。 */ }
            action <'F-ARS-IMU-INL-03'> F_ARS_IMU_INL_03 { doc /* IMUの熱制御は内部ヒータと強制空冷から成り、強制空冷はファンがキャビン空気を各IMUの筐体に通すもので、内部ヒータが働くために必要である（IMUワークブック2.10節）。 */ }
            action <'F-ARS-IMU-INL-04'> F_ARS_IMU_INL_04 { doc /* 1979年の飛行運用マニュアルは、IMUをキャビンから300ミクロンフィルタを通して吸い込んだ空気で冷やし、ファンのすぐ上流にファン保護用の600ミクロンフィルタを置くとする。 */ }
            action <'F-ARS-IMU-INL-05'> F_ARS_IMU_INL_05 { doc /* IMU #1・2・3のフィルタ・スクリーンはミッドデッキ天井のパネルMO42F・MO58Fの上前方にあり、スクイーズラッチの点検口を開けてクレビス工具で清掃する（IFM 4-5、約10分）。 */ }
            action <'F-ARS-IMU-INL-06'> F_ARS_IMU_INL_06 { doc /* 故障処置手順6.1dでは、IMUファンΔPの異常の切り分けで吸込みスクリーンの閉塞を点検し、デブリトラップの目詰まりによる閉塞であれば、IFMのMIDDECK (OVERHEAD) FILTER CLEANINGでIMUフィルタだけを清掃する（MAL 6.1d）。 */ }
            action <'F-ARS-IMU-INL-07'> F_ARS_IMU_INL_07 { doc /* STS-125では、IMUファンΔPの上昇に対してMCCが乗員にIMUフィルタの点検を求め、乗員は3枚のフィルタがほぼ同じ状態であることを確かめて清掃した（IFA STS-125-V-13）。 */ }
            action <'F-ARS-IMU-INL-08'> F_ARS_IMU_INL_08 { doc /* IMU出口ホース（3本）はIMUマニホールドにつながり、IMUの緊急冷却ではこれらをマニホールドから外して掃除機のホースの先に集め、掃除機でIMUに空気を通す（IFM I-3）。 */ }
            action <'F-ARS-IMU-INL-09'> F_ARS_IMU_INL_09 { doc /* STS-1の消耗品・熱解析は、IMUを通る空気流量を156 lb/hr（14.7 psia）とした（JSC-16720 3.3節）。 */ }
            action <'F-ARS-IMU-INL-10'> F_ARS_IMU_INL_10 { doc /* 同じ解析の表VIは、IMU冷却空気の入口温度の仕様上限を95°F（解析値79.6°F）とし、SODBの入口の上限は95°Fで、再評価による（まだ非公式の）上限は89°F、出口の上限は廃止されると注記する（JSC-16720）。 */ }
            action <'F-ARS-IMU-INL-11'> F_ARS_IMU_INL_11 { doc /* IMU冷却系は当初オービタで最も大きな騒音源で、GFEの消音器（入口3個・出口1個）が追加された（Goodman、NOISE-CON 2010）。 */ }
            action <'F-ARS-IMU-INL-12'> F_ARS_IMU_INL_12 { doc /* STS-2の騒音調査では、ミッドデッキのIMU吸込口で68 dBが計測された（STS-2報告2.5.5節）。 */ }
        }
        package <'SSD-FD-ARS-IMU-MON-001'> FN_ARS_IMU_MON {
            action <'F-ARS-IMU-MON-01'> F_ARS_IMU_MON_01 { doc /* IMU FAN信号調整器はIMUファンが正常に回っていることを確かめる回転数センサに給電し、H2O BYP LOOP 1 SNSR信号調整器は水ループ1のインターチェンジャ流量センサとIMUファンΔPセンサに給電する（訓練マニュアル3.5節）。 */ }
            action <'F-ARS-IMU-MON-02'> F_ARS_IMU_MON_02 { doc /* IMU FAN信号調整器には、パネルL4の遮断器（SIG CONDR IMU FAN）からAC3のB相の電力が供給される（訓練マニュアル表3-6）。 */ }
            action <'F-ARS-IMU-MON-03'> F_ARS_IMU_MON_03 { doc /* IMUファンΔPセンサには、パネルO14のMNAの遮断器（H2O BYP LOOP 1 SNSR）から電力が供給される（訓練マニュアル表3-6）。 */ }
            action <'F-ARS-IMU-MON-04'> F_ARS_IMU_MON_04 { doc /* IMUファンΔPはBFSのSM SYS SUMM 1（DISP 78）に表示され、表示範囲は0〜7 in H2Oである（訓練マニュアル図3-16）。 */ }
            action <'F-ARS-IMU-MON-05'> F_ARS_IMU_MON_05 { doc /* SPEC 66 ENVIRONMENT（DISP 66、SM OPS 2・4）は、IMUファンA・B・Cのうち運転中のファンを「*」で示し、ΔPを0〜7.0 in H2Oで示す（訓練マニュアル図3-19）。 */ }
            action <'F-ARS-IMU-MON-06'> F_ARS_IMU_MON_06 { doc /* 各表示は運転中のファンに「*」を付け、その右に状態を示す。空白は正常、「M」はデータなし、「↓」は運転していたファンの回転数が所定の限界より下がったことを表す（IMUワークブック2.10節）。 */ }
            action <'F-ARS-IMU-MON-07'> F_ARS_IMU_MON_07 { doc /* ΔPまたは回転数の異常はSMアラートのメッセージ（「S66 IMU FAN DP」「S66 IMU FN SPD A(B,C)」「SM1 CABIN IMU」）で知らせ、故障処置手順6.1d CABIN IMUで処置する（MAL 6.1d）。 */ }
            action <'F-ARS-IMU-MON-08'> F_ARS_IMU_MON_08 { doc /* ΔPの計測精度はフルスケール（7 in H2O）の±3.4%（0.238 in H2O）で、選択したファンの回転数表示は10,000±240〜12,720±700 rpmの範囲で正常を示す（A17-104）。 */ }
            action <'F-ARS-IMU-MON-09'> F_ARS_IMU_MON_09 { doc /* ΔPが失われたときは、回転数センサの「↓」表示でファンの故障を監視する（MAL 6.1d）。 */ }
            action <'F-ARS-IMU-MON-10'> F_ARS_IMU_MON_10 { doc /* OI MDM（OF1）を失うとIMUファンΔPとファンAの回転数センサが得られなくなり、ファンAで運転中ならファンB（C）に切り替える（MAL COMM SSR-10）。 */ }
            action <'F-ARS-IMU-MON-11'> F_ARS_IMU_MON_11 { doc /* AC3母線を失うとIMU FAN信号調整器が止まり、IMUファンA・B・Cの回転数の正常表示センサがすべて失われる（MAL EPS SSR-130）。 */ }
            action <'F-ARS-IMU-MON-12'> F_ARS_IMU_MON_12 { doc /* STS-125では、IMUファンΔPが飛行規則の限界（4.71）を上下するまで上昇したが、計測値が0.224 in H2O高くずれていた（許容の3.4%以内）ことが原因とされ、説明のついた事象として閉じられた（IFA STS-125-V-13）。 */ }
        }
        package <'SSD-FD-ARS-IMU-OPS-001'> FN_ARS_IMU_OPS {
            action <'F-ARS-IMU-OPS-01'> F_ARS_IMU_OPS_01 { doc /* 搭乗時にはIMUファン1台が運転済みで、上昇中はAC母線間の短絡で主エンジンを失うのを防ぐため、HUM SEPとIMU FANの信号調整器を断電しておく（STS-6でこれらの信号調整器へ電力を送る配線束が短絡した）（訓練マニュアル3.6.1節）。 */ }
            action <'F-ARS-IMU-OPS-02'> F_ARS_IMU_OPS_02 { doc /* 上昇中の交流負荷の管理では、キャビンファン・IMUファン・湿度分離器の再構成はMECO後まで要らないとする（A9-154の根拠）。 */ }
            action <'F-ARS-IMU-OPS-03'> F_ARS_IMU_OPS_03 { doc /* IMUファンは、ΔPが3.70（3.94）in H2O未満または4.95（4.71）in H2O超の場合か、選択時に回転数が異常を示す場合に喪失とし、適切な冷却に必要な最低流量は144 lb/hr（ΔP 4.95 in H2Oで供給）である（A17-104）。 */ }
            action <'F-ARS-IMU-OPS-04'> F_ARS_IMU_OPS_04 { doc /* 故障処置手順6.1dの公称構成はファンBの運転で、ΔPが3.7未満・4.95超（10.2 psi運用では3.0未満・3.8超）になるとファンを切り替えて原因を切り分け、IMUファンが止まったままIMUを30分を超えて運転するとIMUを損傷するおそれがあると警告する（MAL 6.1d）。 */ }
            action <'F-ARS-IMU-OPS-05'> F_ARS_IMU_OPS_05 { doc /* 1相を失った回転機器（キャビンファンを除く）は代替機に切り替える。2相での運転の寿命は（新品の機器で）168時間と確かめられており、性能も通常より下がるためである（A17-154A）。 */ }
            action <'F-ARS-IMU-OPS-06'> F_ARS_IMU_OPS_06 { doc /* 冷却機器の最大停止時間は、IMUの冷却の制約からIMUファンでは45分である（A18-501C）。 */ }
            action <'F-ARS-IMU-OPS-07'> F_ARS_IMU_OPS_07 { doc /* 有害物質（レベル3）がこぼれた場合は、拡散を防ぐためにフライトデッキの乗員がキャビンファンとIMUファンを止める。IMUファンを止めておける時間は45分までである（A13-155B）。 */ }
            action <'F-ARS-IMU-OPS-08'> F_ARS_IMU_OPS_08 { doc /* アビオニクスベイにHalonを放出した後の電源断でもIMUファンは止めない。ファンはアビオニクスベイ（1）内にあり、ベイの外にあるIMUは冷却なしでは30分を超えて運転できないためで、ファンが故障していれば直ちに冗長のファンを起動する（A17-53C）。 */ }
            action <'F-ARS-IMU-OPS-09'> F_ARS_IMU_OPS_09 { doc /* IMUファン3台すべての喪失は、IMUのサイクル運用で軌道到達可とし、軌道上で掃除機のファンを取り付け、初日のPLSに入る（A17-1001 注[5]）。 */ }
            action <'F-ARS-IMU-OPS-10'> F_ARS_IMU_OPS_10 { doc /* IMUの緊急冷却（IFM）は、3台のIMUファンがすべて故障したときに限り、掃除機をIMUファンの代わりに使って周囲の空気でIMUを冷やす手順で、所要1時間である（IFM I-1）。 */ }
            action <'F-ARS-IMU-OPS-11'> F_ARS_IMU_OPS_11 { doc /* ファンは3重の冗長で、1台が故障しても他の2台のどちらかを起動してIMUを冷却できるため、ファンの故障はIMUの内部ヒータの故障ほど重大ではない（IMUワークブック4.5節）。 */ }
            action <'F-ARS-IMU-OPS-12'> F_ARS_IMU_OPS_12 { doc /* STS-125では、ΔPの上昇に対してファンBからファンAへ切り替え、約65分後にファンCを起動して約3分間ファンAと並列に運転した後にファンAを止め、以後の飛行ではファンCを使った（IFA STS-125-V-13）。 */ }
        }
        package <'SSD-FD-ARS-RCRS-001'> FN_ARS_RCRS {
            action <'F-ARS-RCRS-01'> F_ARS_RCRS_01 { doc /* 再生式CO2除去装置（RCRS）は長期単独飛行向けでOV-105のみがハードウェア能力を持つが、ISS係留中は不要で今後の使用予定もなく、SCOMでは歴史的情報として記載されている。 */ }
            action <'F-ARS-RCRS-02'> F_ARS_RCRS_02 { doc /* CO2は2個の同一の固体アミン樹脂ベッドの一方にキャビン空気を通して除去し、樹脂（多孔質ポリマ基材にPEI吸着剤を被覆）は空気中の水蒸気と結合した水和アミンとしてCO2と弱い重炭酸結合を作るため、反応には水が必要である。 */ }
            action <'F-ARS-RCRS-03'> F_ARS_RCRS_03 { doc /* 一方のベッドが吸着する間に他方は加熱と真空排気で再生するため上昇・再突入中は使えず、吸着と再生は13分ごとに自動で切り替わり、完全な1サイクルは13分×2である。 */ }
            action <'F-ARS-RCRS-04'> F_ARS_RCRS_04 { doc /* RCRS搭載機は打上げと再突入にLiOHキャニスタを1個ずつ使い、もう一方のCO2吸収器スロットの活性炭キャニスタで臭気を除去し、10日以上の飛行では途中で交換する。 */ }
            action <'F-ARS-RCRS-05'> F_ARS_RCRS_05 { doc /* RCRSはミッドデッキ床下のvolume Dに設置し、主要部品は化学ベッド2個、真空サイクル弁と均圧弁、RCRSファン、流量制御弁、ullage-save圧縮機、冗長コントローラ2台（1・2）である。 */ }
            action <'F-ARS-RCRS-06'> F_ARS_RCRS_06 { doc /* 流量制御弁は打上げ前に乗員数「4」または「5〜7」に設定し、RCRSを通る空気流量をそれぞれ72 lb/hrまたは110 lb/hrとする。 */ }
            action <'F-ARS-RCRS-07'> F_ARS_RCRS_07 { doc /* 制御スイッチはパネルMO51Fにあり、コントローラ1・2のAC・DC電源、OPER/STBYを選ぶ3位置モーメンタリスイッチ、OPER/FAIL状態灯を備え、運転状態はOPS 2のSPEC 66 ENVIRONMENTで確認する。 */ }
            action <'F-ARS-RCRS-08'> F_ARS_RCRS_08 { doc /* PPCO2を7.6 mmHg未満に保てない場合またはPPCO2の把握を失った場合はRCRS喪失とし、両コントローラ（A・B）が故障すると手動運転の手段はない（A17-106）。 */ }
            action <'F-ARS-RCRS-09'> F_ARS_RCRS_09 { doc /* RCRSは真空源が無い上昇・再突入では停止し、軌道上ではOMS-2後なるべく早く起動して軌道離脱噴射前なるべく遅く停止し、軌道離脱準備で停止した後はウェーブオフ周回では再起動せず、ウェーブオフ日には消耗品が許せば再起動する（A17-155）。 */ }
            action <'F-ARS-RCRS-10'> F_ARS_RCRS_10 { doc /* キャビンまたはアビオニクスベイの火災後はRCRSを手動停止し（HCl・HF・HCNが固体アミンに不可逆に吸着するため）、LiOH・ATCOで汚染物質を除去した後に再起動する（A17-156）。 */ }
            action <'F-ARS-RCRS-11'> F_ARS_RCRS_11 { doc /* 再生に入るベッドの空気は、ullage-save圧縮機での吸出し（ステート4）と均圧弁による両ベッドの均圧（ステート5）で最大90%を回収し、真空へ失うキャビン空気を約1.6 lb/日に抑える（訓練マニュアル付録C.2.3）。 */ }
        }
        package <'SSD-FD-ARS-RCRS-BED-001'> FN_ARS_RCRS_BED {
            action <'F-ARS-RCRS-BED-01'> F_ARS_RCRS_BED_01 { doc /* CO2は同一の固体アミン樹脂の化学ベッド2個で除去し、一方のベッドが吸着する間に他方が再生する（訓練マニュアル付録C.2.1）。 */ }
            action <'F-ARS-RCRS-BED-02'> F_ARS_RCRS_BED_02 { doc /* 樹脂は多孔質のポリマ基材にポリエチレンイミン（PEI）の吸着剤を被覆したもので、0.5 mmの小さな多孔質の球に被覆して表面積と吸着容量を大きくしている（訓練マニュアル付録C.2.1）。 */ }
            action <'F-ARS-RCRS-BED-03'> F_ARS_RCRS_BED_03 { doc /* 樹脂はキャビン空気中の水蒸気と結合して水和アミンとなり、これがCO2と弱い重炭酸結合を作る。乾いたアミンはCO2と直接反応しないため、吸着には水が必要である（訓練マニュアル付録C.2.1）。 */ }
            action <'F-ARS-RCRS-BED-04'> F_ARS_RCRS_BED_04 { doc /* 再生中のベッドは熱処理と真空排気でCO2を脱着する。吸着中のベッドで生じた熱を再生中のベッドへ移して重炭酸結合を切り、放出したCO2は真空へ排気して船外へ捨てる（訓練マニュアル付録C.2.1）。 */ }
            action <'F-ARS-RCRS-BED-05'> F_ARS_RCRS_BED_05 { doc /* RCRSは機体の既存の真空ベント管を使って脱着中のベッドを排気する（訓練マニュアル付録C.2.2）。 */ }
            action <'F-ARS-RCRS-BED-06'> F_ARS_RCRS_BED_06 { doc /* 真空による脱着は4組の真空サイクル弁（VCV）で制御し、各ベッドの入口と出口にある弁が、吸着中の通気、脱着のための真空への開放、ベッドの隔離を行う（訓練マニュアル付録C.2.2）。 */ }
            action <'F-ARS-RCRS-BED-07'> F_ARS_RCRS_BED_07 { doc /* 各VCVは空気ポペットと真空ポペットを持ち、アクチュエータAはベッドAの空気ポペットとベッドBの真空ポペットを、アクチュエータBはベッドAの真空ポペットとベッドBの空気ポペットを動かす。アクチュエータは、ポペット前後の差圧が3.4 psiを超えるとポペットが不用意に開かない大きさにしてある（訓練マニュアル付録C.2.2）。 */ }
            action <'F-ARS-RCRS-BED-08'> F_ARS_RCRS_BED_08 { doc /* 吸着の工程は10分54秒で、その間に他方のベッドはCO2を真空へ脱着する（訓練マニュアル付録C.2.3のステート2・8）。 */ }
            action <'F-ARS-RCRS-BED-09'> F_ARS_RCRS_BED_09 { doc /* 制御器に電源を入れた直後の起動シーケンスでは、固体アミンの劣化でベッドAにたまったアンモニアを除くため、ベッドAを2分間真空へ排気する（訓練マニュアル付録C.2.3）。 */ }
            action <'F-ARS-RCRS-BED-10'> F_ARS_RCRS_BED_10 { doc /* 真空ベント隔離弁が閉じた場合、真空ベントダクトが詰まった場合、ARSのダクトに漏れがある場合は、RCRSのCO2除去は効かない（A17-106A）。 */ }
            action <'F-ARS-RCRS-BED-11'> F_ARS_RCRS_BED_11 { doc /* 火災の燃焼生成物のうちHCl・HF・HCNは固体アミンと不可逆に反応し、通常運転で真空に曝しても除かれずに吸着部位に残って、RCRSのCO2除去能力を下げる（A17-156）。 */ }
        }
        package <'SSD-FD-ARS-RCRS-CTL-001'> FN_ARS_RCRS_CTL {
            action <'F-ARS-RCRS-CTL-01'> F_ARS_RCRS_CTL_01 { doc /* 作動中の制御器の制御論理がRCRSの運転サイクルを管理し、各構成品と計装へ出力信号と電力を供給し、計装からの入力で故障を検知する（訓練マニュアル付録C.2.2）。 */ }
            action <'F-ARS-RCRS-CTL-02'> F_ARS_RCRS_CTL_02 { doc /* 2台の制御器のうち作動するのは1台で、同時に作動させると制御器1が制御器2に優先する。2台を同時に給電する手順はない（訓練マニュアル付録C.2.2）。 */ }
            action <'F-ARS-RCRS-CTL-03'> F_ARS_RCRS_CTL_03 { doc /* 運転シーケンスは周期的な工程で、起動直後の始動期間の後は26分ごとに繰り返す。当初は30分周期で設計されたが、吸着性能を上げるため短縮された（訓練マニュアル付録C.2.3）。 */ }
            action <'F-ARS-RCRS-CTL-04'> F_ARS_RCRS_CTL_04 { doc /* 運転シーケンス（図C-5）は、ベッドAが吸着しベッドBが再生する半周期と、ベッドを入れ替えた半周期から成り、各半周期は吸着・再生の工程の後にullage-save圧縮機の工程と均圧の工程を行う（訓練マニュアル付録C.2.3）。 */ }
            action <'F-ARS-RCRS-CTL-05'> F_ARS_RCRS_CTL_05 { doc /* SCOMは、吸着と再生が13分ごとに自動で入れ替わり、13分の工程2回で1周期となるとする。 */ }
            action <'F-ARS-RCRS-CTL-06'> F_ARS_RCRS_CTL_06 { doc /* パネルMO51Fには、制御器1・2のAC・DC電源スイッチ、OPER（運転シーケンスの開始）とSTBY（待機、シーケンスの停止）を選ぶ3位置モーメンタリのモードスイッチ、共通計装の電源スイッチと、各制御器の状態灯がある（訓練マニュアル付録C.3）。 */ }
            action <'F-ARS-RCRS-CTL-07'> F_ARS_RCRS_CTL_07 { doc /* 交流電源の遮断器はMO51Fの電源スイッチの下に、直流の遮断器はパネルML86B:Eにある。制御器1はAC1とMN A、制御器2はAC3とMN Cから給電される（訓練マニュアル付録C.3）。 */ }
            action <'F-ARS-RCRS-CTL-08'> F_ARS_RCRS_CTL_08 { doc /* 故障検知の論理は各パラメータ・圧縮機回転数・RCRSの弁位置を監視し、故障を検知するとRCRSを停止して、MO51Fの該当する制御器の故障灯を点灯させ、故障ディスクリートのテレメトリを6秒間「1」にする。故障灯はディスクリートが「0」に戻っても点灯したままである（訓練マニュアル付録C.5）。 */ }
            action <'F-ARS-RCRS-CTL-09'> F_ARS_RCRS_CTL_09 { doc /* RCRSは自動の制御器を必要とし手動で運転する手段がないため、両制御器（A・B）が故障すると運転できない。自動停止の論理は、ベッド圧力・ベッド差圧・圧縮機回転数・弁位置の表示が許容できなければRCRSを停止する（A17-106A）。 */ }
            action <'F-ARS-RCRS-CTL-10'> F_ARS_RCRS_CTL_10 { doc /* 故障処置手順6.8aは、MO51Fの表示灯とSPEC 66の表示から、MN A（C）電源の喪失、AC1（3）φA電源の喪失、制御器の故障停止、共通BITE、制御器の全電源喪失などの故障モードを判別する（MAL 6.8a）。 */ }
            action <'F-ARS-RCRS-CTL-11'> F_ARS_RCRS_CTL_11 { doc /* 故障処置手順6.8aの注記は、系統が11分ごとに2分6秒間ベッドを隔離することと、系統の1周期に26分かかることを示す（MAL 6.8a）。 */ }
            action <'F-ARS-RCRS-CTL-12'> F_ARS_RCRS_CTL_12 { doc /* Orbit Opsチェックリストの表示灯試験では、MO51FのRCRS CNTLR 1・2の灯（各2個）が点灯することを確かめる。 */ }
        }
        package <'SSD-FD-ARS-RCRS-FAN-001'> FN_ARS_RCRS_FAN {
            action <'F-ARS-RCRS-FAN-01'> F_ARS_RCRS_FAN_01 { doc /* キャビン空気の一部をARSのキャビンファンの上流から取り出してRCRSに通し、RCRSを流れる空気はARSの全流量の約6%である（訓練マニュアル付録C.2.1）。 */ }
            action <'F-ARS-RCRS-FAN-02'> F_ARS_RCRS_FAN_02 { doc /* RCRSファンは、CO2を効率よく除去するために吸着中のベッドへ空気を押し通す（訓練マニュアル付録C.2.2）。 */ }
            action <'F-ARS-RCRS-FAN-03'> F_ARS_RCRS_FAN_03 { doc /* ファンのすぐ下流に2位置の弁があってRCRSの流量を調整し、2つの位置は乗員4〜5名用と6〜7名用の大きさで、打上げ前に適切な位置に設定する（訓練マニュアル付録C.2.2）。 */ }
            action <'F-ARS-RCRS-FAN-04'> F_ARS_RCRS_FAN_04 { doc /* SCOMは、打上げ前に流量制御弁を乗員数「4」または「5〜7」に設定し、RCRSの流量をそれぞれ72 lb/hr・110 lb/hrにするとしている。 */ }
            action <'F-ARS-RCRS-FAN-05'> F_ARS_RCRS_FAN_05 { doc /* ファンの上流にはフィルタ・消音器の組立があり、フィルタは粒子がファンと固体アミンのベッドに入るのを防ぎ、消音器は入口ダクトを通って伝わるファンの騒音を下げる（訓練マニュアル付録C.2.2）。 */ }
            action <'F-ARS-RCRS-FAN-06'> F_ARS_RCRS_FAN_06 { doc /* 入口のフィルタは、ロッカー2個を外して点検パネルを開ければ飛行中に清掃できる（訓練マニュアル付録C.2.2）。 */ }
            action <'F-ARS-RCRS-FAN-07'> F_ARS_RCRS_FAN_07 { doc /* SCOMのRCRS系統図は、キャビン空気ループからの入口にフィルタ・消音器・ファン組立（40ミクロン）を置き、流量制御弁を備えることを示す。 */ }
            action <'F-ARS-RCRS-FAN-08'> F_ARS_RCRS_FAN_08 { doc /* 故障処置手順6.8aでは、フィルタ差圧が0.5（10.2 psia運用では0.35）を超える場合にフィルタの閉塞と流量制御弁の設定を疑い、IFMのEDO RCRSフィルタ清掃と流量制御弁の調整で、弁の位置が乗員数に合っていることを確かめる（MAL 6.8a）。 */ }
            action <'F-ARS-RCRS-FAN-09'> F_ARS_RCRS_FAN_09 { doc /* RCRSの流量は限られているため、火災後の汚染物質の除去にはRCRSは効率が悪い（A17-156）。 */ }
        }
        package <'SSD-FD-ARS-RCRS-MON-001'> FN_ARS_RCRS_MON {
            action <'F-ARS-RCRS-MON-01'> F_ARS_RCRS_MON_01 { doc /* 制御器1・2はそれぞれのベッド圧力センサとベッド差圧センサに給電し、それ以外の共通計装（CO2分圧・真空圧力・フィルタ差圧・入口空気温度）はどちらの制御器を使っても性能を監視できるが、冗長性はない（訓練マニュアル付録C.4）。 */ }
            action <'F-ARS-RCRS-MON-02'> F_ARS_RCRS_MON_02 { doc /* 表C-1のセンサの範囲は、ベッド圧力0〜20 psia、ベッド差圧0〜5 in H2O、入口温度32〜133°F、CO2分圧0〜30 mmHg、真空圧力0〜5 mmHg、フィルタ差圧0〜3 in H2Oである（訓練マニュアル付録C.4）。 */ }
            action <'F-ARS-RCRS-MON-03'> F_ARS_RCRS_MON_03 { doc /* 共通計装は制御機能を持たず、システム評価のためにダウンリンクされるだけである（訓練マニュアル付録C.4）。 */ }
            action <'F-ARS-RCRS-MON-04'> F_ARS_RCRS_MON_04 { doc /* 乗員はSPEC 66 ENVIRONMENTの右下でRCRSの運転を確認し、表示はCO2 CNTLR 1・2、FILTER ΔP、PPCO2、TEMP、BED A PRESS・B PRESS、ΔP、VAC PRESSである（訓練マニュアル付録C.4・表C-2）。 */ }
            action <'F-ARS-RCRS-MON-05'> F_ARS_RCRS_MON_05 { doc /* CO2 CNTLRの表示はAC電源とDC電源のONディスクリートを要する多重ディスクリートで、「*」は給電中だが運転していないこと、「↓」は故障から6秒間だけ現れることを示す（訓練マニュアル表C-2の注）。 */ }
            action <'F-ARS-RCRS-MON-06'> F_ARS_RCRS_MON_06 { doc /* RCRSに固有のSMメッセージは2つあり、「S66 CO2 RL SYS」は制御器が故障したか故障検知の論理がいずれかのベッドの圧力異常を検知したとき、「S66 CO2 RL SYS PCO2」はCO2分圧が限界外のときに出る（訓練マニュアル付録C.6）。 */ }
            action <'F-ARS-RCRS-MON-07'> F_ARS_RCRS_MON_07 { doc /* SCOMのRCRS系統図は、RCRSのCO2分圧・入口温度・フィルタ差圧・真空圧力と、制御器1・2それぞれのベッド圧力・ベッド差圧の計測点を示す。 */ }
            action <'F-ARS-RCRS-MON-08'> F_ARS_RCRS_MON_08 { doc /* 故障処置手順6.8bは、オービタのPPCO2とRCRSのPPCO2の差が2 mmHgを超える場合や、Spacelabモジュールを搭載していればそのCO2センサとの比較から、どちらのセンサが故障したかを判定する（MAL 6.8b）。 */ }
            action <'F-ARS-RCRS-MON-09'> F_ARS_RCRS_MON_09 { doc /* OI MDM（OF1）を失うと、制御器1のDC電源表示・ベッドA圧力・故障表示、真空圧力、制御器2のAC電源表示・ベッドB圧力が得られなくなり、制御器1を使っている場合は制御器の構成を切り替える（MAL COMM SSR-10）。 */ }
            action <'F-ARS-RCRS-MON-10'> F_ARS_RCRS_MON_10 { doc /* PPCO2を把握できなくなった場合はRCRSのCO2除去能力を正しく評価できないため、LiOHキャニスタを定期的に装着・交換してCO2を管理する（A17-155B.4）。 */ }
        }
        package <'SSD-FD-ARS-RCRS-OPS-001'> FN_ARS_RCRS_OPS {
            action <'F-ARS-RCRS-OPS-01'> F_ARS_RCRS_OPS_01 { doc /* RCRSは真空源のない上昇・再突入では停止し、その間はLiOHキャニスタでPPCO2を制御する。再突入まで作動させたままでも、真空源を失ってRCRSが停止するだけで損傷はない（A17-155A）。 */ }
            action <'F-ARS-RCRS-OPS-02'> F_ARS_RCRS_OPS_02 { doc /* 軌道上ではOMS-2後なるべく早く起動して正常に作動するかをすぐに確かめ、軌道離脱噴射前なるべく遅く停止して、搭載したLiOHキャニスタの使用を減らす。停止時には新しいLiOHキャニスタを装着して、軌道離脱準備と再突入のCO2を制御する（A17-155B.1）。 */ }
            action <'F-ARS-RCRS-OPS-03'> F_ARS_RCRS_OPS_03 { doc /* 軌道離脱準備で停止した後は、作業負荷が大きいためウェーブオフの周回では再起動せず、ウェーブオフの日には極低温の消耗品が追加の電力消費を許せば再起動する（A17-155B.2）。 */ }
            action <'F-ARS-RCRS-OPS-04'> F_ARS_RCRS_OPS_04 { doc /* キャビン減圧とエアロック減圧の間はRCRSを手動で停止する。作動させたままだと制御器の論理が真空ベント管やキャビン圧の入力で停止し、S66 CO2 RL SYS MALFとMO51Fの故障灯が出て、電源を切って入れ直さなければ再開できない。停止は約20分と短く、PPCO2も圧力の低下で下がる（A17-155B.3）。 */ }
            action <'F-ARS-RCRS-OPS-05'> F_ARS_RCRS_OPS_05 { doc /* RCRSは、PPCO2を7.6 mmHg未満に保てない場合と、PPCO2を把握できなくなった場合に喪失とする（A17-106）。 */ }
            action <'F-ARS-RCRS-OPS-06'> F_ARS_RCRS_OPS_06 { doc /* RCRSを失った場合はLiOHキャニスタを装着し、搭載数が限られるため、その数が飛行終了（EOM）を決める（A17-155B.4）。 */ }
            action <'F-ARS-RCRS-OPS-07'> F_ARS_RCRS_OPS_07 { doc /* オービタ系統のGo/No-Go基準では、RCRSを失うとLiOHキャニスタの数と乗員数がEOMを決め、PLSの機会を見送るには未使用のLiOHを最低2日分予備に持つ必要がある（A2-1001注[7]）。 */ }
            action <'F-ARS-RCRS-OPS-08'> F_ARS_RCRS_OPS_08 { doc /* キャビンまたはアビオニクスベイの火災の後はRCRSを手動で停止し、LiOH・活性炭とATCOのキャニスタで汚染物質を除いた後に再起動してCO2の除去を続ける（A17-156）。 */ }
            action <'F-ARS-RCRS-OPS-09'> F_ARS_RCRS_OPS_09 { doc /* 有害物質（レベル4）がオービタの大気に漏れた場合、RCRSを使う飛行では固体アミンの汚染を防ぐためRCRSの電源を切る（A13-155A）。 */ }
            action <'F-ARS-RCRS-OPS-10'> F_ARS_RCRS_OPS_10 { doc /* SCOMの運用の節は、RCRS搭載機では軌道投入後に乗員がRCRSを起動し、以後は通常の操作なしに13分ごとにベッドが切り替わり（26分周期）、10日以上の飛行では途中で活性炭キャニスタを交換し、軌道離脱準備でLiOHキャニスタを交換してRCRSを停止するとする。 */ }
            action <'F-ARS-RCRS-OPS-11'> F_ARS_RCRS_OPS_11 { doc /* 故障処置手順6.8aでは、故障が一方の制御器だけなら他方の制御器（SYS 2(1)）で運転を続け、両方の制御器に及ぶならRCRSを停止し、LiOHキャニスタ1個を装着してMCCとLiOHの運用計画を決める（MAL 6.8a）。 */ }
            action <'F-ARS-RCRS-OPS-12'> F_ARS_RCRS_OPS_12 { doc /* STS-65では、RCRSをリストリクタ付きのLiOHキャニスタで補い、15時間ごとの交換でCO2分圧を平均2.3 mmHg（最大3.0 mmHg）に保った。 */ }
        }
        package <'SSD-FD-ARS-RCRS-USC-001'> FN_ARS_RCRS_USC {
            action <'F-ARS-RCRS-USC-01'> F_ARS_RCRS_USC_01 { doc /* 6個の均圧弁（PEV）は、化学ベッドの圧力をそろえたり調整したりし、ullage-save圧縮機がベッドを排気できるようにする（訓練マニュアル付録C.2.2）。 */ }
            action <'F-ARS-RCRS-USC-02'> F_ARS_RCRS_USC_02 { doc /* 各PEVは通電で開く2つのコイルを持つソレノイド弁で、2台の制御器がそれぞれ一方のコイルを動かすため、コイル1つや制御器1台を失っても系統は失われない。電源を失うと弁は自動で閉じる（訓練マニュアル付録C.2.2）。 */ }
            action <'F-ARS-RCRS-USC-03'> F_ARS_RCRS_USC_03 { doc /* ullage-save圧縮機は各脱着工程の始めに脱着するベッドを排気し、抜いた空気を乗員室へ戻して、真空へ捨てるキャビン空気を減らす。元のキャビン圧に応じてベッド内の空気の70〜80%を回収し、圧縮機出口の消音器が騒音を下げる（訓練マニュアル付録C.2.2）。 */ }
            action <'F-ARS-RCRS-USC-04'> F_ARS_RCRS_USC_04 { doc /* ステート4では、圧縮機がPEV 2を通して75秒間ベッドAの空気を吸い出し、14.7 psiaから約3 psiaまで下げる（訓練マニュアル付録C.2.3）。 */ }
            action <'F-ARS-RCRS-USC-05'> F_ARS_RCRS_USC_05 { doc /* ステート5ではPEV 2と5を開いて両ベッドの圧力をそろえ、再生に入るベッドに残る空気の半分を他方のベッドへ移す（ベッドの空気量の約10%を回収）。ステート4・5で再生するベッドの空気の最大90%を回収し、真空へ失う空気を約1.6 lb/日に抑える（訓練マニュアル付録C.2.3）。 */ }
            action <'F-ARS-RCRS-USC-06'> F_ARS_RCRS_USC_06 { doc /* ステート6では、PEV 1でベッドAを真空側へ減圧し、PEV 6でベッドBをキャビン空気で再加圧する30秒の工程で、ポペットの両側の圧力をそろえる。VCVは3.4 psiを超える差圧に逆らって動けず、これはベッドがキャビン空気と真空の両方に開くのを防ぐための制限である（訓練マニュアル付録C.2.3）。 */ }
            action <'F-ARS-RCRS-USC-07'> F_ARS_RCRS_USC_07 { doc /* 半周期の最後（ステート12）では、PEV 3でベッドAをキャビン空気で再加圧し、PEV 4でベッドBを真空へ排気して、26分の周期を終える（訓練マニュアル付録C.2.3）。 */ }
            action <'F-ARS-RCRS-USC-08'> F_ARS_RCRS_USC_08 { doc /* 圧縮機が故障してもRCRSは運転を続けるが、再生のたびに真空へ失うキャビン空気が増え、この事象は飛行中にも起きている（訓練マニュアル付録C.2.2）。 */ }
            action <'F-ARS-RCRS-USC-09'> F_ARS_RCRS_USC_09 { doc /* 圧縮機は起動30秒後に、排気中のベッドの圧力が開始時の2/3未満に下がったかを確かめ、下がらなければ制御器を入れ直すか他方の制御器を選ぶまで止められる。この故障では故障灯もテレメトリも出ず、ullage-saveの工程でベッド圧が下がらないことだけが手がかりになる（訓練マニュアル付録C.5）。 */ }
            action <'F-ARS-RCRS-USC-10'> F_ARS_RCRS_USC_10 { doc /* RCRSの運転は船外へのベント工程で窒素（N2）を消費し、長期飛行でN2の必要量が増える要因の一つとなる（訓練マニュアル2.2節）。 */ }
            action <'F-ARS-RCRS-USC-11'> F_ARS_RCRS_USC_11 { doc /* SCOMのRCRS系統図は、6個の均圧弁（PEV 1〜6）の弁組立と圧縮機を示す。 */ }
        }
        package <'SSD-FD-ARS-THC-001'> FN_ARS_THC {
            action <'F-ARS-THC-01'> F_ARS_THC_01 { doc /* キャビン温度制御弁はキャビン熱交換器を迂回する空気量を配分する可変位置弁で、乗員が手動で、または2台のキャビン温度コントローラの一方が自動で位置決めし、弁と2台のコントローラはパネルMD44Fの下のECLSSベイにある。 */ }
            action <'F-ARS-THC-02'> F_ARS_THC_02 { doc /* パネルL1のCABIN TEMP CNTLRスイッチを1にするとコントローラ1が有効になり、CABIN TEMPロータリスイッチの位置に応じて空気流の0〜70%を熱交換器の外へ迂回させ、全COOLで約65°F、全WARMで約80°Fとなる。 */ }
            action <'F-ARS-THC-03'> F_ARS_THC_03 { doc /* コントローラ1が故障した場合は乗員がパネルMD44Fでアクチュエータアームのリンクをコントローラ2へ付け替えてからCABIN TEMP CNTLRを2にし、OFF位置では両コントローラ・ロータリスイッチ・自動制御の電源が断たれる。 */ }
            action <'F-ARS-THC-04'> F_ARS_THC_04 { doc /* 熱交換器を通った空気とバイパス空気は下流の給気ダクトで合流してCDR・PLTコンソールと各所のダクト吹出口から乗員室へ吹き出され、上昇・再突入では最大冷却のためCABIN TEMPを全COOLにする。 */ }
            action <'F-ARS-THC-05'> F_ARS_THC_05 { doc /* キャビン熱交換器出口温度はパネルO1のAIR TEMP計器下のロータリスイッチをCAB HX OUTにすると表示でき、145°Fを超えるとパネルF7の黄色AV BAY/CABIN AIR警報灯が点灯する。 */ }
            action <'F-ARS-THC-06'> F_ARS_THC_06 { doc /* コントローラやロータリスイッチで弁を制御できない場合、乗員はパネルMD44Fでバイパス弁アームを4つの固定穴（FULL COOL、2/3 COOL、1/3 COOL、FULL HEAT）の一つにピンで固定する。 */ }
            action <'F-ARS-THC-07'> F_ARS_THC_07 { doc /* 熱交換器で凝縮した水分は空気流でスラーパへ押し出され、2台の湿度分離器の一方がスラーパから空気と水を吸い込んで遠心力で分離し、公称約1 lb/hr・最大約4 lb/hrの水を廃水タンクへ送り、空気は排気ダクトでキャビンへ戻す。 */ }
            action <'F-ARS-THC-08'> F_ARS_THC_08 { doc /* ファンセパレータA・BはパネルL1のHUMIDITY SEP A・Bスイッチで個別に制御して通常は1台を使い、乗員室の相対湿度は通常30〜65%に保たれる。 */ }
            action <'F-ARS-THC-09'> F_ARS_THC_09 { doc /* ISSミッション向けに、軌道上で湿度分離器の凝縮水を緊急用水容器（CWC）へ切り替えて送れるよう改修されており、ISSからの分離後にCWCは緊急クロスタイ廃水QDから機外へ排出される。 */ }
            action <'F-ARS-THC-10'> F_ARS_THC_10 { doc /* キャビン温度を95（90）°F未満に保てない、A13-52のPPCO2制約を満たせない、または湿度制御に失敗した（通常6±1 lb/day/人の廃水タンク増加率の説明できない低下、構造や機器の結露）場合はキャビン大気制御の喪失とする（A17-102）。 */ }
            action <'F-ARS-THC-11'> F_ARS_THC_11 { doc /* 湿度分離器の作動は、HUM SEP信号調整器が給電する回転数センサで確かめ、キャビン熱交換器の空気出口温度とキャビン温度のセンサには、キャビン温度コントローラと同じCABIN CNTLR 1の遮断器が給電する（訓練マニュアル3.5節）。 */ }
        }
        package <'SSD-FD-ARS-THC-HX-001'> FN_ARS_THC_HX {
            action <'F-ARS-THC-HX-01'> F_ARS_THC_HX_01 { doc /* キャビン熱交換器は、キャビン空気が拾った熱をARS水冷却ループへ移す空気/水熱交換器で、キャビンファンが暖かいキャビン空気を送り込んで冷やす（訓練マニュアル3.2.4節）。 */ }
            action <'F-ARS-THC-HX-02'> F_ARS_THC_HX_02 { doc /* キャビン空気中の湿気は熱交換器内のslurperバーに凝縮し、凝縮水は熱交換器から湿度分離器へ引き出される（訓練マニュアル3.2.4節）。 */ }
            action <'F-ARS-THC-HX-03'> F_ARS_THC_HX_03 { doc /* 熱交換器で生じた凝縮水は空気流でslurperへ押し出され、2台の湿度分離器の一方がslurperから空気と水を吸い出す（SCOM 2.9節）。 */ }
            action <'F-ARS-THC-HX-04'> F_ARS_THC_HX_04 { doc /* 1979年の飛行運用マニュアルは、空気が熱交換器内のコールドプレートの間を通るときの温度変化でプレート上に凝縮が生じるとする。 */ }
            action <'F-ARS-THC-HX-05'> F_ARS_THC_HX_05 { doc /* 水冷却ループの冷えた水は、液冷服熱交換器と飲料水チラーに続いてキャビン熱交換器とIMU熱交換器を通り、各ループのポンプパッケージへ戻る（SCOM 2.9節）。 */ }
            action <'F-ARS-THC-HX-06'> F_ARS_THC_HX_06 { doc /* ATCOはキャビン熱交換器のすぐ下流にあり、熱交換器を出た空気の一部がATCOを通る（訓練マニュアル3.2.6節）。 */ }
            action <'F-ARS-THC-HX-07'> F_ARS_THC_HX_07 { doc /* RCRS搭載時は、RCRSでCO2を除いた空気もキャビン熱交換器を通して送られる（SCOM 2.9節）。 */ }
            action <'F-ARS-THC-HX-08'> F_ARS_THC_HX_08 { doc /* 運用飛行規則A13-152は、キャビン温度コントローラを全COOLにすると熱交換器を通る空気流量が最大になり、湿度分離器で除く汚染物質が増えるとする。 */ }
            action <'F-ARS-THC-HX-09'> F_ARS_THC_HX_09 { doc /* STS-4では熱交換器・slurper組立の空気出口ダクトに遊離水がないことを飛行中に2回点検し、STS-3後のslurper部の清掃が遊離水の再発を防いだ可能性があるとされた。 */ }
            action <'F-ARS-THC-HX-10'> F_ARS_THC_HX_10 { doc /* IOAのCIL評価（1988年）は、slurperの配管・継手（ARS-344）について、追加情報によりNASAの臨界度（3/2R）に同意して指摘を取り下げた。 */ }
        }
        package <'SSD-FD-ARS-THC-MON-001'> FN_ARS_THC_MON {
            action <'F-ARS-THC-MON-01'> F_ARS_THC_MON_01 { doc /* CABIN CNTLR 1の遮断器は、キャビン温度コントローラのほか、キャビン熱交換器の空気出口温度センサとキャビン温度センサに給電する（訓練マニュアル3.5節）。 */ }
            action <'F-ARS-THC-MON-02'> F_ARS_THC_MON_02 { doc /* HUM SEP信号調整器は、湿度分離器が正常に回っていることを確かめる回転数センサに給電する（訓練マニュアル3.5節）。 */ }
            action <'F-ARS-THC-MON-03'> F_ARS_THC_MON_03 { doc /* SCOMのキャビン空気系統図は、キャビン温度コントローラにつながるキャビン温度センサとダクト温度センサ、キャビン温度選択器を示す。 */ }
            action <'F-ARS-THC-MON-04'> F_ARS_THC_MON_04 { doc /* 熱交換器下流のセンサの温度データはパネルO1の兼用のAIR TEMP計器へ直接送られ、SM SYS SUMM 1とSPEC 66 ENVIRONMENTにも表示される（SCOM 4.1節）。 */ }
            action <'F-ARS-THC-MON-05'> F_ARS_THC_MON_05 { doc /* 熱交換器出口温度（V61T2635A、CAB HX AIROUT T）はAV BAY/CABIN AIR灯の入力の一つで、上限は145°Fである（訓練マニュアル3.5.3節）。 */ }
            action <'F-ARS-THC-MON-06'> F_ARS_THC_MON_06 { doc /* 主C&Wのハードウェアチャネル114がキャビン熱交換器の空気温度に割り当てられ、限界外でAV BAY/CABIN AIR灯を点灯させる（SCOM 2.2節）。 */ }
            action <'F-ARS-THC-MON-07'> F_ARS_THC_MON_07 { doc /* SPEC 66 ENVIRONMENTは、HX OUT T（+45〜+145°F）、CABIN T（+32〜+122°F）と、湿度分離器A・Bの運転状態（HUMID SEP、止まると下向き矢印）を表示する（訓練マニュアル3.5.1節）。 */ }
            action <'F-ARS-THC-MON-08'> F_ARS_THC_MON_08 { doc /* キャビン湿度のトランスデューサはCABIN AIR信号調整器から給電されるが、その値はMCCだけが見る（訓練マニュアル3.5節）。 */ }
            action <'F-ARS-THC-MON-09'> F_ARS_THC_MON_09 { doc /* 分離器の回転数が下がると「S66 HUMID SEP A(B)」の警報が出て、SPEC 66の表示から分離器の故障、回転数センサのディスクリートの故障、信号調整器の故障を切り分ける（MAL 6.2j）。 */ }
            action <'F-ARS-THC-MON-10'> F_ARS_THC_MON_10 { doc /* 熱交換器出口温度とキャビン温度がともに低く表示される場合は、キャビン温度コントローラ1の信号調整器の故障と判定する（MAL 6.4p）。 */ }
            action <'F-ARS-THC-MON-11'> F_ARS_THC_MON_11 { doc /* 運用飛行規則A17-152は、通常はキャビン温度トランスデューサでキャビン温度を測るが、トランスデューサは周囲の熱負荷の影響を受け、STS-103ではマルチメータより約7〜11°F高かったため、必要なら他の計測手段を使うとする。 */ }
            action <'F-ARS-THC-MON-12'> F_ARS_THC_MON_12 { doc /* STS-54ではARSは問題なく作動し、キャビン空気温度と相対湿度の最高値は80°Fと56%だった。 */ }
        }
        package <'SSD-FD-ARS-THC-OPS-001'> FN_ARS_THC_OPS {
            action <'F-ARS-THC-OPS-01'> F_ARS_THC_OPS_01 { doc /* キャビン大気制御の喪失判定（A17-102）で、湿度制御の状態は湿度の値ではなく廃水タンクの増加率（通常6±1 lb/day/人）で判断する。STS-5で分離器Bの入口が詰まったときも湿度は変わらず、増加率の低下で検知された。 */ }
            action <'F-ARS-THC-OPS-02'> F_ARS_THC_OPS_02 { doc /* A17-102Aの根拠では、95°Fを超えるとフライトデッキのアビオニクスが過熱し、水ループのポンプ出口温度はキャビン温度より8〜10°F低いため、キャビン温度39°Fではポンプ出口の水が凍結点を下回る。 */ }
            action <'F-ARS-THC-OPS-03'> F_ARS_THC_OPS_03 { doc /* 再突入・着陸の乗員室温度の上限は75°Fで、就寝中が寒すぎる場合はCDRと医師の合意で上げられる。個人冷却装置（ICU）が周囲温度75°Fで340 BTU/hrを除くよう設計されていることが根拠である（A13-31C）。 */ }
            action <'F-ARS-THC-OPS-04'> F_ARS_THC_OPS_04 { doc /* 上昇と再突入では、キャビンの熱負荷が大きいため、バイパス弁を自動でFULL COOLへ駆動する（A17-151A）。 */ }
            action <'F-ARS-THC-OPS-05'> F_ARS_THC_OPS_05 { doc /* 上昇前は、コントローラ1に給電してロータリスイッチをCOOLにし弁をFULL COOLにしてからコントローラ1を断電し、軌道上でコントローラ1を再び入れる（訓練マニュアル3.6節）。 */ }
            action <'F-ARS-THC-OPS-06'> F_ARS_THC_OPS_06 { doc /* 上昇中は、主エンジンを失いうる交流母線間の短絡を防ぐため、HUM SEPとIMU FANの信号調整器を断電しておく（STS-6でこれらの信号調整器への電線束が短絡した）（訓練マニュアル3.6節）。 */ }
            action <'F-ARS-THC-OPS-07'> F_ARS_THC_OPS_07 { doc /* 軌道上では、乗員は快適さのためにコントローラを任意の位置にしてよいが、ISS係留中にISSの露点を保つためにキャビン温度を下げる必要がある場合はそれを優先する（A17-152B）。 */ }
            action <'F-ARS-THC-OPS-08'> F_ARS_THC_OPS_08 { doc /* キャビンが寒すぎる場合は、熱交換器バイパス弁の手動ピン止め、照明の点灯、空冷機器の電源投入、両水ループの最大インターチェンジャ流量、FESの停止、ラジエータ出口温度HIの順に行う（A17-152B2）。 */ }
            action <'F-ARS-THC-OPS-09'> F_ARS_THC_OPS_09 { doc /* 上限温度の超過が予測される日は、就寝後にバイパス弁を自動でFULL COOLへ駆動してキャビンを冷やしておく（cabin coldsoak）（A17-152B3）。 */ }
            action <'F-ARS-THC-OPS-10'> F_ARS_THC_OPS_10 { doc /* 再突入前日（EOM-1）の就寝前に、再突入日の起床時に70°Fとなる位置へコントローラを自動で駆動し、再突入日の起床後にバイパス弁をFULL COOLにする（A17-152C）。 */ }
            action <'F-ARS-THC-OPS-11'> F_ARS_THC_OPS_11 { doc /* EVA後の除染（A15-203）では、ヒドラジン類が水に溶けるため、IV乗員が温度コントローラを全COOLにして凝縮熱交換器の空気流を最大にし、汚染物質を凝縮させて廃水系へ送る。 */ }
            action <'F-ARS-THC-OPS-12'> F_ARS_THC_OPS_12 { doc /* 軌道上の最初の数日は、運転中の湿度分離器に水が溜まっていないかを約12時間ごとに点検する（SCOM 5.3節）。 */ }
        }
        package <'SSD-FD-ARS-THC-SEP-001'> FN_ARS_THC_SEP {
            action <'F-ARS-THC-SEP-01'> F_ARS_THC_SEP_01 { doc /* 2台の湿度分離器はキャビン熱交換器に隣接して床下のECLSSベイにあり、常時1台を使う（訓練マニュアル3.2.5節）。 */ }
            action <'F-ARS-THC-SEP-02'> F_ARS_THC_SEP_02 { doc /* 分離器のファンが吸引を作って熱交換器から水を含んだ空気を引き出し、回転ドラムの遠心力で空気と凝縮水を分け、凝縮水を廃水タンクへ送り、除湿した空気を37 lb/hrでECLSSベイへ戻す。分離器は三相115 V ACの電動機で駆動される（訓練マニュアル3.2.5節）。 */ }
            action <'F-ARS-THC-SEP-03'> F_ARS_THC_SEP_03 { doc /* 分離器は公称約1 lb/hr、最大約4 lb/hrの水を除き、水は廃水タンクへ、空気は排気ダクトで乗員室へ戻す（SCOM 2.9節）。 */ }
            action <'F-ARS-THC-SEP-04'> F_ARS_THC_SEP_04 { doc /* 1979年の飛行運用マニュアルは、分離器の露点範囲を39〜61°F、モータの回転数を5,430〜5,700 rpm、除水量を0〜4 lb/hrとする。 */ }
            action <'F-ARS-THC-SEP-05'> F_ARS_THC_SEP_05 { doc /* 凝縮水QDの追加に伴い、分離器の共通出口は排出ラインを経て廃水タンクにつながり、廃水タンク1の出口弁が開なら凝縮水は廃水タンクへ、閉なら接続したCWCへ流れる（SCOM 2.9節）。 */ }
            action <'F-ARS-THC-SEP-06'> F_ARS_THC_SEP_06 { doc /* 凝縮水の回収では、Y-Yホースで凝縮水QDにCWCをつなぎ、パネルML31CのWASTE H2O TK1 DRAIN VLVを閉じ、24時間ごとにCWCの溜まり具合を確かめる（Orbit Opsチェックリスト5-43）。 */ }
            action <'F-ARS-THC-SEP-07'> F_ARS_THC_SEP_07 { doc /* IFMの凝縮水回収の再構成（W-8）は、両分離器を止めて凝縮水回収ラインを分離器Bの試験ポート49から分離器Aの試験ポート48へ付け替える手順を示す。 */ }
            action <'F-ARS-THC-SEP-08'> F_ARS_THC_SEP_08 { doc /* 故障処置手順6.2jは、各分離器下流の逆止弁が開固着すると廃水タンクの水で分離器が浸水しうると注意する。 */ }
            action <'F-ARS-THC-SEP-09'> F_ARS_THC_SEP_09 { doc /* IOAのCIL評価（1988年）は、分離器出口の逆止弁（ARS-340、4個）について、水の逆流は有効な影響で飛行の打切りにつながるとした。 */ }
            action <'F-ARS-THC-SEP-10'> F_ARS_THC_SEP_10 { doc /* 分離器から水が漏れた場合は1台を常に運転したままにし（両方を同時に止めると分離器がさらに浸水し、再起動時に損傷しうる）、下部機器ベイの遊離水を清掃する（MAL ECLS SSR-16）。 */ }
            action <'F-ARS-THC-SEP-11'> F_ARS_THC_SEP_11 { doc /* 詰まった分離器の空気出口から漏れる水は、空気穴を開けたごみ袋にタオルを詰めて出口に取り付けて吸い取る（IFM W-40）。 */ }
            action <'F-ARS-THC-SEP-12'> F_ARS_THC_SEP_12 { doc /* SODBは、キャビンファンの起動・停止の前と少なくとも5分後まで水分離器を運転するとし、止まった分離器に水が溜まるとモータと軸受を損傷しうるとする。 */ }
        }
        package <'SSD-FD-ARS-THC-TCV-001'> FN_ARS_THC_TCV {
            action <'F-ARS-THC-TCV-01'> F_ARS_THC_TCV_01 { doc /* キャビン温度制御弁はキャビン熱交換器を迂回する空気の流量を変える可変位置弁で、迂回した暖かい空気と熱交換器を通った冷たい空気の比率でキャビン温度が決まる（訓練マニュアル3.2.3節）。 */ }
            action <'F-ARS-THC-TCV-02'> F_ARS_THC_TCV_02 { doc /* CABIN TEMPロータリスイッチの位置に応じて、有効なコントローラが空気流の0〜70%を熱交換器の外へ迂回させ、全COOLは約65°F、全WARMは約80°Fに当たる（SCOM 2.9節）。 */ }
            action <'F-ARS-THC-TCV-03'> F_ARS_THC_TCV_03 { doc /* コントローラはモータ駆動のアクチュエータで、弁と2台のコントローラはパネルMD44Fの下のECLSSベイにあり、単一のバイパス弁にアクチュエータアームでつながる（SCOM 2.9節）。 */ }
            action <'F-ARS-THC-TCV-04'> F_ARS_THC_TCV_04 { doc /* 自動では弁アームを弁アームリンクに、リンクを主または副のコントローラのアクチュエータにピン止めしてからコントローラに給電し、全COOLから全HOTまでの移動は最大4分である（訓練マニュアル3.2.3節）。 */ }
            action <'F-ARS-THC-TCV-05'> F_ARS_THC_TCV_05 { doc /* 手動では弁アームを4つの固定穴の一つにピン止めし、FULL COOLは熱交換器への流量が最大、2/3 COOLと1/3 COOLは最大冷却能力の約2/3と約1/3、FULL HEATは流量が最小となる（SCOM 2.9節）。 */ }
            action <'F-ARS-THC-TCV-06'> F_ARS_THC_TCV_06 { doc /* 1979年の飛行運用マニュアルは、各コントローラが給気ダクトと還流ダクトの温度を検知して乗員の選んだ65〜80°Fの温度に制御し、バイパス弁は全閉にならない仕切り板のようなもので空気流の0〜70%を迂回させるとする。 */ }
            action <'F-ARS-THC-TCV-07'> F_ARS_THC_TCV_07 { doc /* パネルL1のCABIN TEMPロータリスイッチ（COOL–WARM）で65〜80°Fの間の温度を選び、CABIN TEMP CNTRLスイッチ（1–OFF–2）で2台のコントローラの一方を選ぶ（訓練マニュアル表3-6）。 */ }
            action <'F-ARS-THC-TCV-08'> F_ARS_THC_TCV_08 { doc /* コントローラの切替では、CAB TEMP選択器をWARM（COOL）に回してリンクが副（主）アクチュエータにつながる位置に来るまで平均約5分待ち、CNTLRをOFFにしてMD44Fでリンクを付け替え、CNTLRを2（1）にしてから温度を選び直す（Orbit Opsチェックリスト5-42）。 */ }
            action <'F-ARS-THC-TCV-09'> F_ARS_THC_TCV_09 { doc /* 熱交換器を通った空気とバイパス空気は熱交換器下流の給気ダクトで合流し、CDR・PLTのコンソールと各所のダクト吹出口から乗員室へ吹き出す（SCOM 2.9節）。 */ }
            action <'F-ARS-THC-TCV-10'> F_ARS_THC_TCV_10 { doc /* 1979年の飛行運用マニュアルは、合流した空気をコンソール、ミッドデッキ、MS・PSのステーションの給気口から乗員室へ出すとする。 */ }
            action <'F-ARS-THC-TCV-11'> F_ARS_THC_TCV_11 { doc /* STS-2では、STS-1で環境の影響を受けたセンサが高温を示したため自動のキャビン温度コントローラを使わず、作業中は全COOL、就寝中は全WARMにバイパス弁をピン止めする計画とし、乗員は初日の就寝中も全COOLのままとした。 */ }
        }
        package <'SSD-FD-ARS-WCL-001'> FN_ARS_WCL {
            action <'F-ARS-WCL-01'> F_ARS_WCL_01 { doc /* 水冷却ループは完全に独立した2系統が並んで流れ、同時運転もできるが通常は1系統だけを稼働させ（通常はループ2）、両者の違いはループ1（予備）がポンプ2台、ループ2が1台である点だけで、ポンプは前方ロッカー下のECLSSベイにある三相117 V AC電動機で駆動される。 */ }
            action <'F-ARS-WCL-02'> F_ARS_WCL_02 { doc /* ポンプ下流で流れは3つの並列経路に分かれ、第1はAv Bay 1の空気/水熱交換器とコールドプレート、第2はAv Bay 2の空気/水熱交換器とコールドプレートおよび乗員室窓の熱調整、第3はフライトデッキのMDMコールドプレート、Av Bay 3Aの空気/水熱交換器とコールドプレート、Av Bay 3Bのコールドプレートを通る。 */ }
            action <'F-ARS-WCL-03'> F_ARS_WCL_03 { doc /* 3経路はインターチェンジャ上流で合流した後に再び分かれ、一方はフレオン/水インターチェンジャで冷却されてから液冷服熱交換器・飲料水チラー・キャビン熱交換器・IMU熱交換器を通ってポンプパッケージへ戻り、他方の温水はそれらを迂回してポンプパッケージで合流し、バイパス経路の弁がポンプパッケージ出口の混合水温を制御する。 */ }
            action <'F-ARS-WCL-04'> F_ARS_WCL_04 { doc /* バイパス弁はパネルL1のH2O LOOP 1・2 BYPASS MODEスイッチで制御し、AUTOではバイパスコントローラがポンプ出口温度63.0±2.5°Fを保つよう弁を動かし、MANではH2O LOOP MAN INCR/DECRスイッチで乗員が弁位置を調整する。 */ }
            action <'F-ARS-WCL-05'> F_ARS_WCL_05 { doc /* バイパス弁は打上げ前にインターチェンジャ流量が約950 lb/hrとなるよう手動で調整して投入後までMANのままとし、軌道上は稼働ループをAUTOにしてポンプ出口を約63°Fに保ち、両ループの長時間運転はインターチェンジャの能力を超えてキャビン温度が上がるため避ける。 */ }
            action <'F-ARS-WCL-06'> F_ARS_WCL_06 { doc /* 各ループのアキュムレータはGN2で19〜35 psiに加圧され、ポンプ入口に正圧を与え、熱膨張を吸収し、ポンプの起動・停止時の圧力変動を抑える。 */ }
            action <'F-ARS-WCL-07'> F_ARS_WCL_07 { doc /* ポンプ出口圧はパネルO1のH2O PUMP OUT PRESS計器（LOOP 1/LOOP 2切替）に表示され、ループ1で19.5 psia未満または79.5 psia超、ループ2で45 psia未満または81 psia超のときパネルF7の黄色H2O LOOP警報灯が点灯し、ポンプ出口圧と差圧はSM GPCへ送られてDISP 88に表示される。 */ }
            action <'F-ARS-WCL-08'> F_ARS_WCL_08 { doc /* ループ1のポンプはパネルL1のH2O PUMP LOOP 1 A/BスイッチとGPC/OFF/ONスイッチ、ループ2のポンプはH2O PUMP LOOP 2スイッチで制御し、OPS 2でGPC位置にするとGPCが非稼働ループのポンプを4時間ごとに6分運転して熱調整し、OPS 1・3・6ではループ2のGPC-ON指令がBFSに常駐するためGPC位置で直ちに起動する。 */ }
            action <'F-ARS-WCL-09'> F_ARS_WCL_09 { doc /* アキュムレータ量が0（5）%、MIN BYP位置でインターチェンジャ流量600（649）lb/hr以上を保てない、稼働ループのポンプ出口温度を85（82.75）°F未満に保てない（14.7 psia）、またはループ間漏れ（水-水、フレオン-水）が確認された場合などにARS水ループ喪失とする（A18-101）。 */ }
            action <'F-ARS-WCL-10'> F_ARS_WCL_10 { doc /* 上昇・再突入では両ループともバイパス弁をMAN、インターチェンジャ流量を950±50 lb/hrに設定し（ループ1はポンプBでOFF、ループ2はON）、ループ2を稼働ループとするのはポンプ1台のループ2の故障が検知されないまま残ることを避けるためである（A18-151A）。 */ }
            action <'F-ARS-WCL-11'> F_ARS_WCL_11 { doc /* 両フレオンループの蒸発器出口温度が32°F未満になれば両水ループを運転し、両ループの運転と流量比例弁のICH位置で、インターチェンジャへのフレオン入口温度が6°Fに下がるまで水の凍結を防ぐ（A18-151C）。 */ }
            action <'F-ARS-WCL-12'> F_ARS_WCL_12 { doc /* フレオン-水の漏れでは影響ループを必要時以外運転せず、乗員室への水の漏れでは、次のフレオン-水漏れで有毒なフレオン21が乗員室に入るのを避けるため影響ループを止める（A18-151E・F）。 */ }
            action <'F-ARS-WCL-13'> F_ARS_WCL_13 { doc /* 1ループの喪失はゼロフォールトトレラントとなり、両ループを失うと乗員室内のアビオニクスの冷却と湿度制御を失うため、上昇中はAOAとし、故障から4時間以内の着陸を要する（A18-1001B）。 */ }
            action <'F-ARS-WCL-14'> F_ARS_WCL_14 { doc /* インターチェンジャ流量・出口温度、キャビン熱交換器入口温度、ポンプ出口温度・差圧、アキュムレータ量は、SM OPS 2・4のSPEC 88 APU/ENVIRON THERMに表示される（訓練マニュアル3.5.1節）。 */ }
        }
        package <'SSD-FD-ARS-WCL-AVL-001'> FN_ARS_WCL_AVL {
            action <'F-ARS-WCL-AVL-01'> F_ARS_WCL_AVL_01 { doc /* ポンプ下流で流れは3つの並列経路に分かれ、第1はAv Bay 1の空気/水熱交換器とコールドプレート、第2はAv Bay 2の空気/水熱交換器とコールドプレートと乗員室窓の熱調整、第3はフライトデッキのMDMコールドプレート、Av Bay 3Aの空気/水熱交換器とコールドプレート、Av Bay 3Bのコールドプレートを通り、インターチェンジャの上流で合流する（SCOM 2.9節）。 */ }
            action <'F-ARS-WCL-AVL-02'> F_ARS_WCL_AVL_02 { doc /* 各ベイと乗員室の一部の電子機器はコールドプレートに取り付けられ、各ベイの棚のコールドプレートは水冷却ループの流れに対して直並列に接続される（SCOM 2.9節）。 */ }
            action <'F-ARS-WCL-AVL-03'> F_ARS_WCL_AVL_03 { doc /* Av Bay 1経路はベイの熱交換器で空気の熱を拾った後25 ft²のコールドプレートを冷やし、Av Bay 2経路は熱交換器と30 ft²のコールドプレートを冷やすとともに、オービタのすべての窓の周りのシールを熱調整する（訓練マニュアル3.3.2〜3.3.3節）。 */ }
            action <'F-ARS-WCL-AVL-04'> F_ARS_WCL_AVL_04 { doc /* Av Bay 3経路は一部の水でMDMコールドプレートを冷やし大半はこれを迂回した後、Av Bay 3A（熱交換器と32 ft²のコールドプレート）と、水冷の機器だけを収めた別区画のAv Bay 3B（5 ft²のコールドプレート）に分かれる（訓練マニュアル3.3.4節）。 */ }
            action <'F-ARS-WCL-AVL-05'> F_ARS_WCL_AVL_05 { doc /* 訓練マニュアルの表3-2〜3-5は、Av Bay 1・2・3A・3Bの機器を強制空冷・自然対流・水冷に分けて示す。 */ }
            action <'F-ARS-WCL-AVL-06'> F_ARS_WCL_AVL_06 { doc /* マスタタイミングユニット（MTU）はミッドデッキのAv Bay 3Bにあり、水冷却ループのコールドプレートで冷却される（SCOM 2.6節）。 */ }
            action <'F-ARS-WCL-AVL-07'> F_ARS_WCL_AVL_07 { doc /* 前方ベイ1〜3の電力制御組立・負荷制御組立・モータ制御組立・インバータはコールドプレートに搭載されて水冷却ループで冷却され、インバータ分配組立は空冷である（SCOM 2.8節）。 */ }
            action <'F-ARS-WCL-AVL-08'> F_ARS_WCL_AVL_08 { doc /* ドッキング用投光器とフォワードバルクヘッド投光器は水冷却ループで冷やすコールドプレートを使い、OV-104にだけ残り、OV-103・OV-105からは水ループのコールドプレートの問題で撤去された（SCOM 2.15節）。 */ }
            action <'F-ARS-WCL-AVL-09'> F_ARS_WCL_AVL_09 { doc /* MIN BYP位置でインターチェンジャ流量を600 lb/hr以上に保てないと、通常の再突入（GPC 5台）でAv Bay 2のコールドプレートを上限130°F未満に保てず、ベイの熱交換器を出る空気はポンプ出口の水より約10°F高いため、ポンプ出口温度を85°F未満に保てないと機器が過熱しうる（A18-101B・C）。 */ }
            action <'F-ARS-WCL-AVL-10'> F_ARS_WCL_AVL_10 { doc /* あるAv Bayの温度が上がる原因には、そのベイを通る水ループ経路の流れの制限もありうる（訓練マニュアル付録B.6）。 */ }
            action <'F-ARS-WCL-AVL-11'> F_ARS_WCL_AVL_11 { doc /* IOAのCIL評価（1988年）は、窓の熱調整系（ARS-194）の故障はシールの喪失につながるとし、オービタの全シールを扱うNASAのFMEAで評価済みであることを確認した。 */ }
        }
        package <'SSD-FD-ARS-WCL-CLD-001'> FN_ARS_WCL_CLD {
            action <'F-ARS-WCL-CLD-01'> F_ARS_WCL_CLD_01 { doc /* インターチェンジャで冷えた水は液冷服熱交換器、ギャレーの水チラー、キャビン熱交換器、IMU熱交換器の順に流れ、バイパス流と合流してポンプパッケージへ戻る（訓練マニュアル3.3節）。 */ }
            action <'F-ARS-WCL-CLD-02'> F_ARS_WCL_CLD_02 { doc /* 液冷服（LCVG）熱交換器はエアロック内にあり、EVAの前後に液冷服を冷やす水ループを水冷却ループで冷却する（訓練マニュアル3.3.7節）。 */ }
            action <'F-ARS-WCL-CLD-03'> F_ARS_WCL_CLD_03 { doc /* エアロックにはEMUごとに閉じた2系統のLCVG冷却ループが出入りし、SCUにつないだ液冷服を冷やす水は、LCVG熱交換器でオービタの水ループにより冷やされる（訓練マニュアル6.3節）。 */ }
            action <'F-ARS-WCL-CLD-04'> F_ARS_WCL_CLD_04 { doc /* 飲料水チラーは、給水タンクからの乗員の飲料水を冷やす（訓練マニュアル3.3.8節）。 */ }
            action <'F-ARS-WCL-CLD-05'> F_ARS_WCL_CLD_05 { doc /* ギャレー給水弁を開くと、給水は水冷却ループの飲料水チラーで冷やす経路と、チラーを迂回する経路に分かれる（SCOM 2.9節）。 */ }
            action <'F-ARS-WCL-CLD-06'> F_ARS_WCL_CLD_06 { doc /* キャビン熱交換器はキャビン空気が拾った熱をARSの水冷却ループへ移し、空気中の湿分は熱交換器のスラーパーバーに凝縮する（訓練マニュアル3.2.4節）。 */ }
            action <'F-ARS-WCL-CLD-07'> F_ARS_WCL_CLD_07 { doc /* IMUファンの出口空気は、フライトデッキのIMU熱交換器で水冷却ループにより冷やされてから乗員室へ戻る（SCOM 2.9節）。 */ }
            action <'F-ARS-WCL-CLD-08'> F_ARS_WCL_CLD_08 { doc /* SODBは水チラーの最低作動温度を35°Fとし、系内の水が凍ると機器が損傷して運用できなくなるとする。 */ }
            action <'F-ARS-WCL-CLD-09'> F_ARS_WCL_CLD_09 { doc /* EMUのファン・ポンプで液冷服配管の水をオービタのLCG熱交換器へ循環させれば、配管の圧力と温度を下げる非常手段になる（A15-202）。 */ }
            action <'F-ARS-WCL-CLD-10'> F_ARS_WCL_CLD_10 { doc /* IOAのCIL評価（1988年）は、LCVG熱交換器（ARS-199）についてNASAのより保守的な冗長性の定義と高い臨界度に同意し、指摘を取り下げた。 */ }
            action <'F-ARS-WCL-CLD-11'> F_ARS_WCL_CLD_11 { doc /* STS-114では、ドッキング中にFESを止めていたためフレオンループの温度が軌道周期で変動し、液冷服の冷却ループの温度に表れた。通常この変動は、WCL 1の6分間の周期運転がLCGの流れと重なったときだけ見られる。 */ }
        }
        package <'SSD-FD-ARS-WCL-ICH-001'> FN_ARS_WCL_ICH {
            action <'F-ARS-WCL-ICH-01'> F_ARS_WCL_ICH_01 { doc /* 3経路の合流水は再び2つに分かれ、一方はフレオン/水インターチェンジャで冷やされ、他方の温水はインターチェンジャと冷側の熱交換器を迂回してポンプパッケージで合流し、バイパス経路の弁が混合後のポンプ出口水温を制御する（SCOM 2.9節）。 */ }
            action <'F-ARS-WCL-ICH-02'> F_ARS_WCL_ICH_02 { doc /* 水冷却ループが集めた熱はインターチェンジャでATCSのフレオン冷却ループへ移され、インターチェンジャは有毒なフレオン21を乗員室の外に置くため乗員室外にあり、バイパス弁はインターチェンジャを通る流量を決める可変位置の分流弁である（訓練マニュアル3.3.5節）。 */ }
            action <'F-ARS-WCL-ICH-03'> F_ARS_WCL_ICH_03 { doc /* インターチェンジャは対向流のプレートフィン熱交換器で、2系統の水ループと2系統のフレオンループがともに通り、フレオンループにとっては熱源となる（訓練マニュアル4.10節）。 */ }
            action <'F-ARS-WCL-ICH-04'> F_ARS_WCL_ICH_04 { doc /* 手動モードでは乗員がH2O LOOP BYPASSスイッチのINCRでバイパス流量を増やし（インターチェンジャ流量は減る）、DECRで減らし、自動モードではバイパス制御器がポンプ出口温度を63°Fに保つよう弁を動かす（訓練マニュアル3.3.5節）。 */ }
            action <'F-ARS-WCL-ICH-05'> F_ARS_WCL_ICH_05 { doc /* 自動モードでは、ポンプ出口温度が設定値63.0±2.5°Fを超えるとバイパス弁を閉じる向きに動かしてインターチェンジャへの流れを増やし、下回るとバイパス量を増やして排熱を減らす（SCOM 2.9節）。 */ }
            action <'F-ARS-WCL-ICH-06'> F_ARS_WCL_ICH_06 { doc /* バイパス弁は打上げ前にインターチェンジャ流量が約950 lb/hrとなるよう手動で調整され、制御は軌道投入後まで手動モードのままとする（SCOM 2.9節）。 */ }
            action <'F-ARS-WCL-ICH-07'> F_ARS_WCL_ICH_07 { doc /* 2ループを長時間同時に運転するとインターチェンジャの伝熱能力を超えて水ループに熱がたまり、インターチェンジャ経路の液冷服・チラー・キャビン・IMUの熱交換器の冷却能力が落ち、インターチェンジャ出口が63°Fに近づくとAv Bay経路の冷却も失われる（訓練マニュアル3.3.6節）。 */ }
            action <'F-ARS-WCL-ICH-08'> F_ARS_WCL_ICH_08 { doc /* 上昇・再突入では、高熱負荷時のインターチェンジャでのフレオンと水の熱負荷の不整合でAUTOの制御が適切に働かないため、両ループともバイパス弁をMANとし、キャビンとアビオニクスの温度に最適な950±50 lb/hrに設定する（A18-151A）。 */ }
            action <'F-ARS-WCL-ICH-09'> F_ARS_WCL_ICH_09 { doc /* 軌道上は、飛行データで不整合が予測ほど大きくないと分かったため稼働ループのバイパス弁をAUTOとし、STS-44ではループ2がAUTOで正常に動作した（A18-151B）。 */ }
            action <'F-ARS-WCL-ICH-10'> F_ARS_WCL_ICH_10 { doc /* ラジエータ制御器の低温保護は、ラジエータ出口温度が33±0.5°F未満になるとラジエータをバイパスし、停滞した水ループの水がインターチェンジャで凍るのを防ぐ（訓練マニュアル4.13節）。 */ }
            action <'F-ARS-WCL-ICH-11'> F_ARS_WCL_ICH_11 { doc /* 両フレオンループの蒸発器出口温度が32°F未満になれば両水ループを運転し、両ループの運転と流量比例弁のICH位置で、インターチェンジャへのフレオン入口温度が6°Fに下がるまで水の凍結を防げる（A18-151C）。 */ }
            action <'F-ARS-WCL-ICH-12'> F_ARS_WCL_ICH_12 { doc /* インターチェンジャ流量が550 lb/hr未満になるとSM警報が出て、MANでバイパスを減らして流量が回復するかを確かめる（MAL 6.4o）。 */ }
        }
        package <'SSD-FD-ARS-WCL-MON-001'> FN_ARS_WCL_MON {
            action <'F-ARS-WCL-MON-01'> F_ARS_WCL_MON_01 { doc /* H2O CNTLRはバイパス弁の駆動電力に加えてポンプパッケージのすべての計装（アキュムレータ量、ポンプ出口圧・出口温度・差圧）に給電し、H2O BYP LOOP 1 SNSRの信号調整器はループ1のインターチェンジャ流量センサとIMUファン差圧センサに、LOOP 2 SNSRはループ2のインターチェンジャ流量センサに給電する（訓練マニュアル3.5節）。 */ }
            action <'F-ARS-WCL-MON-02'> F_ARS_WCL_MON_02 { doc /* 水ループの計装は、ポンプ出口圧・ポンプ出口温度・ポンプ差圧・アキュムレータ量と、インターチェンジャ流量・インターチェンジャ出口温度・キャビン熱交換器入口温度である（訓練マニュアル図3-15）。 */ }
            action <'F-ARS-WCL-MON-03'> F_ARS_WCL_MON_03 { doc /* SPEC 88 APU/ENVIRON THERM（SM OPS 2・4）は、各ループのポンプ出口圧（0〜150 psia）・出口温度・差圧（0〜60 psid）、インターチェンジャ流量（0〜1,400 lbm/hr）と出口温度、キャビン熱交換器入口温度、アキュムレータ量を表示する（訓練マニュアル3.5.1節）。 */ }
            action <'F-ARS-WCL-MON-04'> F_ARS_WCL_MON_04 { doc /* SM SYS SUMM 2（DISP 79、BFSとPASS SM OPS 2・4）は、THERM CNTLの欄にH2O PUMP P（0〜150 psia）を表示する（訓練マニュアル3.5.1節）。 */ }
            action <'F-ARS-WCL-MON-05'> F_ARS_WCL_MON_05 { doc /* パネルO1のH2O PUMP OUT PRESS計器はLOOP 1・LOOP 2の切替でポンプ出口圧を示し、SM DISP 88と同じトランスデューサを使う（SCOM 2.9節）。 */ }
            action <'F-ARS-WCL-MON-06'> F_ARS_WCL_MON_06 { doc /* パネルF7の黄色のH2O LOOP灯は、ループ1のポンプ出口圧（V61P2600A）が19.5 psia未満か79.5 psia超、ループ2（V61P2700A）が45 psia未満か81 psia超で点灯し、常用のループ2は劣化を知らせるため限界を高く、通常止めておくループ1は非運転時の圧力を挟むように設定する（訓練マニュアル3.5.3節）。 */ }
            action <'F-ARS-WCL-MON-07'> F_ARS_WCL_MON_07 { doc /* H2O LOOP灯のハードウェアチャネルは、ループ1が105、ループ2が115である（SCOM 2.2節）。 */ }
            action <'F-ARS-WCL-MON-08'> F_ARS_WCL_MON_08 { doc /* ループ2のポンプ出口圧のSM警報の限界は、スイッチがONまたはGPCでポンプON指令があるときは50〜75 psia、OFFまたはON指令がないときは下限20 psiaで、スイッチ位置によるプレコンディショニングで選ばれる（C&W訓練マニュアル図5-2）。 */ }
            action <'F-ARS-WCL-MON-09'> F_ARS_WCL_MON_09 { doc /* SM警報は、ポンプ出口圧50 psia未満・75 psia超（非運転ループは20 psia未満）、ポンプ差圧33 psid未満・46 psid超（非運転ループは5 psid超）で出る（MAL 6.4l）。 */ }
            action <'F-ARS-WCL-MON-10'> F_ARS_WCL_MON_10 { doc /* アキュムレータ量は20%未満・80%超でSM警報を出し、水量が正常ならアキュムレータ量10%の変化でポンプ出口圧が約1 psia変わる（MAL 6.4n）。 */ }
            action <'F-ARS-WCL-MON-11'> F_ARS_WCL_MON_11 { doc /* インターチェンジャ出口温度35°F未満、キャビン熱交換器入口温度34°F未満、ポンプ出口温度45°F未満・90°F超でSM警報を出す（MAL 6.4p）。 */ }
            action <'F-ARS-WCL-MON-12'> F_ARS_WCL_MON_12 { doc /* バイパス制御器を失うと、そのループの計装は流量と一部の温度を除いて失われ、ポンプ出口圧とアキュムレータ量を失うとフレオン/水のループ間漏れを検知できないため、そのループは必要な場合以外使わない（MAL ECLS SSR-4）。 */ }
        }
        package <'SSD-FD-ARS-WCL-OPS-001'> FN_ARS_WCL_OPS {
            action <'F-ARS-WCL-OPS-01'> F_ARS_WCL_OPS_01 { doc /* 上昇中はループ2を運転しループ1を止め、両ループのバイパス弁でインターチェンジャ流量を約950 lb/hrにし、軌道上はループ1をGPC位置に、ループ2のバイパス制御器をAUTOにする（SCOM 2.9節）。 */ }
            action <'F-ARS-WCL-OPS-02'> F_ARS_WCL_OPS_02 { doc /* ループ2を稼働ループとするのは、ポンプ1台のループ2を予備にするとそのポンプの故障がループ1の故障まで検知されないおそれがあるためで、ループ1はすぐ使えるよう950 lb/hrに設定しておく（A18-151A）。 */ }
            action <'F-ARS-WCL-OPS-03'> F_ARS_WCL_OPS_03 { doc /* SM OPS 2でGPC位置にすると、待機ループのポンプはOPSの移行時に6分のON指令を受けた後240分止まり、以後4時間ごとに6分運転して、ループ内の大きな温度差を防ぐ（訓練マニュアル3.6.2節）。 */ }
            action <'F-ARS-WCL-OPS-04'> F_ARS_WCL_OPS_04 { doc /* GPC位置ではSM GPCがPL MDM 1を通してループ1のポンプを、PL MDM 2を通してループ2のポンプを指令し、周期はSPEC 60かTMBUで連続運転に変えられ、PASS SMとBFSがともに使えないときはアップリンクかDPS UTILITY SPEC 1からのリアルタイムコマンドで動かせる（訓練マニュアル3.6.3節）。 */ }
            action <'F-ARS-WCL-OPS-05'> F_ARS_WCL_OPS_05 { doc /* リレーの故障によるAC3とAC1の短絡で上昇中に主エンジンを失わないよう、ループ1ポンプAの遮断器（ループ2のGPC位置の電源を兼ねる）は飛行の全段階で開いておく（訓練マニュアル3.6.1節）。 */ }
            action <'F-ARS-WCL-OPS-06'> F_ARS_WCL_OPS_06 { doc /* H2O LOOP PRESS LOW（ポンプの故障かループの漏れ）ではループの切替をMECO後まで待ち、新しいポンプの起動時のAC過渡で同じ母線の主エンジン制御器2台を失わないようにし、切替後はポンプ出口圧が約60〜65 psiaでキャビン熱交換器出口とAv Bayの空気温度が安定か低下することを確かめる（訓練マニュアル付録B.4）。 */ }
            action <'F-ARS-WCL-OPS-07'> F_ARS_WCL_OPS_07 { doc /* 上昇中のMECO前の再構成を認めるAC負荷のうち、水ループのポンプはアビオニクスの空気温度のFDAが出た場合に限る（A9-154A）。 */ }
            action <'F-ARS-WCL-OPS-08'> F_ARS_WCL_OPS_08 { doc /* ARS水ループは、アキュムレータ量0%、MIN BYPでインターチェンジャ流量600 lb/hr以上を保てない、14.7 psiaで稼働ループのポンプ出口温度を85°F未満に保てない、ループ間漏れ（水-水・フレオン-水）の確認のいずれかで喪失とする（A18-101A〜D）。 */ }
            action <'F-ARS-WCL-OPS-09'> F_ARS_WCL_OPS_09 { doc /* フレオン-水の漏れでは、135 psig以上になりうる圧力とフレオン21に適合しない部品のため影響ループを必要時以外運転せず、乗員室への水の漏れでは、次のインターチェンジャでのフレオン-水漏れで有毒なフレオン21が乗員室に入るのを避けるため影響ループを止める（A18-151E・F）。 */ }
            action <'F-ARS-WCL-OPS-10'> F_ARS_WCL_OPS_10 { doc /* 1ループの喪失はゼロフォールトトレラントとなり上昇中なら初日のPLSとし、両ループの喪失では上昇中はAOAとし、故障から2時間以内に乗員室が約90°F・相対湿度100%に近づくため4時間以内の着陸を要する（A18-1001B）。 */ }
            action <'F-ARS-WCL-OPS-11'> F_ARS_WCL_OPS_11 { doc /* 冷却機器を止めておける最大時間は、水ループではS帯電力増幅器の冷却の制約から10分である（A18-501D）。 */ }
            action <'F-ARS-WCL-OPS-12'> F_ARS_WCL_OPS_12 { doc /* Av Bayの温度が130°Fを超えて両ファンの運転でも下がらなければ水ループを切り替えて5分待ち、下がれば水ループの劣化としてECLS SSR-4で予備ループへ移る（MAL 6.1b）。 */ }
        }
        package <'SSD-FD-ARS-WCL-PMP-001'> FN_ARS_WCL_PMP {
            action <'F-ARS-WCL-PMP-01'> F_ARS_WCL_PMP_01 { doc /* 水冷却ループ1（予備）はポンプ2台、ループ2（常用）は1台を持ち、ポンプは前方ロッカー下のECLSSベイにある三相115 V AC電動機駆動の遠心ポンプである（訓練マニュアル3.3.1節）。 */ }
            action <'F-ARS-WCL-PMP-02'> F_ARS_WCL_PMP_02 { doc /* ループ1では各ポンプ下流の玉形の逆止弁が、非運転ポンプを通る逆流を防ぐ（SCOM 2.9節）。 */ }
            action <'F-ARS-WCL-PMP-03'> F_ARS_WCL_PMP_03 { doc /* アキュムレータはループの熱による容積変化を補い、ポンプの押込み圧を保ってキャビテーションを防ぎ、ベローズが伸び切ると水量は1.81 lb、底付きでも0.19 lbが残る（訓練マニュアル3.3.1節）。 */ }
            action <'F-ARS-WCL-PMP-04'> F_ARS_WCL_PMP_04 { doc /* 各ループのアキュムレータはGN2で19〜35 psiに加圧され、ポンプ入口に正圧を与え、熱膨張を吸収し、ポンプの起動・停止時の圧力変動を抑える（SCOM 2.9節）。 */ }
            action <'F-ARS-WCL-PMP-05'> F_ARS_WCL_PMP_05 { doc /* ポンプの設計圧は90 psig、耐圧は135 psig、流量範囲は970±15 lb/hr、入口圧は18〜35 psig、昇圧は46.5±1.2 psidで、アキュムレータの容積は56 in³、ループの容積（アキュムレータを除く）は1,810 in³、水量は65.3 lbである（訓練マニュアル3.6.5節）。 */ }
            action <'F-ARS-WCL-PMP-06'> F_ARS_WCL_PMP_06 { doc /* ループ1のポンプAはAC1、ポンプBはAC2、ループ2のポンプはAC3の三相電力を、パネルL4の各3個の遮断器からパネルL1のH2O PUMPスイッチを通して受け、AC1の遮断器はループ2のGPC位置の電源も兼ねる（訓練マニュアル表3-6）。 */ }
            action <'F-ARS-WCL-PMP-07'> F_ARS_WCL_PMP_07 { doc /* ループ2のポンプはON位置ではAC3から給電され、上昇・再突入でBFSがペイロードMDMを制御しているときはGPC位置でAC1から給電されるため、ポンプが1台のループ2でもAC3を失ったときに給電を保てる（SCOM 2.9節）。 */ }
            action <'F-ARS-WCL-PMP-08'> F_ARS_WCL_PMP_08 { doc /* SODBは、1相を失った水ポンプを停止し（フレオンとの流量の不整合と消費電力の増加を避けるため。必要なら再起動できる）、ポンプの最低入口圧を18.0 psia（下回るとキャビテーションのおそれ）とする。 */ }
            action <'F-ARS-WCL-PMP-09'> F_ARS_WCL_PMP_09 { doc /* ポンプは水の流れで自らを冷却するため、流路が極端に、または完全に閉塞すると数分で過熱して故障する（MAL 6.4l）。 */ }
            action <'F-ARS-WCL-PMP-10'> F_ARS_WCL_PMP_10 { doc /* 通常のアキュムレータ量はループ1で約45%、ループ2で約55%である（MAL 6.4l）。 */ }
            action <'F-ARS-WCL-PMP-11'> F_ARS_WCL_PMP_11 { doc /* アキュムレータのベローズが破れてGN2と水が混ざると、ループを動かしたときに窒素の泡がポンプを通って運転が不安定になるため、そのループを喪失とみなす（A18-101E）。 */ }
            action <'F-ARS-WCL-PMP-12'> F_ARS_WCL_PMP_12 { doc /* IOAのCIL評価（1988年）は、アキュムレータ（ARS-108）が故障してもポンプの揚程でループを運転できるとのNASA担当者の見解に同意し、指摘を取り下げた。 */ }
        }
        package <'SSD-FD-ECL-ATCS-001'> FN_ECL_ATCS {
            action <'F-ECL-ATCS-01'> F_ECL_ATCS_01 { doc /* ATCSは、ARSの熱を水／フレオン熱交換器で、燃料電池の熱を各燃料電池熱交換器で受け取り、ECLSS酸素供給ラインのPRSD酸素と油圧作動油を加温する。 */ }
            action <'F-ECL-ATCS-02'> F_ECL_ATCS_02 { doc /* 同一構成の2系統のフレオン21冷却ループ、アビオニクス用コールドプレート網、液液熱交換器、放熱器・フラッシュエバポレータ（FES）・アンモニアボイラの3種のヒートシンクから成る。 */ }
            action <'F-ECL-ATCS-03'> F_ECL_ATCS_03 { doc /* 地上ではGSE熱交換器で排熱し、打上げ後約125秒でFESを起動し、軌道上でペイロードベイドアを開くまでFESで排熱する。 */ }
            action <'F-ECL-ATCS-04'> F_ECL_ATCS_04 { doc /* 軌道上は放熱器で排熱し、熱負荷と姿勢の組合せで放熱器の能力を超えるとFESが自動的に補助する。 */ }
            action <'F-ECL-ATCS-05'> F_ECL_ATCS_05 { doc /* 再突入ではV = 12k（高度約175,000 ft）までFESで排熱し、その後は放熱器のコールドソークを滑走の終わりまで主な冷却に使い、コールドソークが尽きた後は地上冷却が接続されるまでアンモニアボイラで排熱する。 */ }
            action <'F-ECL-ATCS-06'> F_ECL_ATCS_06 { doc /* 放熱器は左右のペイロードベイドアの内側に4枚ずつのパネルを持ち、最大の排熱能力は61,100 Btu/hである。 */ }
            action <'F-ECL-ATCS-07'> F_ECL_ATCS_07 { doc /* フレオンは中胴のコールドプレート網と後部アビオニクスベイ4・5・6を通り、電子機器を冷却する。 */ }
        }
        package <'SSD-FD-TCS-FCL-001'> FN_TCS_FCL {
            action <'F-TCS-FCL-01'> F_TCS_FCL_01 { doc /* フレオン21冷却ループは同一構成の2系統で、各系統のポンプパッケージは2台のポンプとアキュムレータから成り、常に1台のポンプが運転される。 */ }
            action <'F-TCS-FCL-02'> F_TCS_FCL_02 { doc /* 金属ベローズ式のアキュムレータは窒素で加圧され、ポンプの吸入圧を確保し、熱膨張を吸収する。 */ }
            action <'F-TCS-FCL-03'> F_TCS_FCL_03 { doc /* フレオンは燃料電池熱交換器と中胴コールドプレート網を並列に流れた後、油圧熱交換器、放熱器、GSE熱交換器、アンモニアボイラ、FESを順に通る。 */ }
            action <'F-TCS-FCL-04'> F_TCS_FCL_04 { doc /* その後、流路はカーゴ熱交換器・ECLSS酸素リストリクタ・ペイロード熱交換器・ARSインターチェンジャ側と、後部アビオニクスベイ4〜6側の2つに分かれる。 */ }
            action <'F-TCS-FCL-05'> F_TCS_FCL_05 { doc /* 左舷の放熱器パネルはループ1に、右舷のパネルはループ2に直列に接続される。 */ }
            action <'F-TCS-FCL-06'> F_TCS_FCL_06 { doc /* 最初の39飛行では、コロンビアでのフレオン流量の低下が主要な問題の一つであった。 */ }
        }
        package <'SSD-FD-TCS-FES-001'> FN_TCS_FES {
            action <'F-TCS-FES-01'> F_TCS_FES_01 { doc /* FESは上昇時の高度140,000 ft超で排熱し、軌道上では必要に応じて放熱器を補い、軌道離脱・再突入では高度約100,000 ftまで排熱する。 */ }
            action <'F-TCS-FES-02'> F_TCS_FES_02 { doc /* 1つの筐体に高負荷蒸発器とトッピング蒸発器があり、高負荷蒸発器は冷却能力が大きいが排気が左側のみで推力を生じる。 */ }
            action <'F-TCS-FES-03'> F_TCS_FES_03 { doc /* フィン付きの芯に水を噴霧して蒸発させ、水1 lbあたり約1,000 Btuの熱を奪う。 */ }
            action <'F-TCS-FES-04'> F_TCS_FES_04 { doc /* 水は給水タンクから給水系統A・Bで供給され、主制御器A・Bは出口温度を39°F、副制御器は62°Fに制御する。 */ }
            action <'F-TCS-FES-05'> F_TCS_FES_05 { doc /* トッピング蒸発器は、軌道上で給水タンクの余剰の水を捨てるためにも使える。 */ }
            action <'F-TCS-FES-06'> F_TCS_FES_06 { doc /* STS-26とSTS-34では、FESの運用上の不具合が発生した。 */ }
        }
        package <'SSD-FD-TCS-GSE-001'> FN_TCS_GSE {
            action <'F-TCS-GSE-01'> F_TCS_GSE_01 { doc /* 地上作業（点検・打上げ前・着陸後）では、フレオン21ループ内のGSE熱交換器が地上冷却によって機体の熱を排出する。 */ }
            action <'F-TCS-GSE-02'> F_TCS_GSE_02 { doc /* 打上げから高度140,000 ft未満（約125秒）までは、ループの熱容量（サーマルラグ）で熱を吸収する。 */ }
            action <'F-TCS-GSE-03'> F_TCS_GSE_03 { doc /* 射点ではパッド地上冷却系がGSE熱交換器を通じて機上ループを十分に冷やし、軌道到達までの熱容量を確保する。 */ }
            action <'F-TCS-GSE-04'> F_TCS_GSE_04 { doc /* 地上冷却系は、整備施設・組立棟・着陸施設でのオービタ通電時にも必要とされた。 */ }
            action <'F-TCS-GSE-05'> F_TCS_GSE_05 { doc /* 着陸後の回収隊の冷却車は、T-0アンビリカルを通じてオービタの冷却系にFreon 114を供給した。 */ }
        }
        package <'SSD-FD-TCS-HX-001'> FN_TCS_HX {
            action <'F-TCS-HX-01'> F_TCS_HX_01 { doc /* ATCSは、水／フレオンインターチェンジャでARSが集めた乗員室の熱を、燃料電池熱交換器で燃料電池の熱を受け取り、酸素リストリクタでPCSの極低温酸素を加温し、油圧作動油も加温する。 */ }
            action <'F-TCS-HX-02'> F_TCS_HX_02 { doc /* 開発では、フレオン冷却ループと他の5つの機体系の間で熱をやり取りする最適化された熱交換器が開発された。 */ }
            action <'F-TCS-HX-03'> F_TCS_HX_03 { doc /* 油圧熱交換器は、軌道上の循環時は作動油を加温し、打上げ前・上昇・大気圏飛行中は油圧系の余剰熱をフレオンへ移す。 */ }
            action <'F-TCS-HX-04'> F_TCS_HX_04 { doc /* フレオンポンプ、ARSインターチェンジャ、燃料電池熱交換器、ペイロード熱交換器、中胴コールドプレートは中胴前部の下部にある。 */ }
            action <'F-TCS-HX-05'> F_TCS_HX_05 { doc /* 後部アビオニクスベイ4・5・6の電子機器とレートジャイロ組立も、フレオンのコールドプレートで冷却される。 */ }
        }
        package <'SSD-FD-TCS-NH3-001'> FN_TCS_NH3 {
            action <'F-TCS-NH3-01'> F_TCS_NH3_01 { doc /* アンモニアボイラは、アンモニアの低い沸点を利用して、再突入中の高度400,000 ft未満または着陸後の地上でフレオン21ループを冷却する。 */ }
            action <'F-TCS-NH3-02'> F_TCS_NH3_02 { doc /* 独立した2系統のアンモニア貯蔵・制御系が、1つの共通ボイラへ供給する。 */ }
            action <'F-TCS-NH3-03'> F_TCS_NH3_03 { doc /* 各タンクは49 lbのアンモニアを持ち、ヘリウムで最大運用圧力550 psiaに加圧される。 */ }
            action <'F-TCS-NH3-04'> F_TCS_NH3_04 { doc /* 主制御器はボイラ出口のフレオン温度を35±3°F、副制御器は34±3°Fに制御し、PRI/GPCの構成で31.25°Fを10秒超下回ると主制御器から副制御器へ自動で切り替わる。 */ }
            action <'F-TCS-NH3-05'> F_TCS_NH3_05 { doc /* アンモニアボイラは着陸後、地上冷却カートがGSE熱交換器に接続されるまで使われ、再突入で放熱器のコールドソークを使う場合は、放熱器出口温度が55°Fに達した着陸後に起動する。 */ }
            action <'F-TCS-NH3-06'> F_TCS_NH3_06 { doc /* 初期の飛行では、アンモニアボイラ系の問題も報告されている。 */ }
        }
        package <'SSD-FD-TCS-RAD-001'> FN_TCS_RAD {
            action <'F-TCS-RAD-01'> F_TCS_RAD_01 { doc /* 放熱器はペイロードベイドアの内面に取り付けられ、ドアを閉じているときは通常バイパスされるが、軌道離脱の準備でコールドソークした放熱器内のフレオンは再突入の後半にヒートシンクとして使われる。 */ }
            action <'F-TCS-RAD-02'> F_TCS_RAD_02 { doc /* 放熱器は左右のペイロードベイドアの内面に各4枚のパネルがあり、前方の2枚は展開式、後方の3枚目と4枚目は固定式で、最大の排熱能力は61,100 Btu/hである。 */ }
            action <'F-TCS-RAD-03'> F_TCS_RAD_03 { doc /* 展開式パネルはドアから35.5°開いて両面から放熱し、表面には放射特性を得るための銀蒸着テフロンテープが貼られる。 */ }
            action <'F-TCS-RAD-04'> F_TCS_RAD_04 { doc /* 各パネルは幅10 ft・長さ15 ftで、展開式2枚と固定式2枚を装備すると有効放熱面積は1,195 ft²となる。 */ }
            action <'F-TCS-RAD-05'> F_TCS_RAD_05 { doc /* 流量制御弁が高温のバイパス流と放熱器からの低温流を混合し、放熱器出口温度を通常38°F（高設定57°F）に制御する。 */ }
        }
        package <'SSD-FD-ECL-CAB-001'> FN_ECL_CAB {
            action <'F-ECL-CAB-01'> F_ECL_CAB_01 { doc /* 乗員室は14.7±0.2 psiaに与圧され、平均で窒素80%・酸素20%の混合気に維持される。 */ }
            action <'F-ECL-CAB-02'> F_ECL_CAB_02 { doc /* 相対湿度、二酸化炭素・一酸化炭素濃度、温度、換気はARSが制御する。 */ }
            action <'F-ECL-CAB-03'> F_ECL_CAB_03 { doc /* EVA前には乗員室圧を10.2 psiaまで下げ、EVA終了後に14.7 psiaへ戻す。 */ }
            action <'F-ECL-CAB-04'> F_ECL_CAB_04 { doc /* 乗員室の容積は2,475 ft³であり、外部エアロックを合わせると約2,703 ft³となる。 */ }
            action <'F-ECL-CAB-05'> F_ECL_CAB_05 { doc /* 乗員室構造の熱容量により、再突入から乗員の退出まで室温は95°Fを超えない。 */ }
        }
        package <'SSD-FD-ECL-FDS-001'> FN_ECL_FDS {
            action <'F-ECL-FDS-01'> F_ECL_FDS_01 { doc /* 煙検知・消火機能は、乗員室のアビオニクスベイ、乗員室、Spacelab与圧モジュールに設けられる。 */ }
            action <'F-ECL-FDS-02'> F_ECL_FDS_02 { doc /* イオン化式の検知素子が煙濃度または濃度の変化率を検知して警報を発し、煙濃度の情報をCRTと計器盤L1に表示する。 */ }
            action <'F-ECL-FDS-03'> F_ECL_FDS_03 { doc /* 煙濃度2,200±200 µg/m³、または毎秒22 µg/m³の上昇が20秒間に8回連続すると、L1の煙検知灯、C/Wマスターアラーム、サイレンが作動する。 */ }
            action <'F-ECL-FDS-04'> F_ECL_FDS_04 { doc /* 3つのアビオニクスベイには、それぞれFreon 1301（Halon 1301）の消火ボトルが1本ある。 */ }
            action <'F-ECL-FDS-05'> F_ECL_FDS_05 { doc /* 固定消火ボトルは、計器盤L1で該当ベイのスイッチをアームし、放出ボタンを2秒以上押して作動させる。 */ }
            action <'F-ECL-FDS-06'> F_ECL_FDS_06 { doc /* 乗員室には携帯消火器が3本（ミッドデッキに2本、フライトデッキに1本）あり、先細のノズルを計器盤の消火穴に差し込んでパネル内部の火災に対処でき、アビオニクスベイ消火器の予備にもなる。 */ }
            action <'F-ECL-FDS-07'> F_ECL_FDS_07 { doc /* 消火器は宇宙では実演目的でしか放出されたことがなく、飛行中に放出した場合は機内大気と表面の清浄化のため直ちに地球へ帰還するとされる。 */ }
            action <'F-ECL-FDS-08'> F_ECL_FDS_08 { doc /* 運用中、乗員が電源遮断で火災を未然に防いだ事象が5件、煙検知器回路の誤報・故障が15件あった。 */ }
            action <'F-ECL-FDS-09'> F_ECL_FDS_09 { doc /* オービタには、ミッドデッキとフライトデッキのアビオニクス冷却空気の戻りラインに9個のイオン化式煙検知器があり、Spacelabにはさらに6個がある。 */ }
            action <'F-ECL-FDS-10'> F_ECL_FDS_10 { doc /* 煙検知・消火は急減圧とともにクラス1（緊急）警報に属し、MDMやソフトウェアを介さないハードウェアのみで処理される一方、煙の情報はSM SYS SUMM 1画面にも表示される。 */ }
            action <'F-ECL-FDS-11'> F_ECL_FDS_11 { doc /* 煙感知器と各ベイの消火ボトルの点火回路は、主母線A（L/R FLT DK、BAY 2A/3B、FIRE SUPPR BAY 3）・B（BAY 1B/3A、FIRE SUPPR BAY 1）・C（CABIN、BAY 1A/2B、FIRE SUPPR BAY 2）の遮断器（パネルO14・O15・O16）から給電される。 */ }
            action <'F-ECL-FDS-12'> F_ECL_FDS_12 { doc /* キャビンまたはベイの両ファンが故障して空気が循環しない場合は、その区画の煙検知を喪失とみなす。空気の循環がないと、火元が感知器から離れていれば煙の粒子が間に合って届かないためである（A17-2）。 */ }
        }
        package <'SSD-FD-ECL-FDS-ALM-001'> FN_ECL_FDS_ALM {
            action <'F-ECL-FDS-ALM-01'> F_ECL_FDS_ALM_01 { doc /* 煙検知・消火の警報は急減圧とともにクラス1（緊急）警報で、ハードウェアだけで発報し、音は煙検知系が起動するサイレンで、急減圧のクラクソンと区別される（SCOM 2.2節）。 */ }
            action <'F-ECL-FDS-ALM-02'> F_ECL_FDS_ALM_02 { doc /* 感知器のトリップ信号は、パネルL1の該当するSMOKE DETECTION灯と、パネルF2・F4・A7・MO52Jの4つのMASTER ALARM灯を点灯させ、乗員室のサイレンを鳴らす（SCOM 2.2節）。 */ }
            action <'F-ECL-FDS-ALM-03'> F_ECL_FDS_ALM_03 { doc /* サイレンは666〜1,470 Hzを5秒周期で上下する音で、いずれかのMASTER ALARM押しボタンで止められる。バックアップC&Wは高い煙濃度に対してクラス2の警報も出す（C&W訓練マニュアル3.3.1節）。 */ }
            action <'F-ECL-FDS-ALM-04'> F_ECL_FDS_ALM_04 { doc /* L1のCABIN灯はキャビンファン・プレナムの感知器、L FLT DECK・R FLT DECK灯は左右の還流ダクトの感知器、AV BAY灯は各ベイの感知器で点灯する（SCOM 2.2節）。 */ }
            action <'F-ECL-FDS-ALM-05'> F_ECL_FDS_ALM_05 { doc /* 警報はSENSOR RESETまでラッチされ、ラッチ中は別の火災が起きても2回目のサイレンは鳴らないが、L1灯とSM SYS SUMM 1の濃度は有効で、バックアップC&Wがクラス2の音を出す。A群とB群は独立で、一方がラッチ中でも他方は緊急警報を出せる（C&W訓練マニュアル3.3.2.2節）。 */ }
            action <'F-ECL-FDS-ALM-06'> F_ECL_FDS_ALM_06 { doc /* CIRCUIT TESTをAまたはBにすると、AGENT DISCH灯が点灯し、約20秒後にSMOKE DETECTION A（B）灯とサイレンが作動する。5〜10秒でOFFにすると20秒の遅れを飛ばして直ちに作動する（SCOM 2.2節）。 */ }
            action <'F-ECL-FDS-ALM-07'> F_ECL_FDS_ALM_07 { doc /* CIRCUIT TESTはCNTL BUS BC3の28 VをA群またはB群の感知器に加えて灯と20秒の遅れを試験し、SENSOR RESETは感知器の論理回路をリセットして次のサイレン警報を可能にする（C&W訓練マニュアル表3-1）。 */ }
            action <'F-ECL-FDS-ALM-08'> F_ECL_FDS_ALM_08 { doc /* 軌道運用チェックリストの回路試験は、A・Bの各回路を5〜10秒でOFFにする方法と15〜25秒待つ方法の2通りで行い、A試験ではSMOKE DETECTION A灯5個、B試験ではB灯4個（PAYLOAD灯は消灯）とサイレン・MASTER ALARMを確かめる。 */ }
            action <'F-ECL-FDS-ALM-09'> F_ECL_FDS_ALM_09 { doc /* 警報後に感知器をリセットし、5秒で再警報すれば濃度、20秒で再警報すれば増加率による警報である。直ちに再警報すれば感知器を疑い、自己試験を行ってSM SYS SUMM 1の濃度を確かめる（SCOM 2.2節）。 */ }
            action <'F-ECL-FDS-ALM-10'> F_ECL_FDS_ALM_10 { doc /* 故障処置手順C/W 4.2dは、煙検知灯のないサイレンに対し、SM SYS SUMM 1の濃度（2.2超または20秒で0.4超の増加）を確かめ、A・Bの回路試験で煙検知の表示回路の故障とC/Wのサイレン起動回路の故障を切り分ける。 */ }
            action <'F-ECL-FDS-ALM-11'> F_ECL_FDS_ALM_11 { doc /* C&Wの電源A（B）を失うと、音声発生器A（B）による煙警報音が失われる（SCOM 2.2節）。 */ }
            action <'F-ECL-FDS-ALM-12'> F_ECL_FDS_ALM_12 { doc /* SCOMの経験則は、煙濃度が1.8を下回ったらSENSOR RESETを押し、次の警報がマスクされるのを防ぐとする（SCOM 2.2節）。 */ }
        }
        package <'SSD-FD-ECL-FDS-DET-001'> FN_ECL_FDS_DET {
            action <'F-ECL-FDS-DET-01'> F_ECL_FDS_DET_01 { doc /* 煙感知器は乗員室と3つのアビオニクスベイに計9個あり、A群はキャビンファン出口・フライトデッキの左還流ダクト・各ベイに1個ずつ、B群はフライトデッキの右還流ダクトと各ベイに1個ずつ置かれる。ベイの感知器はベイの上部と下部の近くにあり、ベイ内の火災は両方の感知器が検知するはずである（C&W訓練マニュアル3.3.2節）。 */ }
            action <'F-ECL-FDS-DET-02'> F_ECL_FDS_DET_02 { doc /* 感知器は煙粒子の濃度とその増加率を感知し、濃度2,000±200 µg/m³が5秒以上続くか、毎秒22 µg/m³の増加が20秒間に8回連続すると警報信号（トリップ）を出す（SCOM 2.2節）。 */ }
            action <'F-ECL-FDS-DET-03'> F_ECL_FDS_DET_03 { doc /* 感知器は容積形ポンプで周囲の空気を連続して吸引し、入口で40ミクロンを超える粒子を除き、分離器で2ミクロン以下の粒子だけを感知室に入れる。所要電力は約6.5 Wである（C&W訓練マニュアル3.3.2.2節）。 */ }
            action <'F-ECL-FDS-DET-04'> F_ECL_FDS_DET_04 { doc /* 感知室と基準室はアメリシウム241のα線で空気を電離し、煙の微粒子で感知室の電流が下がることによる両室の電流差から、警報と濃度のアナログ出力を作る（C&W訓練マニュアル3.3.2.2節）。 */ }
            action <'F-ECL-FDS-DET-05'> F_ECL_FDS_DET_05 { doc /* 感知器は過電流による電線束の加熱などで出る微小粒子に感度があり、火災の前段階（presmoke）で警報を出す（C&W訓練マニュアル3.3.2.2節）。 */ }
            action <'F-ECL-FDS-DET-06'> F_ECL_FDS_DET_06 { doc /* 感知器はBrunswick社の能動式イオン化感知器で、交流同期電動機で回す回転ベーン式容積形ポンプで空気を吸い込み、大きな粒子を空力的に分けて誤警報を防ぎ、LSIが周波数とその変化率から警報を判定する（Gibb他、1985年）。 */ }
            action <'F-ECL-FDS-DET-07'> F_ECL_FDS_DET_07 { doc /* 開発では、当初の水晶振動子マイクロバランス（QCM）方式を寿命の問題からイオン化室に替え、空気密度による信号のずれを2つの線源の特性の組合せで抑えた（Gibb他、1985年）。 */ }
            action <'F-ECL-FDS-DET-08'> F_ECL_FDS_DET_08 { doc /* 空気ポンプはベーン材をFluoroloy Dに替えて12,000時間を超える運転を実証し、電動機は湿式軸受と低回転化で20,000時間の寿命とし、自己診断回路は電流の波形の周波数で電動機の断線を判定する方式に改めた（Gibb他、1985年）。 */ }
            action <'F-ECL-FDS-DET-09'> F_ECL_FDS_DET_09 { doc /* 各感知器は警報と濃度計測の2つの独立な指示を出し、回路試験で検出できるハードウェア故障は空気ポンプの故障だけである。試験のいずれかに合格すればポンプは動いており、GPCへの濃度は有効とみなす（A17-2）。 */ }
            action <'F-ECL-FDS-DET-10'> F_ECL_FDS_DET_10 { doc /* 煙検知が働くには、各区画でアビオニクスベイファンとキャビンファンによる空気の循環が必要である。感知器の温度制限（130°F）を超えるとポンプ駆動回路が故障し、煙検知を失うおそれがある（SODB 3.4.6.5節）。 */ }
            action <'F-ECL-FDS-DET-11'> F_ECL_FDS_DET_11 { doc /* STS-28（1989年）では、テレプリンタのケーブルの短絡で火花が出たが、感知器の濃度は最大でも警報設定値2,000 µg/m³を大きく下回った。大きな粒子が分離器で除かれたことなどが理由に挙げられた（Friedman、1993年）。 */ }
            action <'F-ECL-FDS-DET-12'> F_ECL_FDS_DET_12 { doc /* STS-8では、アビオニクスベイ1のB感知器が断続的に煙警報を出したが同じベイのA感知器は煙を示さず、9個すべてが試験で良好だったため、B感知器の遮断器を開いて誤警報を防いだ。 */ }
        }
        package <'SSD-FD-ECL-FDS-FIX-001'> FN_ECL_FDS_FIX {
            action <'F-ECL-FDS-FIX-01'> F_ECL_FDS_FIX_01 { doc /* 前方アビオニクスベイ1・2・3AにHalon消火ボトルが1本ずつ常設され、各ボトルは長さ8 in・直径4.25 inの圧力容器に3.74〜3.8 lbのHalonを収める（SCOM 2.2節）。 */ }
            action <'F-ECL-FDS-FIX-02'> F_ECL_FDS_FIX_02 { doc /* 放出は、パネルL1の該当するFIRE SUPPRESSIONスイッチをARMにし、AGENT DISCH押しボタンを2秒以上押す。押しボタンが火工品点火制御器（PIC）を作動させ、ボトルの火工弁が開いてHalonがベイへ放出される（SCOM 2.2節）。 */ }
            action <'F-ECL-FDS-FIX-03'> F_ECL_FDS_FIX_03 { doc /* FIRE SUPPRESSION AV BAY 1（2、3）のSAFE/ARMスイッチは、主母線B（C、A）からの電力をAGENT DISCH押しボタンとボトルのPICのアーム回路へ入切りする（C&W訓練マニュアル表3-1）。 */ }
            action <'F-ECL-FDS-FIX-04'> F_ECL_FDS_FIX_04 { doc /* ARMでカバー付きのAGENT DISCH押しボタンに電力が加わり、押した後1秒の時間遅れで誤放出を防いでから主母線の電力がPICへ送られる（C&W訓練マニュアル3.3.3.4節）。 */ }
            action <'F-ECL-FDS-FIX-05'> F_ECL_FDS_FIX_05 { doc /* ボトルのノズル組立は1.5 inノズル・PIC・ばね・中空円筒形の刃から成り、PICの爆発でばねが刃を容器の隔膜に打ち込んで破り、Halonを放出する。放出前の圧力は65°Fで185 psigである（C&W訓練マニュアル3.3.3.5節）。 */ }
            action <'F-ECL-FDS-FIX-06'> F_ECL_FDS_FIX_06 { doc /* ボトル圧力が60±10 psigを下回るとAGENT DISCH灯が点灯し、ボトルが放出されたことを示す（SCOM 2.2節）。 */ }
            action <'F-ECL-FDS-FIX-07'> F_ECL_FDS_FIX_07 { doc /* 放出でベイ内のHalon濃度は7.5〜9.5%になり、消火に必要な濃度は4〜5%である。携帯消火器をベイに放出した場合は6〜7%になる（C&W訓練マニュアル3.3.3.4節）。 */ }
            action <'F-ECL-FDS-FIX-08'> F_ECL_FDS_FIX_08 { doc /* ベイのHalonはベイファンが運転していても50時間有効である。放出時には感知器の濃度が約7,500 µg/m³に跳ね上がり、90〜120秒で火災による濃度の水準に戻る（C&W訓練マニュアル3.3.3.6節）。 */ }
            action <'F-ECL-FDS-FIX-09'> F_ECL_FDS_FIX_09 { doc /* 放出時にはベイの圧力が一時的に約1 psia上がり、放出音は乗員に聞こえ、試験では最大143 dBに達した（C&W訓練マニュアル3.3.3.5節）。 */ }
            action <'F-ECL-FDS-FIX-10'> F_ECL_FDS_FIX_10 { doc /* AGENT DISCH灯が放出音を伴わずに点灯した場合、または音を伴う点灯から50時間（冷却を強化しアクティブ冷却のペイロードを置いたベイ3Aは28時間）が経過した場合に、前部アビオニクスベイの消火を喪失とする（A17-3）。 */ }
            action <'F-ECL-FDS-FIX-11'> F_ECL_FDS_FIX_11 { doc /* 固定ボトルのHalon充填量は1.7 kg、放出時間は1秒である（Friedman・Dietrich、1991年）。 */ }
            action <'F-ECL-FDS-FIX-12'> F_ECL_FDS_FIX_12 { doc /* IOAのFMEA/CIL評価（1988年）は、ベイの消火ボトルの回路が単一系統であることを重視し、主ボトルが放出できないとき上昇・再突入中は携帯消火器で代替できない点を懸念とした。 */ }
        }
        package <'SSD-FD-ECL-FDS-OPS-001'> FN_ECL_FDS_OPS {
            action <'F-ECL-FDS-OPS-01'> F_ECL_FDS_OPS_01 { doc /* 火災は、乗員による炎・煙の目視、またはベイでは同じ区画の2個の感知器が2,000 µg/m³を超える場合、1個が2,000 µg/m³で増加中かつ他方が自己試験に不合格の場合、電気データで持続的な短絡が確かめられた場合とする（A17-1A）。 */ }
            action <'F-ECL-FDS-OPS-02'> F_ECL_FDS_OPS_02 { doc /* 乗員室の火災では、乗員は感知器の警報より先ににおいで気づくことが多く、Halonを放出する前に火元を特定して火災を確かめなければならない（A17-1A）。 */ }
            action <'F-ECL-FDS-OPS-03'> F_ECL_FDS_OPS_03 { doc /* ベイの煙検知は、一方の感知器が回路試験の両方に不合格で他方がいずれかに不合格の場合、両感知器の電源を保てない場合、両ベイファンの故障で空気が循環しない場合に喪失とし、乗員室も3個の感知器・電源・両キャビンファンについて同様に判定する（A17-2）。 */ }
            action <'F-ECL-FDS-OPS-04'> F_ECL_FDS_OPS_04 { doc /* ベイの煙検知を失った場合は、持続的な短絡による機器故障があればHalonを放出し、ベイ1・2ではOMS-2後に空冷機器とベイファンの電源を切る。対流による酸素の供給とファンの摩擦による着火を除くためである（A17-51A）。 */ }
            action <'F-ECL-FDS-OPS-05'> F_ECL_FDS_OPS_05 { doc /* ベイ3は通信とC&Wの機器を切れないため、ベイ3の前のロッカーを外して乗員室の感知器と乗員で監視し、再突入の電源投入前にロッカーを戻して携帯のHalonボトルをベイへ放出する（A17-51A）。 */ }
            action <'F-ECL-FDS-OPS-06'> F_ECL_FDS_OPS_06 { doc /* 乗員室の煙検知を失った場合は乗員の1人が常に起きて煙・火災を監視し、区画に指示が2つしか残らない場合は毎日回路試験を行う（A17-51B・C）。 */ }
            action <'F-ECL-FDS-OPS-07'> F_ECL_FDS_OPS_07 { doc /* 火災の処置は、ベイではHalonボトルの放出・ベイファンの停止・ヘルメットのバイザーを下ろすこと、乗員室ではキャビンファンの停止・ヘルメットの着用・携帯のHalonボトルを適切な消火ポートへ放出することである（A17-53A・B）。 */ }
            action <'F-ECL-FDS-OPS-08'> F_ECL_FDS_OPS_08 { doc /* ベイの火災後はベイを船外へパージし、乗員室に燃焼生成物があれば8 psiへ減圧して連続パージする。減圧中にベイの有毒物を乗員室へ吸い出さないよう、ベイのパージは3 lb/hr以上とする（A17-53C）。 */ }
            action <'F-ECL-FDS-OPS-09'> F_ECL_FDS_OPS_09 { doc /* 火災の確認のないHalon放出では、ベイは船外へパージし、放出時刻が分からなければ打上げ時に放出したとみなす。携帯消火器の漏れは、始まりが分かればエアロックの減圧弁から残りを船外へ放出する（A17-54）。 */ }
            action <'F-ECL-FDS-OPS-10'> F_ECL_FDS_OPS_10 { doc /* ベイへ放出したHalonは50時間で約50%、100時間で全量が乗員室へ拡散し、LiOHの活性炭やATCOではほとんど除けない。火災のない放出では、計器盤や乗員室への携帯消火器の放出後の暴露を24〜48時間までとする（A13-152）。 */ }
            action <'F-ECL-FDS-OPS-11'> F_ECL_FDS_OPS_11 { doc /* 火災後は、CSA-CPで15分ごとにO2・CO・HCN・HClを記録してMCCへ報告し、濃度に応じてATCO・活性炭・LiOHキャニスタを交換する。通信がない場合は、煙が見えず、キャビンの感知器の読みが1.2未満などの条件を満たすまでバイザーを下ろしておく（MAL FRP-2）。 */ }
            action <'F-ECL-FDS-OPS-12'> F_ECL_FDS_OPS_12 { doc /* 火災をDPS表示の濃度で確かめたら、軌道上はQDM、上昇・再突入中はバイザーを閉じて酸素を吸い、固定または携帯のHalonボトルで消火する。その後WCSの活性炭フィルタ・ATCO・LiOHで大気を浄化し、安全な水準にできなければ早期に帰還する（SCOM 6.8節）。 */ }
        }
        package <'SSD-FD-ECL-FDS-PFE-001'> FN_ECL_FDS_PFE {
            action <'F-ECL-FDS-PFE-01'> F_ECL_FDS_PFE_01 { doc /* 乗員室には携帯消火器が3本（ミッドデッキに2本、フライトデッキに1本）あり、ノズルは計器盤の消火ポートに合う先細形である（SCOM 2.2節）。 */ }
            action <'F-ECL-FDS-PFE-02'> F_ECL_FDS_PFE_02 { doc /* 消火ポートには、表示付きラベルで覆った直径1/2 inの穴と、表示のない1/2〜1/4 inの先細の穴の2種類があり、パネル直後の空間に通じる。パネル内部やベイ内の火災ではノズルを差し込み、15秒間押して全量を放出する（SCOM 2.2節）。 */ }
            action <'F-ECL-FDS-PFE-03'> F_ECL_FDS_PFE_03 { doc /* 携帯消火器は380 psigに加圧され、ベイの固定ボトルよりやや小さい。約90秒で全量を放出し、最初の30秒で90%が出る。ベイへはポートから空になるまで放出する（C&W訓練マニュアル3.3.3.1〜3.3.3.2節）。 */ }
            action <'F-ECL-FDS-PFE-04'> F_ECL_FDS_PFE_04 { doc /* 消火器は長さ約13.3 in・直径3.5 inで約3.75 lbのHalon 1301を収め、放出時間は1 gで18±2秒、無重量で30±5秒である（飛行運用マニュアル3.24節）。 */ }
            action <'F-ECL-FDS-PFE-05'> F_ECL_FDS_PFE_05 { doc /* 消火器は片手で2秒以内に取り外せ、リングピンを抜いてトリガを握って放出する。無重量では2.4 lbの推力で乗員が動かされるため、体を固定してから放出する（飛行運用マニュアル3.24節）。 */ }
            action <'F-ECL-FDS-PFE-06'> F_ECL_FDS_PFE_06 { doc /* 消火ポートはアビオニクスベイ・ギャレー・CFES・WCS・計器盤にあり、計器盤内部の火災ではポートに、開放空間の火災では炎の根元に向けて放出する（飛行運用マニュアル3.24節）。 */ }
            action <'F-ECL-FDS-PFE-07'> F_ECL_FDS_PFE_07 { doc /* ベイの火災はパネルL1から遠隔操作する固定ボトルで消火し、その場合も再突入の直前に携帯消火器を該当するベイへ放出する（飛行運用マニュアル3.24節）。 */ }
            action <'F-ECL-FDS-PFE-08'> F_ECL_FDS_PFE_08 { doc /* 乗員室でHalonが有効なのはキャビンファンを止めたときだけで、空気が循環していると3本すべてを放出しても濃度は1%未満にとどまる（有効には4%以上が必要）。ファンを再び回すとHalonは乗員室全体に薄まり、次の火災には再び放出が必要になる（C&W訓練マニュアル3.3.3.6節）。 */ }
            action <'F-ECL-FDS-PFE-09'> F_ECL_FDS_PFE_09 { doc /* Halon 1301は無色・無臭・非導電性で、暴露は7%以下なら15分、7〜10%は1分、10〜15%は30秒までとし、15%を超える暴露は避ける（C&W訓練マニュアル3.3.5節）。 */ }
            action <'F-ECL-FDS-PFE-10'> F_ECL_FDS_PFE_10 { doc /* Halonは炎や約900°Fの高温面に触れて分解してから消火に働くとされ、分解生成物はわずかな濃度でも刺激臭のある有害な雰囲気を作る（SCOM 2.2節）。 */ }
        }
        package <'SSD-FD-ECL-H2O-001'> FN_ECL_H2O {
            action <'F-ECL-H2O-01'> F_ECL_H2O_01 { doc /* 給水・廃水系は、FES、乗員の飲用、衛生のための水を供給し、給水系は燃料電池の生成水を、廃水系はキャビン湿度分離器と乗員からの廃水を貯蔵する。 */ }
            action <'F-ECL-H2O-02'> F_ECL_H2O_02 { doc /* ミッドデッキ床下に給水タンク4基と廃水タンク1基があり、各タンクの使用可能容量は165 lbである。 */ }
            action <'F-ECL-H2O-03'> F_ECL_H2O_03 { doc /* 3基の燃料電池は、最大で毎時25 lbの供給水を生成する。 */ }
            action <'F-ECL-H2O-04'> F_ECL_H2O_04 { doc /* 燃料電池からの水素を含む水は2台の水素分離器を通り、余剰水素の85%が除去される。 */ }
            action <'F-ECL-H2O-05'> F_ECL_H2O_05 { doc /* タンクAに入る水は微生物フィルタを通って約0.5 ppmのヨウ素が添加され、通常は乗員の飲用に使われる。 */ }
            action <'F-ECL-H2O-06'> F_ECL_H2O_06 { doc /* タンクA・Bの水は、エアロックのEMU補給、FES給水系A、船外ダンプに使われる。 */ }
            action <'F-ECL-H2O-07'> F_ECL_H2O_07 { doc /* ギャレー給水弁を開くと、給水は水冷却ループの飲料水チラーで冷やす経路と常温の経路に分かれてギャレーへ送られ、ギャレーを搭載しない飛行ではApollo給水器につながれる。 */ }
            action <'F-ECL-H2O-08'> F_ECL_H2O_08 { doc /* 給水・廃水のダンプ配管は非常用クロスタイでつなぐことができ、一方のノズルから他方の水をダンプし、CWCに給水や廃水を貯めることもできる。 */ }
            action <'F-ECL-H2O-09'> F_ECL_H2O_09 { doc /* 給水・廃水タンクは窒素系統1・2のいずれかから15.5〜17.0 psigの窒素で加圧され、打上げ時はタンクAを乗員室へベントして燃料電池の浸水を防ぐ。 */ }
        }
        package <'SSD-FD-ECL-H2O-DMP-001'> FN_ECL_H2O_DMP {
            action <'F-ECL-H2O-DMP-01'> F_ECL_H2O_DMP_01 { doc /* 給水はダンプ隔離弁（乗員室内）とダンプ弁（中胴）を通して全タンクから船外へダンプでき、タンクC・Dの水はクロスオーバ弁を経てダンプする（SCOM 2.9節）。 */ }
            action <'F-ECL-H2O-DMP-02'> F_ECL_H2O_DMP_02 { doc /* SUPPLY H2O DUMP VLV ENABLE/NOZ HTRスイッチはダンプノズルのヒータとダンプ弁に給電し、ノズルヒータに電力がなければ給水ダンプ弁は開けない（訓練マニュアル5.5節）。 */ }
            action <'F-ECL-H2O-DMP-03'> F_ECL_H2O_DMP_03 { doc /* 給水ダンプノズルの上流の配管はサーモスタット制御のA・Bヒータで凍結を防ぎ、ヒータに給電するパネルML86BのH2O LINE HTR A・B遮断器は廃水ダンプ配管と真空ベント配管のヒータにも給電する（SCOM 2.9節）。 */ }
            action <'F-ECL-H2O-DMP-04'> F_ECL_H2O_DMP_04 { doc /* 給水ダンプの前に非常用クロスタイの給水QDへパージ装置を付け、ダンプ後に乗員室の空気（約3 lb/hr）でダンプ弁の残水を除き、残水の凍結で弁が開いて水が漏れ出る現象を防ぐ（SCOM 2.9節）。 */ }
            action <'F-ECL-H2O-DMP-05'> F_ECL_H2O_DMP_05 { doc /* 給水・廃水ダンプ配管の隔離弁とダンプ弁の間には非常用クロスタイの接続があり、可撓ホースで両系をつないで一方のノズルから他方の水をダンプでき、CWC（公称95 lb）にも充填できる（SCOM 2.9節）。 */ }
            action <'F-ECL-H2O-DMP-06'> F_ECL_H2O_DMP_06 { doc /* 余剰の給水は、ダンプ配管、FES、クロスタイからCWCへ、廃水ダンプ配管の順に捨て、給水系の無菌性を保つ（運用飛行規則A18-55）。 */ }
            action <'F-ECL-H2O-DMP-07'> F_ECL_H2O_DMP_07 { doc /* 給水ダンプはノズル温度が100°F以上で始め、ノズル温度A・Bがともに90°F未満になれば中止して、以後そのノズルからのダンプを行わない（A18-56）。 */ }
            action <'F-ECL-H2O-DMP-08'> F_ECL_H2O_DMP_08 { doc /* 廃水ダンプはノズル温度150°F超で始め、ノズルヒータ作動中のノズル温度は周囲のタイルのはく離を防ぐため350°F以下とする（A17-505）。 */ }
            action <'F-ECL-H2O-DMP-09'> F_ECL_H2O_DMP_09 { doc /* 廃水ノズルに着氷を検知したときは、氷がなくなるまで両ノズルからのダンプを中止する。両ノズルは約6.5〜7.0 in離れており、廃水ノズルの着氷は給水ノズルの着氷を助長する（A17-502）。 */ }
            action <'F-ECL-H2O-DMP-10'> F_ECL_H2O_DMP_10 { doc /* 軌道運用チェックリストでは、給水ダンプはノズル温度が100°Fを超えてから（約5分）、廃水ダンプは250°Fを超えてから（約10分）ダンプ弁を開き、水量は毎分約1〜2%減る（5-6）。 */ }
            action <'F-ECL-H2O-DMP-11'> F_ECL_H2O_DMP_11 { doc /* 給水ダンプ弁が故障した場合は、クロスタイの給水QDと廃水QDをY/Yホースでつなぎ、燃料電池の生成水の空き容量を作るため給水を廃水ダンプ配管から捨てる（IFM W-41）。 */ }
            action <'F-ECL-H2O-DMP-12'> F_ECL_H2O_DMP_12 { doc /* STS-65では給水ダンプ中にノズル温度が50°Fへ急落してダンプを中止し、最大2ガロンの水が凍結したと推定され、13回の焼出しで氷を溶かして以後の給水はFESで捨てた。 */ }
        }
        package <'SSD-FD-ECL-H2O-FCW-001'> FN_ECL_H2O_FCW {
            action <'F-ECL-H2O-FCW-01'> F_ECL_H2O_FCW_01 { doc /* 3基の燃料電池は最大毎時25 lb（発電1 kWあたり約0.77 lb）の生成水を生み、生成水は単一の水リリーフ制御盤に集まって、通常は飲料水タンクAへ、必要なら燃料電池の水リリーフノズルへ向けられる（SCOM 2.9節）。 */ }
            action <'F-ECL-H2O-FCW-02'> F_ECL_H2O_FCW_02 { doc /* 生成水は、燃料電池と給水タンクの圧力差によって給水タンクへ送られる（訓練マニュアル5.1節）。 */ }
            action <'F-ECL-H2O-FCW-03'> F_ECL_H2O_FCW_03 { doc /* 水素を含む生成水は水リリーフ制御盤から2台の水素分離器を通り、余剰水素の85%が除かれる。分離器は水素と親和性のある銀パラジウム管の束でできている（SCOM 2.9節）。 */ }
            action <'F-ECL-H2O-FCW-04'> F_ECL_H2O_FCW_04 { doc /* 水素は銀パラジウム管の壁を透過し、真空ベント配管から船外へ排出される（訓練マニュアル5.1節）。 */ }
            action <'F-ECL-H2O-FCW-05'> F_ECL_H2O_FCW_05 { doc /* タンクAへ入る水は微生物フィルタを通って約0.5 ppmのヨウ素を加えられ、タンクA内の微生物の増殖が防がれる（SCOM 2.9節）。 */ }
            action <'F-ECL-H2O-FCW-06'> F_ECL_H2O_FCW_06 { doc /* タンクAが満杯か入口弁が閉じているときは、水は1.5 psidの逆止弁を経てタンクBへ、さらに次の1.5 psidの逆止弁を経てタンクC・Dの入口へ流れる（SCOM 2.9節）。 */ }
            action <'F-ECL-H2O-FCW-07'> F_ECL_H2O_FCW_07 { doc /* 主経路の閉塞に備えて、各燃料電池の生成水配管にはタンクBの入口マニホールドへ向かう並列の冗長経路が設けられ、この経路は水素分離器を通らない（SCOM 2.9節）。 */ }
            action <'F-ECL-H2O-FCW-08'> F_ECL_H2O_FCW_08 { doc /* 冗長経路には温度センサがあり、主経路の圧力はテレメトリとBFS THERMAL表示で監視でき、水リリーフ盤の共通出口のpHセンサが燃料電池の健全性と水の純度を示す（SCOM 2.9節）。 */ }
            action <'F-ECL-H2O-FCW-09'> F_ECL_H2O_FCW_09 { doc /* 燃料電池水のpH表示が高いときは、生成水を小便器へ流してpH試験紙で確かめる。高いpHは水中の水酸化カリウム（KOH）の濃度が高いことによる（IFM W-14）。 */ }
            action <'F-ECL-H2O-FCW-10'> F_ECL_H2O_FCW_10 { doc /* 給水圧が40 psiaを超えると、故障処置手順6.5dでタンクの過充填かタンクA/B間の逆止弁の故障かを切り分け、タンクAの出口弁を開いて水量を下げるなどの処置をとる（MAL 6.5d）。 */ }
            action <'F-ECL-H2O-FCW-11'> F_ECL_H2O_FCW_11 { doc /* STS-82では水素分離器のない冗長経路から給水系へ水素が入り、EMUへの水素の混入を防ぐため、すべてのEVAとEMU補給が終わるまでタンクCを隔離した（運用飛行規則A18-57A）。 */ }
            action <'F-ECL-H2O-FCW-12'> F_ECL_H2O_FCW_12 { doc /* IOAの評価（1988年）は、燃料電池出口配管の流れの制限は燃料電池の「デッドヘッド」を招いて生命・機体の喪失につながりうるとし、外部漏れは任務への影響にとどまるとした。 */ }
        }
        package <'SSD-FD-ECL-H2O-GAL-001'> FN_ECL_H2O_GAL {
            action <'F-ECL-H2O-GAL-01'> F_ECL_H2O_GAL_01 { doc /* パネルR11LのSUPPLY H2O GALLEY SUP VLVスイッチを開にすると、給水は並列の2経路に分かれ、一方はARSの水冷却ループの飲料水チラーで冷やされ、他方はチラーを通らない常温水となる（SCOM 2.9節）。 */ }
            action <'F-ECL-H2O-GAL-02'> F_ECL_H2O_GAL_02 { doc /* ギャレー給水弁を閉じると飲料水はミッドデッキのECLSS給水パネルから切り離され、ギャレーを搭載しない飛行では冷水と常温水をApollo給水器につないで飲用と食品の復水に使う（SCOM 2.9節）。 */ }
            action <'F-ECL-H2O-GAL-03'> F_ECL_H2O_GAL_03 { doc /* チラーはARSの水冷却ループで乗員の飲料水を冷やす（訓練マニュアル3.3.8節）。 */ }
            action <'F-ECL-H2O-GAL-04'> F_ECL_H2O_GAL_04 { doc /* ギャレーの復水ステーションは、食品・飲料パックへ0.5オンス刻みで0.5〜8オンスを給水し、温水（145〜165°F）と冷水（40〜60°F）を出す（SCOM 2.12節）。 */ }
            action <'F-ECL-H2O-GAL-05'> F_ECL_H2O_GAL_05 { doc /* 個人衛生用の水は、ギャレー搭載時は補助ポートのQDから、非搭載時は給水器のQDから12 ftのホースで取り出し、ホースの上流には微生物の逆汚染を防ぐ微生物チェック弁がある（1987年の飛行運用マニュアル）。 */ }
            action <'F-ECL-H2O-GAL-06'> F_ECL_H2O_GAL_06 { doc /* ギャレーのヨウ素除去装置（GIRAまたはLIRS）は飛行1日目に取り付け、帰還日に水分補給の準備の後に外す。GIRAは冷水のヨウ素を除き、常温・温水では約1.5 ppmに下げ、乗員のヨウ素摂取を1人1日1 mg未満に保つ（運用飛行規則A17-551A）。 */ }
            action <'F-ECL-H2O-GAL-07'> F_ECL_H2O_GAL_07 { doc /* GIRAの使用中は常温・温水の摂取を1人1日16オンスまでとし、冷水は制限しない。就寝中は冷水ラインをGIRAから外し、ヨウ素を含む水をギャレー内に残して微生物の増殖を防ぐ（A17-551B・C）。 */ }
            action <'F-ECL-H2O-GAL-08'> F_ECL_H2O_GAL_08 { doc /* GIRAの取付けでは、常温（非断熱）の供給ラインに微生物チェック弁（MCV）を、冷水（断熱）のラインにフィルタと活性炭・イオン交換（ACTEX）カートリッジをつなぐ（軌道運用チェックリスト5-53）。 */ }
            action <'F-ECL-H2O-GAL-09'> F_ECL_H2O_GAL_09 { doc /* ISSドッキング飛行では余剰の給水を船外へダンプせず、専用の移送ラインか、ギャレーで手作業で満たす移送バッグでISSへ移す（訓練マニュアル5.1節）。 */ }
            action <'F-ECL-H2O-GAL-10'> F_ECL_H2O_GAL_10 { doc /* STS-114では19個のCWCに給水を満たし、そのうち18個（計1,739.7 lb）をISSへ移送した。 */ }
            action <'F-ECL-H2O-GAL-11'> F_ECL_H2O_GAL_11 { doc /* 水タンクの窒素加圧を失うとギャレーへの給水圧が下がり、復水ステーションの給水量が設定より少なくなることがある。タンクAを隔離するとギャレーへは燃料電池の生成量分しか給水できない（MAL 6.2i）。 */ }
            action <'F-ECL-H2O-GAL-12'> F_ECL_H2O_GAL_12 { doc /* STS-59ではギャレーの温水・冷水に気泡が混じったが、オービタの給水系からの気体の混入ではなく、給水時のベンチュリ効果によるものと判断された。 */ }
        }
        package <'SSD-FD-ECL-H2O-PRS-001'> FN_ECL_H2O_PRS {
            action <'F-ECL-H2O-PRS-01'> F_ECL_H2O_PRS_01 { doc /* 給水・廃水タンクは通常PCSの窒素で加圧され、窒素圧は乗員室圧より15.5〜17.0 psi高く保たれて、水を系統へ送る力となる（訓練マニュアル5.3節）。 */ }
            action <'F-ECL-H2O-PRS-02'> F_ECL_H2O_PRS_02 { doc /* PCS系統1・2の200 psigの窒素は水タンク用N2レギュレータ（流量1 lb/hrに制限）で15.5〜17.0 psigに下げられ、H2O TK N2隔離弁を通って共通のH2O TK N2マニホールドへ入り、廃水タンクと給水タンクのベローズを加圧する。過圧は18.5±1.5 psigで乗員室へ逃がすリリーフ弁が防ぐ（訓練マニュアル5.3節）。 */ }
            action <'F-ECL-H2O-PRS-03'> F_ECL_H2O_PRS_03 { doc /* 窒素系統1・2はそれぞれ単独で水タンクを加圧でき、パネルMO10WのH2O TK N2 REG INLETとH2O TK N2 ISOLの手動弁で制御し、窒素と水は金属のベローズで分けられる（SCOM 2.9節）。 */ }
            action <'F-ECL-H2O-PRS-04'> F_ECL_H2O_PRS_04 { doc /* 打上げ時はタンクAを乗員室へベントする。機体の姿勢と加速度が生成水の流入を妨げ、窒素で加圧したままだと生成水が船外へ逃げ、その経路が故障すれば燃料電池が浸水して発電が止まるためである（訓練マニュアル5.3節）。 */ }
            action <'F-ECL-H2O-PRS-05'> F_ECL_H2O_PRS_05 { doc /* パネルML26CのSUPPLY H2O GN2 TK A SPLY弁とTK VENT弁（いずれも2位置の手動弁）で、タンクAを加圧マニホールドから切り離して乗員室へベントする（訓練マニュアル5.5節）。 */ }
            action <'F-ECL-H2O-PRS-06'> F_ECL_H2O_PRS_06 { doc /* タンクAの弁は、タンクAの量が98（93）%に達する前とタンクBが空になる前に開・加圧の位置へ戻す。満量前に加圧しないとベローズ前後の差圧が15 psidを超えて損傷しうる（運用飛行規則A18-54）。 */ }
            action <'F-ECL-H2O-PRS-07'> F_ECL_H2O_PRS_07 { doc /* タンクA供給弁を開いてベント弁をベント位置にすると全タンクを乗員室圧にでき、漏れが乗員室内なら窒素圧を抜けば漏れが止まる。水の代替加圧弁はマニホールドを乗員室へベントする予備の手段にもなる（訓練マニュアル5.3節）。 */ }
            action <'F-ECL-H2O-PRS-08'> F_ECL_H2O_PRS_08 { doc /* 窒素系統1・2がどちらも使えない場合は、パネルL1のH2O ALTERNATE PRESSスイッチを開にして乗員室の圧力を水タンクに加える。通常は閉じて、与圧系と水タンクの加圧系を切り離す（SCOM 2.9節）。 */ }
            action <'F-ECL-H2O-PRS-09'> F_ECL_H2O_PRS_09 { doc /* 代替加圧弁は飛行中は通常閉じる。開くと水系の圧力が乗員室圧まで下がるため、非常時にだけ使う（運用飛行規則A17-501）。 */ }
            action <'F-ECL-H2O-PRS-10'> F_ECL_H2O_PRS_10 { doc /* 水タンクのN2圧が13.0 psig未満でSMアラートが出ると、故障処置手順6.2iでレギュレータやセンサの故障、N2の漏れを切り分け、再加圧でFESが停止しないようFES制御器を切る（MAL 6.2i）。 */ }
            action <'F-ECL-H2O-PRS-11'> F_ECL_H2O_PRS_11 { doc /* 湿度分離器の漏水などで水タンクを減圧している場合は、ダンプの約30分前から再加圧してダンプ時間を短くし、ダンプ後に再び減圧する（MAL ECLS SSR-17）。 */ }
            action <'F-ECL-H2O-PRS-12'> F_ECL_H2O_PRS_12 { doc /* 廃水タンクにかかわる隔離できない窒素漏れでは水加圧系への窒素供給を止め、IFMで廃水タンクを切り離してから残りを通常の圧力に戻す。FESは低い系統圧で不調になることがあるためである（A17-506C）。 */ }
        }
        package <'SSD-FD-ECL-H2O-SPL-001'> FN_ECL_H2O_SPL {
            action <'F-ECL-H2O-SPL-01'> F_ECL_H2O_SPL_01 { doc /* 給水タンク4基（各165 lb）はミッドデッキ床下にあってPCSの窒素で加圧され、各タンクはベローズ、水量センサ、入口弁・出口弁、疎水性フィルタを持つ（訓練マニュアル5.1節）。 */ }
            action <'F-ECL-H2O-SPL-02'> F_ECL_H2O_SPL_02 { doc /* 水量センサはタンクのベローズの位置から水量を示し、ベローズが漏れると表示は60〜70%付近にとどまる。疎水性フィルタは、漏れた水がN2マニホールドへ入るのを防ぐ（訓練マニュアル5.1節）。 */ }
            action <'F-ECL-H2O-SPL-03'> F_ECL_H2O_SPL_03 { doc /* タンクAは処理水と未処理水を分けるため出口弁を通常閉じて乗員の飲用に充て、タンクB・C・DはFESの冷却に使われることが多い（SCOM 2.9節）。 */ }
            action <'F-ECL-H2O-SPL-04'> F_ECL_H2O_SPL_04 { doc /* 4基の出口は出口マニホールドにまとめられ、タンクBとCの間のクロスオーバ弁でA-B側とC-D側に分かれる。A-B側はFES給水系統A、EMU給水ライン、ダンプ配管に、C-D側はFES給水系統Bにつながる（訓練マニュアル5.1節）。 */ }
            action <'F-ECL-H2O-SPL-05'> F_ECL_H2O_SPL_05 { doc /* FES給水系統Aの水はFESへ直接送られ、系統Bの水はパネルR11LのSUPPLY H2O B SPLY ISOL VLVスイッチで操作する隔離弁を経てFESへ送られる（SCOM 2.9節）。 */ }
            action <'F-ECL-H2O-SPL-06'> F_ECL_H2O_SPL_06 { doc /* FES給水配管は約100 ftあり、パネルL2のFLASH EVAP FEEDLINE HTRスイッチで冗長のサーモスタット制御ヒータを選んで凍結を防ぐ（SCOM 2.9節）。 */ }
            action <'F-ECL-H2O-SPL-07'> F_ECL_H2O_SPL_07 { doc /* 軌道上は燃料電池が飲用とFES冷却に要する以上の水を生むため、タンクA・Bのダンプと充填で水を管理する。ダンプは通常12時間ごとに最大210 lbまで行い、タンクAには乗員5人・96時間分として少なくとも76%（128 lb）を残す（訓練マニュアル5.1節）。 */ }
            action <'F-ECL-H2O-SPL-08'> F_ECL_H2O_SPL_08 { doc /* タンクCは、ペイロードベイ扉を閉じたままの軌道離脱の見送りや緊急の軌道離脱でFESに使う予備として、通常満杯に保つ（訓練マニュアル5.1節）。 */ }
            action <'F-ECL-H2O-SPL-09'> F_ECL_H2O_SPL_09 { doc /* 運用飛行規則は、軌道上の標準構成（タンクA入口開・出口閉、タンクB〜Dの入口・出口開、クロスオーバ弁開）と、ISSへの給水移送構成（タンクA・Bを結び、タンクB入口弁とクロスオーバ弁を閉じて遮断器を抜く）を定める（A18-57A）。 */ }
            action <'F-ECL-H2O-SPL-10'> F_ECL_H2O_SPL_10 { doc /* ヨウ素がFESのコアを腐食させるため、タンクAの水を使うダンプとFES運転は最小にし、タンクAの水は飲用、非常時、着陸機会の確保に使う（A18-51）。 */ }
            action <'F-ECL-H2O-SPL-11'> F_ECL_H2O_SPL_11 { doc /* いつでも帰還できるための給水の最小量は175 lbm（165分の緊急軌道離脱の冷却に相当）とし、通常構成ではPLS点火の4時間前に281 lbmを確保する（A18-59）。 */ }
            action <'F-ECL-H2O-SPL-12'> F_ECL_H2O_SPL_12 { doc /* 乗員室に遊離した給水はIFMで直ちに処理し、修理できないか隔離できない漏れのあるタンクはベント・ダンプして隔離し、以後は使わない（A18-58）。 */ }
        }
        package <'SSD-FD-ECL-H2O-WST-001'> FN_ECL_H2O_WST {
            action <'F-ECL-H2O-WST-01'> F_ECL_H2O_WST_01 { doc /* 廃水タンクは給水タンクと同じ形の1基で、ミッドデッキ床下にあり、乗員の液体廃棄物（尿）と湿度分離器の凝縮水を処分まで衛生的に貯める（訓練マニュアル5.2節）。 */ }
            action <'F-ECL-H2O-WST-02'> F_ECL_H2O_WST_02 { doc /* 廃水タンクの排出可能量は165 lb（残量3.3 lbを除く）で、給水タンクと同じ窒素源で加圧される（SCOM 2.9節）。 */ }
            action <'F-ECL-H2O-WST-03'> F_ECL_H2O_WST_03 { doc /* 廃水はパネルML31CのWASTE H2O TANK 1 VLVスイッチで操作する入口弁から入り、入口弁を開けばタンクの廃水をダンプ配管へも送れる（SCOM 2.9節）。 */ }
            action <'F-ECL-H2O-WST-04'> F_ECL_H2O_WST_04 { doc /* 凝縮水QDの追加に伴い、湿度分離器の共通出口はドレン配管経由で廃水タンクにつながり、出口（ドレン）弁を開くと凝縮水がタンクへ入り、凝縮水の収集時は弁を閉じてCWCへ流す（SCOM 2.9節）。 */ }
            action <'F-ECL-H2O-WST-05'> F_ECL_H2O_WST_05 { doc /* 廃水タンクは量が80%に達する前に廃水ダンプ配管からダンプし、最後の着陸日を支える場合は最終着陸機会の2時間後に93（88）%以下となるようにする（運用飛行規則A17-503A・B）。 */ }
            action <'F-ECL-H2O-WST-06'> F_ECL_H2O_WST_06 { doc /* 廃水の管理は、ダンプとCWCの使用を優先し、次いでクロスタイ経由の給水ノズルからのダンプ、飛行の早期終了、最後のEMU補給後に給水タンクBを予備の廃水タンクとすることの順とする（A17-503）。 */ }
            action <'F-ECL-H2O-WST-07'> F_ECL_H2O_WST_07 { doc /* 廃水タンクは0（5）%までダンプしない。0%ではダンプ配管とベローズが真空になり、WCSと湿度分離器の逆止弁が開いて乗員室の漏れとなるおそれがある（A17-504）。 */ }
            action <'F-ECL-H2O-WST-08'> F_ECL_H2O_WST_08 { doc /* 廃水タンクは、充填できない、タンクか入口マニホールドに修理できない漏れがある、98（93）%でダンプ能力を失った、またはベローズが漏れて廃液圧がH2O N2レギュレータ入口圧より5 psidを超えて高い場合に喪失とする（A17-451）。 */ }
            action <'F-ECL-H2O-WST-09'> F_ECL_H2O_WST_09 { doc /* 過去の飛行で廃水の生成量は1人1日最大6.2 lbあり、ISSミッションではISSとの結合中の廃水ダンプを減らすため湿度凝縮水をCWCに集める（訓練マニュアル5.2節）。 */ }
            action <'F-ECL-H2O-WST-10'> F_ECL_H2O_WST_10 { doc /* 廃水タンクは1人1日約4.4%ずつ増え、尿と凝縮水の寄与はほぼ等しい（SCOM ECLSSの経験則）。 */ }
            action <'F-ECL-H2O-WST-11'> F_ECL_H2O_WST_11 { doc /* 漏れのある廃水タンクはベントして乗員室と同圧にしてダンプし、湿度分離器とWCSのファンセパレータの液体をCWCで集める。通常の飛行はCWCを2個（各95 lbm）積み、7人の乗員で1個あたり約45時間分となる（A17-506B）。 */ }
            action <'F-ECL-H2O-WST-12'> F_ECL_H2O_WST_12 { doc /* 廃水圧が13 psig未満か22 psig超でSMアラートが出ると、故障処置手順6.5cでベローズの損傷や、廃水量95%以上でのタンク満杯を切り分ける（MAL 6.5c）。 */ }
        }
        package <'SSD-FD-ECL-PCS-001'> FN_ECL_PCS {
            action <'F-ECL-PCS-01'> F_ECL_PCS_01 { doc /* ARPCSは酸素・窒素の2ガス方式で、酸素は反応剤貯蔵・分配（PRSD）サブシステムから、窒素は窒素貯蔵タンクから得る。 */ }
            action <'F-ECL-PCS-02'> F_ECL_PCS_02 { doc /* 乗員室を14.7±0.2 psiaに与圧し、平均で窒素80%・酸素20%の混合気に保つ。 */ }
            action <'F-ECL-PCS-03'> F_ECL_PCS_03 { doc /* 酸素分圧は2.95〜3.45 psiaに自動で保たれ、約11.5 psiaの窒素を加えて全圧14.7 psiaとする。 */ }
            action <'F-ECL-PCS-04'> F_ECL_PCS_04 { doc /* 正・負の圧力逃し弁が、乗員室構造を過大圧・過小圧から保護する。 */ }
            action <'F-ECL-PCS-05'> F_ECL_PCS_05 { doc /* 打上げ・帰還用スーツのヘルメットと非常用呼吸マスクへ、呼吸用酸素を直接供給する。 */ }
            action <'F-ECL-PCS-06'> F_ECL_PCS_06 { doc /* 窒素は給水・廃水タンクの加圧にも使われる。 */ }
            action <'F-ECL-PCS-07'> F_ECL_PCS_07 { doc /* 与圧系は2系統の酸素系と2系統の気体窒素系から成り、酸素系は燃料電池と同じPRSDから供給される。 */ }
            action <'F-ECL-PCS-08'> F_ECL_PCS_08 { doc /* PRSDの極低温超臨界酸素は、気体として835〜852 psiaで与圧制御系へ供給される。 */ }
            action <'F-ECL-PCS-09'> F_ECL_PCS_09 { doc /* ARPCSは、1気圧の環境と非常時の8 psiaモードの両方で、酸素分圧と全圧を制御する。 */ }
            action <'F-ECL-PCS-10'> F_ECL_PCS_10 { doc /* 乗員室圧・PPO2・O2/N2流量はO1の計器とSM SYS SUMM 1・DISP 66に表示され、dP/dTが0.08 psi/min以上で低下するとクラクソンが鳴りMASTER ALARM灯が点灯する（SCOM 2.9節）。 */ }
            action <'F-ECL-PCS-11'> F_ECL_PCS_11 { doc /* EVA前の10.2 psia運用では、10.2 psiaのキャビンレギュレータがないため、乗員室圧とPPO2を手動で管理する（訓練マニュアル2.7.3節）。 */ }
        }
        package <'SSD-FD-ECL-PCS-MNF-001'> FN_ECL_PCS_MNF {
            action <'F-ECL-PCS-MNF-01'> F_ECL_PCS_MNF_01 { doc /* 14.7 psiaキャビンレギュレータは入口弁が開いているとき乗員室圧を14.7 psiaに制御し、O2/N2マニホールドにある気体（O2またはN2）が、乗員室圧が14.7 psiaを下回ると補給流として乗員室へ流れる（訓練マニュアル2.3節）。 */ }
            action <'F-ECL-PCS-MNF-02'> F_ECL_PCS_MNF_02 { doc /* 8 psia非常用レギュレータは大きな漏れのときに乗員室圧を8 psiaに保つよう流し、入口弁がないため常に補給できる構成にある（訓練マニュアル2.3節）。 */ }
            action <'F-ECL-PCS-MNF-03'> F_ECL_PCS_MNF_03 { doc /* 14.7 psiレギュレータは14.7±0.2 psia、8 psiレギュレータは8±0.2 psiaに調圧し、仕様上の最大流量はどちらも少なくとも75 lb/hrで、どちらもWCS区画のMO10Wの口から乗員室へ流れる（訓練マニュアル2.3節）。 */ }
            action <'F-ECL-PCS-MNF-04'> F_ECL_PCS_MNF_04 { doc /* レギュレータは、乗員室圧が14.7 psia付近の小さな需要に応じる低流量段（0〜0.75 lb/hr）と、大きく下回ったときの高流量段（0.75〜少なくとも75 lb/hr）の2段から成り、窒素の大流量中にWCSを使うと低酸素症のおそれがある（SCOM 2.9節）。 */ }
            action <'F-ECL-PCS-MNF-05'> F_ECL_PCS_MNF_05 { doc /* O2/N2制御弁を開くと200 psiの窒素がマニホールドを満たしてO2の逆止弁を閉じ、閉じるとマニホールドの圧力が100 psiを下回ったところで100 psiの酸素が流れ込む（訓練マニュアル2.3.1・2.3.2節）。 */ }
            action <'F-ECL-PCS-MNF-06'> F_ECL_PCS_MNF_06 { doc /* 軌道上は使用中の系統のO2/N2制御弁をAUTOにし、O2/N2コントローラがPPO2 2.95 psia未満で弁を閉じて酸素を、3.45 psia超で開いて窒素を流し、その間は前の位置を保つ。実際の制御は3.1±0.05 psiaに保たれている（訓練マニュアル2.3.3節）。 */ }
            action <'F-ECL-PCS-MNF-07'> F_ECL_PCS_MNF_07 { doc /* PPO2センサAのデータはO2/N2コントローラ1が、センサBのデータはコントローラ2が使い、PPO2 SNSR/VLVスイッチをREVERSEにすると対応を入れ替えて、センサ1個の喪失で自動制御を失わないようにする（訓練マニュアル2.3.3節）。 */ }
            action <'F-ECL-PCS-MNF-08'> F_ECL_PCS_MNF_08 { doc /* PPO2 CNTLR SYS 1・2スイッチは、通常範囲（14.7 psiで2.95〜3.45 psia）と非常範囲（8 psiで1.95〜2.45 psia）を選ぶが、EMER位置は手順上使わない（SCOM 2.9節）。 */ }
            action <'F-ECL-PCS-MNF-09'> F_ECL_PCS_MNF_09 { doc /* PPO2の制御は、自動・手動のどちらの方法でも乗員室へ流れる酸素量を制御できなくなったときに喪失とみなし、低い側は酸素を送れなくなったとき、高い側は隔離できない酸素漏れなどで酸素濃度が限界を超えるときである（A17-203）。 */ }
            action <'F-ECL-PCS-MNF-10'> F_ECL_PCS_MNF_10 { doc /* O2/N2コントローラの飛行中の点検には、14.7 psia・AUTOでの両方向の切替の観測が要り、自然な切替が起きなければO2ブリードオリフィスの流れを止めるか、就寝中に制御弁をCLOSE（O2）にして切替を促す（A17-260）。 */ }
            action <'F-ECL-PCS-MNF-11'> F_ECL_PCS_MNF_11 { doc /* 1979年の飛行運用マニュアルは、O2/N2コントローラが乗員室のPPO2を検知してO2/N2制御弁を開閉し、PPO2を14.5 psiの乗員室で3.2 psi、8 psiでは2.2 psiに保つとした。 */ }
            action <'F-ECL-PCS-MNF-12'> F_ECL_PCS_MNF_12 { doc /* STS-2までに、N2/O2の制御盤・供給盤とPPO2センサを交換し、改良したキャビンレギュレータを追加した（STS-2ミッション報告）。 */ }
        }
        package <'SSD-FD-ECL-PCS-MON-001'> FN_ECL_PCS_MON {
            action <'F-ECL-PCS-MON-01'> F_ECL_PCS_MON_01 { doc /* O14のMNAとO15のMNBにあるO2/N2 CNTLRの遮断器は、O2/N2コントローラのほか、乗員室圧、PPO2センサA・B、系統1・2のO2・N2流量、制御弁位置の各トランスデューサに給電し、その他のPCSの計測は専用信号調整器（DSC）が給電する（訓練マニュアル2.6.1節）。 */ }
            action <'F-ECL-PCS-MON-02'> F_ECL_PCS_MON_02 { doc /* O15のMNBのPPO2 C/CABIN dP/dT遮断器がPPO2センサCとハードウェアのdP/dTセンサに給電し、dP/dTセンサはPASS・BFSのすべてのOPSで使える（訓練マニュアル2.6.1節）。 */ }
            action <'F-ECL-PCS-MON-03'> F_ECL_PCS_MON_03 { doc /* BFSのバックアップdP/dTは乗員室圧トランスデューサの値を5秒ごとに30秒前と比べて算出し、等価dP/dTはdP/dTに14.7を掛けて乗員室圧で割るため、漏れ率が一定なら一定の値を示す（訓練マニュアル2.6.1節）。 */ }
            action <'F-ECL-PCS-MON-04'> F_ECL_PCS_MON_04 { doc /* O2濃度はPPO2センサA・B・Cの平均を乗員室圧で割ってPASSのSM SYS SUMM 1に表示し、N2タンクの量はPASSのSM計算機が圧力・容積・温度（PVT）から求める（訓練マニュアル2.6.1節）。 */ }
            action <'F-ECL-PCS-MON-05'> F_ECL_PCS_MON_05 { doc /* 軌道上のPCSの主な表示はPASSのSM SPEC 66で、上昇・再突入ではBFSのSM SYS SUMM 1を使い、O1の計器でCABIN dP/dT、O2/N2流量（系統と気体をロータリスイッチで選ぶ）、乗員室圧、PPO2（センサA・Bを選ぶ）を監視する（訓練マニュアル2.6.2・2.6.3節）。 */ }
            action <'F-ECL-PCS-MON-06'> F_ECL_PCS_MON_06 { doc /* 主C&WのCABIN ATM灯（赤）は乗員室圧、PPO2、O2流量、N2流量の限界外で点灯し、ハードウェアチャネルは乗員室圧、系統1・2のO2流量、PPO2 A・B、系統1・2のN2流量の順に4・14・24・34・44・54・64である（SCOM 2.2節）。 */ }
            action <'F-ECL-PCS-MON-07'> F_ECL_PCS_MON_07 { doc /* CABIN ATM灯の14.7 psiaでの既定の限界は、乗員室圧13.8〜15.2 psia、PPO2 A・B 2.7〜3.6 psia、系統1・2のO2・N2流量4.9 lb/hr以下である（訓練マニュアル2.6.4節）。 */ }
            action <'F-ECL-PCS-MON-08'> F_ECL_PCS_MON_08 { doc /* dP/dtセンサの値が-0.08 psi/minを超えると、4つのMASTER ALARM灯とクラクソン（クラス1）で急減圧を知らせ、警報は負の値だけで出る。dP/dtまたはバックアップdP/dtで0.12 psi/min以上の低下はクラス3の警報を出す（SCOM 2.2節）。 */ }
            action <'F-ECL-PCS-MON-09'> F_ECL_PCS_MON_09 { doc /* 使用中の流量センサは0 lbm/hrで下限外、5 lbm/hrで上限外となり、4.9 lbm/hrで高流量警報を出す。OV-104には25 lbm/hrまで測れる非線形の新しいセンサを組み込み、表示の最大は12.4 lbm/hrとなる（SCOM 2.9節）。 */ }
            action <'F-ECL-PCS-MON-10'> F_ECL_PCS_MON_10 { doc /* PPO2センサは、互いに0.15 psi以内にある2個のうち近い方から0.15 psiを超えてずれると喪失とみなし、2個目以降の故障は過去の特性、O2/N2コントローラの切替の頻度、O2流量から解析で判断する（A17-205）。 */ }
            action <'F-ECL-PCS-MON-11'> F_ECL_PCS_MON_11 { doc /* STS-4の上昇中にもdP/dtが-0.05 psi/minの警報点を超えてクラクソンが作動し、最初の4回の飛行で毎回起きたため、作動値を上げる変更が進められた（STS-4ミッション報告）。 */ }
            action <'F-ECL-PCS-MON-12'> F_ECL_PCS_MON_12 { doc /* STS-108では、EVA後の再与圧の後に系統1の窒素流量センサの表示が0になったまま戻らず、飛行後の試験でセンサの故障を確かめた（STS-108ミッション報告）。 */ }
        }
        package <'SSD-FD-ECL-PCS-N2S-001'> FN_ECL_PCS_N2S {
            action <'F-ECL-PCS-N2S-01'> F_ECL_PCS_N2S_01 { doc /* PCSの窒素は通常ペイロードベイの4基のタンクから供給するが、長期飛行では機体の漏れとウェットトラッシュのベント、RCRSのベント、EVAでの再与圧に多くの窒素が要るため、最大8基まで増やせるようにした（訓練マニュアル2.2節）。 */ }
            action <'F-ECL-PCS-N2S-02'> F_ECL_PCS_N2S_02 { doc /* 常設の4基のうち系統1のタンク3・4は重心の調整のため後部ペイロードベイに移され、系統2のタンク1・2は前部右側にあり、追加の最大4基は飛行ごとにミッションキットとして搭載する（訓練マニュアル2.2節）。 */ }
            action <'F-ECL-PCS-N2S-03'> F_ECL_PCS_N2S_03 { doc /* SCOMは、系統1のタンクを左舷、系統2を右舷に置き、OV-103・OV-105は6基、OV-104は5基とし、タンクはチタンライナのケブラー繊維巻きで、80°Fで公称2,964 psia、容積8,181 in³に充填するとする（SCOM 2.9節）。 */ }
            action <'F-ECL-PCS-N2S-04'> F_ECL_PCS_N2S_04 { doc /* 3,300 psiaの窒素はモータ駆動のN2供給弁からN2供給マニホールドへ入り、N2レギュレータ入口弁を経て200 psigのN2レギュレータで200 psiaに下げられる。弁は電源を失うとその位置に留まり、タンクにヒータはなく圧力だけで送り出す（訓練マニュアル2.2節）。 */ }
            action <'F-ECL-PCS-N2S-05'> F_ECL_PCS_N2S_05 { doc /* N2レギュレータの逃し弁は275 psigで開いて245 psigで閉じ、レギュレータの故障による過圧から窒素系を守るため、真空ベント管から船外へ逃がす（訓練マニュアル2.2節）。 */ }
            action <'F-ECL-PCS-N2S-06'> F_ECL_PCS_N2S_06 { doc /* 調圧後の窒素は乗員室内の逆止弁で他系統への逆流と上流の配管漏れによる流出を防ぎ、N2クロスオーバ弁、水タンク用レギュレータ入口弁、ペイロード用N2弁、O2/N2制御弁へ送る。各系統は少なくとも125 lbm/hrを供給でき、N2クロスオーバ弁は通常閉じておく（SCOM 2.9節）。 */ }
            action <'F-ECL-PCS-N2S-07'> F_ECL_PCS_N2S_07 { doc /* 水タンク用N2レギュレータは200 psiの窒素を15.5〜17.0 psigに下げる2段式のレギュレータで、2段目は18.5±1.5 psigで乗員室へ逃がす（SCOM 2.9節）。 */ }
            action <'F-ECL-PCS-N2S-08'> F_ECL_PCS_N2S_08 { doc /* 給水・廃水タンクは17 psigに加圧され、乗員の使用、船外ダンプ、FESへの給水に必要な圧力で水を押し出す（SCOM 2.9節）。 */ }
            action <'F-ECL-PCS-N2S-09'> F_ECL_PCS_N2S_09 { doc /* N2タンクとN2供給弁の間のMMU GN2隔離弁を開くと高圧の窒素をMMUへ供給でき、ISSへの窒素の移送はPCSのN2系統1だけで行う（訓練マニュアル2.2節）。 */ }
            action <'F-ECL-PCS-N2S-10'> F_ECL_PCS_N2S_10 { doc /* 通常は両方のN2系統を供給弁・レギュレータ入口弁とも開いて1系統として運用し、全タンクから均等に消費する。供給弁が閉じたまま固着する可能性の方が大量のタンク漏れより大きいと判断している（A17-257）。 */ }
            action <'F-ECL-PCS-N2S-11'> F_ECL_PCS_N2S_11 { doc /* N2タンクの圧力が200（375）psia未満になると、N2レギュレータが制御を失って14.7 psiのキャビンレギュレータの需要を満たせなくなるため、N2供給を喪失とみなす（A17-204A）。 */ }
            action <'F-ECL-PCS-N2S-12'> F_ECL_PCS_N2S_12 { doc /* STS-3・STS-4では、テールを太陽に向けた低温の姿勢でGN2系統の漏れが同じ温度・同じ率で繰り返し現れ、真空ベント管の温度差とヒータのデューティ増加で確かめられたが、圧力とPPO2の制御には影響しなかった（STS-4ミッション報告）。 */ }
        }
        package <'SSD-FD-ECL-PCS-O2S-001'> FN_ECL_PCS_O2S {
            action <'F-ECL-PCS-O2S-01'> F_ECL_PCS_O2S_01 { doc /* PRSDは燃料電池と同じ極低温タンクからPCSへ酸素を供給し、タンクのヒータで811〜875 psiaに保たれた酸素は、電源を失ってもその位置に留まるラッチ式電磁弁のO2供給弁からPCSに入る（訓練マニュアル2.1節）。 */ }
            action <'F-ECL-PCS-O2S-02'> F_ECL_PCS_O2S_02 { doc /* O2供給弁の下流のO2リストリクタは、過大な需要で燃料電池の極低温系の圧力が下がるのを防ぎ、系統1は23.9±1 lb/hrのリストリクタ1個、系統2は12.0±0.5 lb/hrのリストリクタ2個を並列に持つ。フレオンループ1が系統1、ループ2が系統2の酸素を加温する（訓練マニュアル2.1節）。 */ }
            action <'F-ECL-PCS-O2S-03'> F_ECL_PCS_O2S_03 { doc /* L2のATM PRESS CONTROL O2 SYS 1・2 SUPPLYスイッチで供給弁を開くと、酸素は最大約25 lb/hrでリストリクタを流れ、リストリクタはフレオン冷却ループとの熱交換器として酸素を温める（SCOM 2.9節）。 */ }
            action <'F-ECL-PCS-O2S-04'> F_ECL_PCS_O2S_04 { doc /* 酸素配管は576隔壁を貫いて乗員室に入り、逆止弁の下流で系統1・2がO2クロスオーバ管でつながり、クロスオーバマニホールドがLEHレギュレータ、直接O2弁、エアロックのEMU用O2配管に酸素を送る（訓練マニュアル2.1節）。 */ }
            action <'F-ECL-PCS-O2S-05'> F_ECL_PCS_O2S_05 { doc /* O2クロスオーバ弁は電源を失うと閉じる電磁弁で、並列の2個のLEHレギュレータが約840 psiaの酸素を100 psigに下げ、C7の2個のLEHレギュレータ入口弁が使わないときにレギュレータを隔離する（訓練マニュアル2.1節）。 */ }
            action <'F-ECL-PCS-O2S-06'> F_ECL_PCS_O2S_06 { doc /* 打上げ・帰還時は、打上げ・帰還用与圧服（LES）のO2ホースをC6、MO32M、MO69MのLEHクイックディスコネクトにつないでLEH O2弁を開き、C5の直接O2弁はミッドデッキへ約20 lb/hrの酸素を流す（訓練マニュアル2.1節）。 */ }
            action <'F-ECL-PCS-O2S-07'> F_ECL_PCS_O2S_07 { doc /* O2レギュレータ入口弁を開くと、100 psigのO2レギュレータが酸素を100 psiaに下げて逆止弁からO2/N2マニホールドへ送り、レギュレータの逃し弁は245 psigで開いて215 psigで閉じ、乗員室へ逃がす（訓練マニュアル2.1節）。 */ }
            action <'F-ECL-PCS-O2S-08'> F_ECL_PCS_O2S_08 { doc /* エアロックのEMU用O2供給弁は、EMUの補給とISSへの酸素移送のために高圧の酸素をエアロックへ送る（訓練マニュアル2.1節）。 */ }
            action <'F-ECL-PCS-O2S-09'> F_ECL_PCS_O2S_09 { doc /* 非常用O2キットはすべてのオービタから外されて配管はキャップで閉じられ、手動・自動の非常用O2弁は閉じたままとする（訓練マニュアル2.1節）。 */ }
            action <'F-ECL-PCS-O2S-10'> F_ECL_PCS_O2S_10 { doc /* 軌道上の代謝用の酸素は、MO69MのLEH O2 8のクイックディスコネクトに差し込むブリードオリフィスから補給し、オリフィスは4〜5人の乗員で0.24 lbm/hr、6〜7人で0.36 lbm/hrを流す寸法とする（SCOM 2.9節）。 */ }
            action <'F-ECL-PCS-O2S-11'> F_ECL_PCS_O2S_11 { doc /* 打上げ・帰還用ヘルメット（LEH）は軌道上の非常呼吸ではオービタの酸素につなぎ、LEH O2の出口は8個しかないため、8人搭乗の飛行では予備の出口としてT弁を搭載する（1987年の飛行運用マニュアル3.6節）。 */ }
            action <'F-ECL-PCS-O2S-12'> F_ECL_PCS_O2S_12 { doc /* O2クロスオーバ弁が閉じたまま開かない場合は、MO10WとC7の間にO2連絡ホースをつないで故障した弁を迂回し、2系統からの供給を回復するIFMがある（IFM O-12）。 */ }
        }
        package <'SSD-FD-ECL-PCS-OPS-001'> FN_ECL_PCS_OPS {
            action <'F-ECL-PCS-OPS-01'> F_ECL_PCS_OPS_01 { doc /* PCS 1は打上げから飛行の中間点まで、PCS 2は中間点から終わりまで運用し、中間で行う冗長機器の点検で系統を切り替える（A17-251A）。 */ }
            action <'F-ECL-PCS-OPS-02'> F_ECL_PCS_OPS_02 { doc /* 上昇・再突入では両系統の14.7 psiaキャビンレギュレータ入口弁とO2レギュレータ入口弁を閉じ、PCS 1のO2/N2制御弁を開、PCS 2を閉として、漏れが起きても8 psiaまでは補給せず窒素を節約し、酸素はすべてLESヘルメットへ送る。軌道上の構成は飛行1日目に行い、選んだ系統の入口弁を開いてO2/N2制御弁をAUTOにする（訓練マニュアル2.7.1・2.7.2節）。 */ }
            action <'F-ECL-PCS-OPS-03'> F_ECL_PCS_OPS_03 { doc /* O2ブリードオリフィスはPPO2が3.20 psia未満なら飛行1日目の就寝前にLEHのクイックディスコネクトに取り付け、帰還日の軌道離脱準備で外す。キャビンレギュレータを低流量域に保ち、WCSの使用や切替による流量高の誤警報をなくすためである（A17-256）。 */ }
            action <'F-ECL-PCS-OPS-04'> F_ECL_PCS_OPS_04 { doc /* 乗員室のO2濃度は、14.7 psiaの運用では25.9%未満、10.2 psiaの運用では30.0%未満に保つ（A17-254A・B）。 */ }
            action <'F-ECL-PCS-OPS-05'> F_ECL_PCS_OPS_05 { doc /* 10.2 psia運用の減圧はエアロックの減圧弁で行い、10.2 psiaのキャビンレギュレータはないため、乗員室圧とPPO2を手動で管理する（訓練マニュアル2.7.3節）。 */ }
            action <'F-ECL-PCS-OPS-06'> F_ECL_PCS_OPS_06 { doc /* 10.2 psia運用では、乗員室圧を10.0〜10.4 psia、PPO2を2.55〜2.80 psia（指示値）に保つ（A17-301）。 */ }
            action <'F-ECL-PCS-OPS-07'> F_ECL_PCS_OPS_07 { doc /* PPO2センサ3個のうち2個が故障している場合や、N2の総量が計画量、N2レッドライン、10.2から14.7 psiaへの再与圧量の和に満たない場合は、10.2 psiaへの減圧を行わない（A17-302B・C）。 */ }
            action <'F-ECL-PCS-OPS-08'> F_ECL_PCS_OPS_08 { doc /* 軌道離脱の前に乗員室を14.7 psiaへ再与圧し、複数のEVAでは最後のEVAまで10.2 psiaに留める。10.2から14.7 psiaへの再与圧には45 lbの窒素と11 lbの酸素が要る（A17-303・A17-304）。 */ }
            action <'F-ECL-PCS-OPS-09'> F_ECL_PCS_OPS_09 { doc /* 上昇中に隔離できない0.15 psia/minを超える漏れが起きれば最も早く帰還・着陸できる緊急中止とし、0.02〜0.15 psia/minならAOAとする（A17-201A）。 */ }
            action <'F-ECL-PCS-OPS-10'> F_ECL_PCS_OPS_10 { doc /* 8 psia・165分の帰還能力は、LESヘルメットへ乗員1人あたり2.5 lb/hrの酸素を送れないとき、またはN2の総量がN2レッドライン（8 psiaの維持に要る量とタンクの計測誤差・残量の和）を下回ったときに失われる（A17-202）。 */ }
            action <'F-ECL-PCS-OPS-11'> F_ECL_PCS_OPS_11 { doc /* 漏れで消耗品が次の着陸機会まで14.7 psiaと8 psiaでの24時間の延長を賄えない場合や、火災・有害物質の漏洩でLES・QDMを長く着ける場合は、14.7 psiaキャビンレギュレータ入口弁を閉じて乗員室を8 psiaまで下げる（A17-255）。 */ }
            action <'F-ECL-PCS-OPS-12'> F_ECL_PCS_OPS_12 { doc /* 乗員室の気密喪失ではN2が尽きる前に着陸できる最も遅い軌道離脱点火時刻（Tmax）を定め、大気での再与圧までは8 psiaを最低の乗員室圧として保つ（A17-258）。 */ }
        }
        package <'SSD-FD-ECL-PCS-RLF-001'> FN_ECL_PCS_RLF {
            action <'F-ECL-PCS-RLF-01'> F_ECL_PCS_RLF_01 { doc /* 2個の正圧逃し弁は15.5 psidで開き、16.0 psidで全開、15.5 psid未満で閉じる。モータ駆動の逃し隔離弁が直列にあり、逃し弁が開いたまま故障すれば隔離して他方で保護を続ける。逃し弁はWCS区画の後壁の裏にあってペイロードベイへ逃がす（訓練マニュアル2.4節）。 */ }
            action <'F-ECL-PCS-RLF-02'> F_ECL_PCS_RLF_02 { doc /* 各逃し弁はL2のCABIN RELIEFスイッチで制御し、ENABLEで電動弁が開いて乗員室圧を逃し弁に導き、逃し弁の最大流量は16.0 psidで150 lb/hrである（SCOM 2.9節）。 */ }
            action <'F-ECL-PCS-RLF-03'> F_ECL_PCS_RLF_03 { doc /* 2個の負圧逃し弁は外気圧が乗員室圧を0.2 psid上回ると開いて外気を入れ、乗員室がつぶれるのを防ぐ。弁はサイドハッチの下にあり、冗長のシールとして付けたキャップは弁が開くと外れる（訓練マニュアル2.4節）。 */ }
            action <'F-ECL-PCS-RLF-04'> F_ECL_PCS_RLF_04 { doc /* 負圧逃し弁は、漏れの後の再突入の終盤のように乗員室圧が外より低いときに開き、乗員の操作は要らない（SCOM 2.9節）。 */ }
            action <'F-ECL-PCS-RLF-05'> F_ECL_PCS_RLF_05 { doc /* キャビンベント隔離弁とキャビンベント弁は直列のモータ駆動弁で、地上で乗員室をペイロードベイへベントする。ベント管は2 psidで1,080 lb/hrを流せるため打上げ後は決して開けず、軌道投入後のチェックリストで弁の電源を切る（訓練マニュアル2.4節）。 */ }
            action <'F-ECL-PCS-RLF-06'> F_ECL_PCS_RLF_06 { doc /* 打上げ前の気密点検では地上要員が乗員室を16.7 psiaに加圧して35分間圧力の低下がないことを確かめ、その間にベント弁とベント隔離弁を交互に開閉して各弁が圧力を保つことを確かめる（訓練マニュアル2.4節）。 */ }
            action <'F-ECL-PCS-RLF-07'> F_ECL_PCS_RLF_07 { doc /* 両方の正圧逃し弁は、開かない故障が過大圧になるまで検知できないため、すべての飛行段階で有効にしておく（A17-252）。 */ }
            action <'F-ECL-PCS-RLF-08'> F_ECL_PCS_RLF_08 { doc /* ベント弁は打上げ前に閉じ、上昇後に遮断器を開いて着陸後の引渡しまで開いたままにし、誤って弁が開くのを防ぐ（A17-253）。 */ }
            action <'F-ECL-PCS-RLF-09'> F_ECL_PCS_RLF_09 { doc /* 小さな乗員室漏れの隔離手順では、負圧逃し弁のキャップを押し込み、CAB RELIEF A・Bを閉じるなどして漏れ箇所を探し、回復の手順で逃し弁を再び有効にする（MAL ECLS SSR-8）。 */ }
            action <'F-ECL-PCS-RLF-10'> F_ECL_PCS_RLF_10 { doc /* 1979年の飛行運用マニュアルは、正圧逃し弁が15.5 psiで自動的に開き、ベント弁はペイロードベイへ直接ベントし、負圧逃し弁は乗員室圧が外より低いときに乗員室へ流れを入れるとした。 */ }
            action <'F-ECL-PCS-RLF-11'> F_ECL_PCS_RLF_11 { doc /* 1988年のIOA評価は、FMEAが挙げた正圧・負圧逃し弁の取付けフランジの割れという故障モードを、原因（材料欠陥・機械的衝撃・振動）との関係が現実的でないとして解析しなかった（IOA中間報告C.16節）。 */ }
        }
        package <'SSD-FD-ECL-WCS-001'> FN_ECL_WCS {
            action <'F-ECL-WCS-01'> F_ECL_WCS_01 { doc /* WCSは、無重量環境で乗員の生物系廃棄物を収集・処理する統合システムで、ミッドデッキの乗員出入口ハッチのすぐ後方に置かれる。 */ }
            action <'F-ECL-WCS-02'> F_ECL_WCS_02 { doc /* 糞便を収集・貯蔵・乾燥し、尿を処理して廃水タンクへ送り、EVAを行うミッションではエアロックからのEMU凝縮水も処理して廃水タンクへ移す。 */ }
            action <'F-ECL-WCS-03'> F_ECL_WCS_03 { doc /* 便器、小便器、ファンセパレータ、臭気・細菌フィルタ、真空ベントのクイックディスコネクト、制御器で構成される。 */ }
            action <'F-ECL-WCS-04'> F_ECL_WCS_04 { doc /* ファンセパレータは搬送空気から液体を分離し、液体は廃水タンクへ、空気は臭気・細菌フィルタを通って乗員室へ戻る。 */ }
            action <'F-ECL-WCS-05'> F_ECL_WCS_05 { doc /* ファンセパレータの制御にはDC電力、運転にはAC電力を使う。 */ }
            action <'F-ECL-WCS-06'> F_ECL_WCS_06 { doc /* 真空ベント系は、使っていない便器の固形廃棄物の乾燥のほか、ウェットトラッシュ区画の排気と、燃料電池の生成水から水素分離器が除いたH2の船外排出に使われる。 */ }
            action <'F-ECL-WCS-07'> F_ECL_WCS_07 { doc /* 臭気・細菌フィルタはアンモニアを除くよう設計され、EVA後の大気除染では便器を運転して乗員室の空気をフィルタに通す。 */ }
            action <'F-ECL-WCS-08'> F_ECL_WCS_08 { doc /* 廃棄物収集器の圧力を計測し、真空ベント隔離弁が閉で故障した場合は、この圧力で真空ベントのオリフィスからの排気を監視する。 */ }
            action <'F-ECL-WCS-09'> F_ECL_WCS_09 { doc /* WCSの便器や尿収集が使えない場合は、便はアポロ型の便袋、尿は男性用の採尿具（UCD）か女性用の吸収具（UAS）で集める。 */ }
        }
        package <'SSD-FD-ECL-WCS-CMD-001'> FN_ECL_WCS_CMD {
            action <'F-ECL-WCS-CMD-01'> F_ECL_WCS_CMD_01 { doc /* 便器は27×27×29インチで通常のトイレと同様に使い、固形廃棄物を集めて貯蔵する多層の疎水性多孔質バッグライナを1枚持つ（SCOM 2.25節）。 */ }
            action <'F-ECL-WCS-CMD-02'> F_ECL_WCS_CMD_02 { doc /* 便器は使用中は加圧されてファンセパレータが搬送気流を作り、使わないときは減圧されて固形廃棄物を乾燥・不活性化する（SCOM 2.25節）。 */ }
            action <'F-ECL-WCS-CMD-03'> F_ECL_WCS_CMD_03 { doc /* 便と尿の収集モードでは、MODEスイッチをCOMMODE/MANUAL/EMUにしてCOMMODE CONTROLハンドルを引き上げ、デブリスクリーンと流量制限器を通したキャビン空気で約15秒で便器を加圧してから、ハンドルを前へ押してスライド弁を開く（SCOM 2.25節）。 */ }
            action <'F-ECL-WCS-CMD-04'> F_ECL_WCS_CMD_04 { doc /* 糞便は直径4インチの座面開口から、座面下の穴を毎分30 ft³で流れるキャビン空気で引き込まれて多孔質ライナにたまり、空気は疎水性材を通ってファンセパレータへ向かう。疎水性材は自由な液体と細菌が収集器から出るのを防ぐ（SCOM 2.25節）。 */ }
            action <'F-ECL-WCS-CMD-05'> F_ECL_WCS_CMD_05 { doc /* 紙類はすべてWCSのキャニスタバッグに入れて補助ウェットトラッシュ区画に置き、ティッシュは気流を妨げ便器のかさを増すため便器に入れないよう勧められている（SCOM 2.25節）。 */ }
            action <'F-ECL-WCS-CMD-06'> F_ECL_WCS_CMD_06 { doc /* COMMODE CONTROLハンドルをBACK/DOWN位置にするとスライド弁が閉じて便器が減圧される。使用後にハンドルを完全に下げないと、真空ベント弁からキャビン空気が失われる（SCOM 2.25節）。 */ }
            action <'F-ECL-WCS-CMD-07'> F_ECL_WCS_CMD_07 { doc /* 1987年の飛行運用マニュアルは、収集器の必要気流を便器で毎分30 ft³、貯蔵容積を2.4 ft³、真空ベントを通る系の漏れを最大0.0985 lb/人日とし、ゲート弁をスライド式とする。 */ }
            action <'F-ECL-WCS-CMD-08'> F_ECL_WCS_CMD_08 { doc /* 便器の内容物は、トルクレンチ（50 in-lb）で2枚羽根の圧縮器のクランクを回して寄せ、1回目は時計回り、2回目は反時計回りに回し、網が搬送管をふさいでいないことを確かめる（Orbit Operations Checklist）。 */ }
            action <'F-ECL-WCS-CMD-09'> F_ECL_WCS_CMD_09 { doc /* スライド弁が開かない、便器が満杯で空にできない、糞便を保持する気流が得られない、使用時に真空ベントを外せない、糞便の貯蔵容器が破損した、のいずれかで便器を喪失とする。修理できなければ、袋の数に限りがあるため飛行を早期に終える場合がある（A17-353）。 */ }
            action <'F-ECL-WCS-CMD-10'> F_ECL_WCS_CMD_10 { doc /* COMMODE CONTROLハンドルには真空側と乗員室側が同時に開く可動範囲があり、ゆっくりまたは不完全に操作するとキャビン漏れを起こしうる。故障処置手順は連動機構の点検とスライド弁の清掃・点検を示す（MAL ECLS 6.2b）。 */ }
            action <'F-ECL-WCS-CMD-11'> F_ECL_WCS_CMD_11 { doc /* 便器の制御弁が故障した場合は、制御弁の連結部を点検・試験し、必要なら手で操作する（IFMチェックリストW-61）。 */ }
            action <'F-ECL-WCS-CMD-12'> F_ECL_WCS_CMD_12 { doc /* STS-8では、真空にさらした収集器の圧力が通常より高く、1〜2 lb/hrのキャビン漏れに相当した。スライド弁の開閉とゲート弁の清掃では直らず、就寝中は真空ベント弁を閉じて漏れを抑えた。 */ }
        }
        package <'SSD-FD-ECL-WCS-FSP-001'> FN_ECL_WCS_FSP {
            action <'F-ECL-WCS-FSP-01'> F_ECL_WCS_FSP_01 { doc /* 尿と空気の混合物はファンセパレータに軸方向から入り、回転する衝突分離器が液体を回転貯液部の外壁へ飛ばす。遠心力で分離した液体は固定のピトー管から二重の逆止弁を経て廃水タンクへ送られ、各分離器の廃水出口の逆止弁は停止側の分離器を通る逆流を防ぐ（SCOM 2.25節）。 */ }
            action <'F-ECL-WCS-FSP-02'> F_ECL_WCS_FSP_02 { doc /* 空気は回転室から引き出され、臭気・細菌フィルタを通ってキャビン空気と混ざり、乗員室へ戻る（SCOM 2.25節）。 */ }
            action <'F-ECL-WCS-FSP-03'> F_ECL_WCS_FSP_03 { doc /* WMSのすべての気体はファンセパレータから臭気・細菌フィルタへ導かれてキャビン空気と混ざり、フィルタは飛行中に取り外して交換できる（SCOM 2.25節）。 */ }
            action <'F-ECL-WCS-FSP-04'> F_ECL_WCS_FSP_04 { doc /* 臭気・細菌フィルタは長さ10インチ・直径7インチの円筒で、活性炭と、0.45 μmを超える粒子の99.999%を除くろ材を持つ。通常は飛行ごとに地上で交換し、予備1個をミッドデッキ床の区画に積む（1987年の飛行運用マニュアル）。 */ }
            action <'F-ECL-WCS-FSP-05'> F_ECL_WCS_FSP_05 { doc /* 各ファンセパレータは回転室5,800 rpm、1相あたり115±5 Vの三相交流で働き、3 Aの遮断器と248°Fの過熱保護を持つ。臭気・細菌フィルタを通って乗員室へ戻る空気は毎分38 ft³である（1987年の飛行運用マニュアル3.17.4.4節）。 */ }
            action <'F-ECL-WCS-FSP-06'> F_ECL_WCS_FSP_06 { doc /* ファンセパレータ1・2は、パネルMA73CのAC1・AC2 WCS FAN SEP遮断器（計6個）から三相交流を、パネルML86BのMNA・MNB WCS CNTLR遮断器（2個）から制御用の直流を受ける（IFMチェックリストW-61）。 */ }
            action <'F-ECL-WCS-FSP-07'> F_ECL_WCS_FSP_07 { doc /* 交流の1相を失うと、WCSのファンセパレータは2相運転となり気流が低下する。EDO WCSの尿ファン・分離器は直流モータ（制御器の内部で交流を直流に変換）で、1相の喪失で尿ファンまたは分離器を失う（MAL EPS SSR-111）。 */ }
            action <'F-ECL-WCS-FSP-08'> F_ECL_WCS_FSP_08 { doc /* 直流または交流の電力を確立できないか、分離器があふれて回復できない場合は、WCSのセパレータを喪失とする。セパレータの主な機能は廃水をキャビン大気から分けることである（A17-351）。 */ }
            action <'F-ECL-WCS-FSP-09'> F_ECL_WCS_FSP_09 { doc /* 両方のファンセパレータがあふれて止まった場合に限り、廃水ダンプ系を使って分離器の出口を真空にさらし、出口圧力を下げて回復させる（IFMチェックリストW-70）。 */ }
            action <'F-ECL-WCS-FSP-10'> F_ECL_WCS_FSP_10 { doc /* 臭気・細菌フィルタはWCSを通る気流からアンモニアを除くよう設計され、EVA後の大気除染では便器を運転してフィルタに最大の気流を流し、乗員室の空気はおよそ60分でフィルタを1巡する（A15-203）。 */ }
            action <'F-ECL-WCS-FSP-11'> F_ECL_WCS_FSP_11 { doc /* 火災の鎮火後は、WCSの活性炭フィルタ、ATCO、LiOHキャニスタで乗員室の大気を浄化する（SCOM 6.8節）。 */ }
            action <'F-ECL-WCS-FSP-12'> F_ECL_WCS_FSP_12 { doc /* STS-65（EDO WCS）では、ファンセパレータ1が運転中に異音と臭気を出し、回転数が通常に達しなかったためファンセパレータ2に切り替えた。着陸後には、水タンクの再加圧で廃水タンクの液体が逆止弁を通って逆流し、ミッドデッキにあふれた。 */ }
        }
        package <'SSD-FD-ECL-WCS-OPS-001'> FN_ECL_WCS_OPS {
            action <'F-ECL-WCS-OPS-01'> F_ECL_WCS_OPS_01 { doc /* WCSの制御器はVACUUM VALVE、FAN SEP選択スイッチ、MODEスイッチ、ファンセパレータのバイパススイッチ、COMMODE CONTROLハンドルである。MODEスイッチとハンドルは機械的に連動して望ましくない構成を防ぎ、ほかの制御器は独立に働く（SCOM 2.25節）。 */ }
            action <'F-ECL-WCS-OPS-02'> F_ECL_WCS_OPS_02 { doc /* 不使用時は、COMMODE CONTROLハンドルをOFF（後ろ・下）、FAN SEPを1、MODEをOFF（尿収集弁を閉）、両方のバイパススイッチをOFF、VACUUM VALVEをOPENとし、便器を真空にさらして廃棄物を乾燥・消毒する（1987年の飛行運用マニュアル）。 */ }
            action <'F-ECL-WCS-OPS-03'> F_ECL_WCS_OPS_03 { doc /* レバーロック式のFAN SEP 1・2 BYPASSスイッチは、FAN SEPまたはMODEスイッチ内のリミットスイッチの故障を手動で迂回し、対応するリレーに直流を与えてファンセパレータに交流を供給する。両方を同時にONにせず、使う前にFAN SEPとホースブロックを同じ分離器に合わせる（SCOM 2.25節）。 */ }
            action <'F-ECL-WCS-OPS-04'> F_ECL_WCS_OPS_04 { doc /* ファンセパレータの切替では、ホースをクレードルに収めてFAN SEP選択スイッチをOFFにし、ホースブロックを切替先に合わせてから選択スイッチを切り替え、切替先の分離器が30秒回った後に通常どおり使う（Orbit Operations Checklist）。 */ }
            action <'F-ECL-WCS-OPS-05'> F_ECL_WCS_OPS_05 { doc /* 乗員室の再与圧中（N2の大流量でO2濃度が下がりうる）と、EMUの排水中（分離器の最大廃水流量0.09 lbm/sを超えてあふれる）はWCSを使わない（A17-401）。 */ }
            action <'F-ECL-WCS-OPS-06'> F_ECL_WCS_OPS_06 { doc /* インラインフィルタからWCS/廃水系の境界のQDまでの尿配管に修理できない漏れがある場合は、乗員室に水が漏れないよう、WCSで液体を運ばない（A17-402）。 */ }
            action <'F-ECL-WCS-OPS-07'> F_ECL_WCS_OPS_07 { doc /* 便器を失った場合はアポロ型の便袋で、尿収集を失った場合は男性用の採尿具（UCD）か女性用の吸収具（UAS）で代替する。標準の搭載量は便袋40枚、UCD 58個・UAS 36個で、少なくともPLS＋2日分に当たる（A17-403・404）。 */ }
            action <'F-ECL-WCS-OPS-08'> F_ECL_WCS_OPS_08 { doc /* 隔離弁が閉で故障した場合は、収集器圧力で真空ベントのオリフィスからの排気を監視する。真空ベント機能を失った場合は、WCSの真空弁を再突入まで開いたままにし、非常時の真空ベント運用のIFMで機能を回復するまで便器の使用を止める。真空弁を閉じると真空ベント管内に数分で可燃性の混合気ができるため、閉じてはならない（A17-405）。 */ }
            action <'F-ECL-WCS-OPS-09'> F_ECL_WCS_OPS_09 { doc /* 飛行継続の判断（A17-1001）では、WCSがない場合は少なくともPLS＋2日（3日）分の袋が要り、飛行の終了時期は排泄の頻度、乗員の人数・性別、代替の収集具の数で決まる。 */ }
            action <'F-ECL-WCS-OPS-10'> F_ECL_WCS_OPS_10 { doc /* AC1母線を失った場合はWCSのファンセパレータ1が止まるため、ホースをクレードルに収め、ホースブロックとFAN SEP選択スイッチをファンセパレータ2に切り替える（MAL EPS SSR-110）。 */ }
            action <'F-ECL-WCS-OPS-11'> F_ECL_WCS_OPS_11 { doc /* 小さなキャビン漏れの切り分けでは、MCCの指示でCOMMODE CNTLを下げ、WCSのVAC VLVと真空ベント隔離弁を閉じ、小便器のホースとホースブロックを外してEMU排出の中央管をテープでふさぐ（MAL ECLS SSR-8）。 */ }
            action <'F-ECL-WCS-OPS-12'> F_ECL_WCS_OPS_12 { doc /* 使用後はウェットワイプでWCSを清掃し、1日1回は消毒用ワイプで消毒する。小便器のファンネルも毎日消毒できる（SCOM 2.25節）。 */ }
        }
        package <'SSD-FD-ECL-WCS-URN-001'> FN_ECL_WCS_URN {
            action <'F-ECL-WCS-URN-01'> F_ECL_WCS_URN_01 { doc /* 小便器はホースに取り付けたファンネルで、男女とも使え、液体廃棄物を集めて廃水タンクへ運ぶ。液体の搬送気流はファンセパレータが作る（SCOM 2.25節）。 */ }
            action <'F-ECL-WCS-URN-02'> F_ECL_WCS_URN_02 { doc /* MODEスイッチがAUTOのとき、小便器のホースをクレードルから外すと選んだファンセパレータが働き、小便器を通して毎分10 ft³以上、コーヒー缶（紙類の収集容器）を通して毎分30 ft³のキャビン空気を引く（SCOM 2.25節）。 */ }
            action <'F-ECL-WCS-URN-03'> F_ECL_WCS_URN_03 { doc /* 1987年の飛行運用マニュアルは、無重量で液体を運ぶために気流を用い、尿の最大流量を0.09 lb/sとし、各乗員に個人用のファンネル（男性用は円錐形、女性用は細長い形）を用意するとする。 */ }
            action <'F-ECL-WCS-URN-04'> F_ECL_WCS_URN_04 { doc /* ファンネルの根元には、気流中の異物を捕らえる円錐形の使い捨てプレフィルタ（40メッシュのステンレス網）があり、少なくとも1日1回交換する（1987年の飛行運用マニュアル）。 */ }
            action <'F-ECL-WCS-URN-05'> F_ECL_WCS_URN_05 { doc /* EMU凝縮水の排出モードでは、MODEスイッチにガードをかぶせて停止を防ぎ、分離器があふれるおそれがあるため排出中は小便器を使わない。EMUの廃水はEVAを行う飛行だけエアロックの廃水弁から排出し、ほかは尿収集モードと同じである（SCOM 2.25節）。 */ }
            action <'F-ECL-WCS-URN-06'> F_ECL_WCS_URN_06 { doc /* EMU排出の配管はホースブロックの中央の管につながり、故障処置手順（ECLS 6.2b）はキャビン漏れの切り分けでこの管をふさぐ手順を示す。 */ }
            action <'F-ECL-WCS-URN-07'> F_ECL_WCS_URN_07 { doc /* 1987年の飛行運用マニュアルは、尿の流量を公称0.05 lb/s・最大0.09 lb/s、1回の最大量を1.8 lb、水分の公称値を3.31 lb/人日とする。 */ }
            action <'F-ECL-WCS-URN-08'> F_ECL_WCS_URN_08 { doc /* 配管の閉塞・漏れや両方の分離器の喪失などで、いずれの経路でも尿を廃水系へ運べない場合は、WCSの尿収集を喪失とする（A17-352）。 */ }
            action <'F-ECL-WCS-URN-09'> F_ECL_WCS_URN_09 { doc /* WCSの清掃では、プレフィルタを点検して1日1回または必要に応じて交換し、ホースブロックから外したホースのスクリーンを点検・清掃する（Orbit Operations Checklist）。 */ }
            action <'F-ECL-WCS-URN-10'> F_ECL_WCS_URN_10 { doc /* 尿前処理のため、プレフィルタハウジングとホースブロック延長の間にOxoneホース区間（OHS）を取り付け、定期的に交換する（Orbit Operations Checklist）。 */ }
            action <'F-ECL-WCS-URN-11'> F_ECL_WCS_URN_11 { doc /* STS-108では、STS-97のWCSで見つかった想定外の析出物に対処するため、アルカリ性と酸性の尿の固形物の生成を防ぐよう再設計したシャトル尿前処理組立（SUPA）を搭載した。 */ }
            action <'F-ECL-WCS-URN-12'> F_ECL_WCS_URN_12 { doc /* STS-4では小便器の気流が飛行中に低下し、プレフィルタを1回清掃すると回復した。飛行後の点検でプレフィルタの30%が目詰まりしていた。 */ }
        }
        package <'SSD-FD-ECL-WCS-VAC-001'> FN_ECL_WCS_VAC {
            action <'F-ECL-WCS-VAC-01'> F_ECL_WCS_VAC_01 { doc /* 真空ベント系はオービタに制御された船外への抽気の経路を与え、真空ベント管は内径1.93インチで、乗員室内から船外へ通じる（訓練マニュアル5.4節）。 */ }
            action <'F-ECL-WCS-VAC-02'> F_ECL_WCS_VAC_02 { doc /* 真空ベント隔離弁は管の乗員室内の部分を隔離する。閉じても弁板のオリフィスが14.7 psiaで3.0±0.25 lb/hrを流し、燃料電池の水素分離器が除いたH2を船外へ排出し続ける（訓練マニュアル5.4節）。 */ }
            action <'F-ECL-WCS-VAC-03'> F_ECL_WCS_VAC_03 { doc /* 隔離弁は上昇・再突入中は閉じ、軌道上で開くと管とノズルのヒータが働いて管内の水蒸気の凍結を防ぐ。WCSは真空ベント管で運転に必要な真空を得る（訓練マニュアル5.4節）。 */ }
            action <'F-ECL-WCS-VAC-04'> F_ECL_WCS_VAC_04 { doc /* 打上げ・再突入ではWCSのVACUUM VALVEを閉じ、軌道上でWCSを使わないときは開いて便器を船外にさらし、固形廃棄物を乾燥させるとともに補助ウェットトラッシュとvolume Fのウェットトラッシュ区画を排気する。便器のライナは気体を通し、自由な液体は通さない（SCOM 2.25節）。 */ }
            action <'F-ECL-WCS-VAC-05'> F_ECL_WCS_VAC_05 { doc /* 真空ベント管はWCSの3方ボール弁で分岐し、便器の下流の手動弁でWCSを真空ベント系から隔離できる。WCSの故障でキャビン漏れが生じた場合などに使う（SCOM 2.25節）。 */ }
            action <'F-ECL-WCS-VAC-06'> F_ECL_WCS_VAC_06 { doc /* 隔離弁はパネルML31CのWASTE H2O VACUUM VENT ISOL VLV CONTROLスイッチで開閉し、電力は同じパネルのVACUUM VENT ISOL VLV BUS SELECTスイッチでMNAまたはMNBから受け、電力を失うと閉じる。弁が開かなくても弁板の小穴から排気は続く（SCOM 2.25節）。 */ }
            action <'F-ECL-WCS-VAC-07'> F_ECL_WCS_VAC_07 { doc /* 真空ベント管のサーモスタット制御のA・BヒータはパネルML86BのH2O LINE HTR A・B遮断器から給電され、ノズルのヒータはパネルML31CのWASTE H2O VACUUM VENT NOZ HTRスイッチで入切りする（SCOM 2.25節）。 */ }
            action <'F-ECL-WCS-VAC-08'> F_ECL_WCS_VAC_08 { doc /* ウェットトラッシュ区画の空気は約3 lb/dayで船外へ排気され、そのためにはWCSの真空ベント弁を開いておく必要がある。区画には嘔吐袋、採尿具、便袋、使用済みの臭気・細菌フィルタなどを入れる（SCOM 2.24節）。 */ }
            action <'F-ECL-WCS-VAC-09'> F_ECL_WCS_VAC_09 { doc /* 真空ベントの主な機能は、燃料電池の生成水から除いたH2（約9.75×10⁻⁵ lb/hr）などの気体廃棄物の船外排出と、EVAのためのエアロックの減圧である。隔離弁が閉で故障し、便器不使用時に収集器圧力が1.0 psiaを超えると真空ベント機能の喪失とする（A17-354）。 */ }
            action <'F-ECL-WCS-VAC-10'> F_ECL_WCS_VAC_10 { doc /* 真空ベント系が故障した場合は、WCSのボール弁と真空ベント弁の間にある真空ベントQDから非常用廃水クロスタイQDへ移送ホースをつなぎ、廃水ダンプ管から排気する（SCOM 2.25節）。 */ }
            action <'F-ECL-WCS-VAC-11'> F_ECL_WCS_VAC_11 { doc /* 隔離弁の閉固着とオリフィスの閉塞に対しては、真空ベント系を廃水ダンプ系に接続して、水素分離器のH2とウェットトラッシュの臭気を船外へ排出するIFM手順があり、完了後5分までは便器を使わない（IFMチェックリストW-53）。 */ }
            action <'F-ECL-WCS-VAC-12'> F_ECL_WCS_VAC_12 { doc /* IOAのFMEA/CIL評価（1988年）は、真空ベントダンプ管の閉塞やヒータの喪失で管内に水素と酸素の危険な混合気が生じうるとして、生命・機体の喪失につながりうる状態とみなした。 */ }
        }
        package <'SSD-FD-EPS-001'> FN_EPS {
            action <'F-EPS-01'> F_EPS_01 { doc /* EPSは、反応剤貯蔵・分配（PRSD）、燃料電池発電装置、電力分配・制御（EPDC）の3サブシステムから成る。 */ }
            action <'F-EPS-02'> F_EPS_02 { doc /* PRSDは極低温の水素と酸素を貯蔵して3基の燃料電池へ供給し、あわせて乗員室の与圧用に極低温酸素をECLSSへ供給する。 */ }
            action <'F-EPS-03'> F_EPS_03 { doc /* 3基の燃料電池は、打上げから着陸後の滑走終了まで、機体の28 V直流電力のすべてを発電する。 */ }
            action <'F-EPS-04'> F_EPS_04 { doc /* 3基の燃料電池は独立した電源として動作し、それぞれが分離された28 V直流母線に同時に給電する。 */ }
            action <'F-EPS-05'> F_EPS_05 { doc /* 基本構成での3基の燃料電池の能力は、合計で平均14 kW、ピーク最大24 kWである（1975年の設計論文）。 */ }
        }
        package <'SSD-FD-EPS-AC-001'> FN_EPS_AC {
            action <'F-EPS-AC-01'> F_EPS_AC_01 { doc /* 各主直流母線は3台の単相静止形インバータに給電し、これが1本の3相交流母線を構成する。 */ }
            action <'F-EPS-AC-02'> F_EPS_AC_02 { doc /* 9台のインバータで117 V（実効値）・400 Hzの交流を作り、交流母線AC1・AC2・AC3へ配電する。 */ }
            action <'F-EPS-AC-03'> F_EPS_AC_03 { doc /* インバータは前部アビオニクスベイにあり、出力は117 V（実効値）・400 Hzである。 */ }
            action <'F-EPS-AC-04'> F_EPS_AC_04 { doc /* 交流母線センサは過電圧・不足電圧・過負荷を監視し、自動トリップ位置では異常のあるインバータを母線から切り離す。 */ }
            action <'F-EPS-AC-05'> F_EPS_AC_05 { doc /* 10台のモータ制御組立が、ベントドア、ペイロードベイドア、RCS/OMSの電動弁などの交流モータへ電力を供給する。 */ }
        }
        package <'SSD-FD-EPS-DC-001'> FN_EPS_DC {
            action <'F-EPS-DC-01'> F_EPS_DC_01 { doc /* 3本の主直流母線（MNA・MNB・MNC）が機体の直流負荷の主電源となり、前部・中部・後部へ配電する。 */ }
            action <'F-EPS-DC-02'> F_EPS_DC_02 { doc /* このほか、必須負荷用の必須母線3本、乗員操作用の制御電力のみを供給する制御母線9本、地上作業専用の予備母線2本がある。 */ }
            action <'F-EPS-DC-03'> F_EPS_DC_03 { doc /* 電力は分配組立、電力制御組立、負荷制御組立、モータ制御組立で制御・分配される。 */ }
            action <'F-EPS-DC-04'> F_EPS_DC_04 { doc /* 遠隔電力制御器（RPC）は3〜20 Aの負荷用の半導体スイッチで、定格の150%で電流を制限し、3秒以内に遮断する。 */ }
            action <'F-EPS-DC-05'> F_EPS_DC_05 { doc /* 主母線同士はバスタイで接続でき、主母線電圧が26.4 V以下になるとC/W警報が点灯する。 */ }
            action <'F-EPS-DC-06'> F_EPS_DC_06 { doc /* ペイロード用には主ペイロード母線（燃料電池3または主母線B・Cから給電）、後部ペイロード母線、補助ペイロード母線がある。 */ }
            action <'F-EPS-DC-07'> F_EPS_DC_07 { doc /* 中胴の電気部品はフレオン21ループのコールドプレートで、前部アビオニクスベイ1〜3の電力・負荷・モータ制御組立とインバータは水冷却ループのコールドプレートで冷却され、インバータ配電組立は空冷である。 */ }
        }
        package <'SSD-FD-EPS-FCP-001'> FN_EPS_FCP {
            action <'F-EPS-FCP-01'> F_EPS_FCP_01 { doc /* 3基の燃料電池は再使用・再起動が可能で、中胴前部のペイロードベイの下に置かれる。 */ }
            action <'F-EPS-FCP-02'> F_EPS_FCP_02 { doc /* 3基は独立した電源として動作し、それぞれが分離された28 V直流母線に同時に給電する。 */ }
            action <'F-EPS-FCP-03'> F_EPS_FCP_03 { doc /* 発電部は3つのサブスタックに収めた96セルから成り、電解質は水酸化カリウム水溶液である。 */ }
            action <'F-EPS-FCP-04'> F_EPS_FCP_04 { doc /* 補機部は反応剤流量を監視し、排熱と生成水を取り除き、スタック温度を制御する。 */ }
            action <'F-EPS-FCP-05'> F_EPS_FCP_05 { doc /* 冷却材がスタックの排熱を燃料電池熱交換器経由でフレオン21冷却ループへ移し、スタックを約200°Fに保つ。 */ }
            action <'F-EPS-FCP-06'> F_EPS_FCP_06 { doc /* 反応剤中の不活性ガスを除くため、96時間を超えない間隔で計画的にパージする。 */ }
            action <'F-EPS-FCP-07'> F_EPS_FCP_07 { doc /* 1基の能力は通常時の最大連続10 kW・非通常時（1基以上の燃料電池が故障したとき）の連続12 kW・10分間の最大16 kWで、オービタの軌道上の平均消費電力は約14 kWである。 */ }
            action <'F-EPS-FCP-08'> F_EPS_FCP_08 { doc /* オービタには予備バッテリがなく、3基の燃料電池が機上電力のすべてを生み出す。 */ }
        }
        package <'SSD-FD-EPS-PRSD-001'> FN_EPS_PRSD {
            action <'F-EPS-PRSD-01'> F_EPS_PRSD_01 { doc /* PRSDは極低温の水素と酸素を超臨界状態で貯蔵して3基の燃料電池へ供給し、あわせて乗員室与圧用の酸素をECLSSへ供給する。 */ }
            action <'F-EPS-PRSD-02'> F_EPS_PRSD_02 { doc /* 液体酸素は−285°F、液体水素は−420°Fで貯蔵される。 */ }
            action <'F-EPS-PRSD-03'> F_EPS_PRSD_03 { doc /* タンクは真空断熱層を持つ二重壁の球形で、消費に伴う圧力低下をヒータで補い、残量を計測できる。 */ }
            action <'F-EPS-PRSD-04'> F_EPS_PRSD_04 { doc /* タンクは水素1基と酸素1基を1セットとし、ミッションに応じて最大5セットを中胴のペイロードベイ内張の下に搭載する。 */ }
            action <'F-EPS-PRSD-05'> F_EPS_PRSD_05 { doc /* 酸素タンクは1基あたり781 lb、水素タンクは92 lbを貯蔵する。 */ }
            action <'F-EPS-PRSD-06'> F_EPS_PRSD_06 { doc /* 軌道上ではヒータ制御の圧力設定が高いタンク3・4・5が燃料電池へ供給し、再突入ではタンク1・2が供給する。 */ }
            action <'F-EPS-PRSD-07'> F_EPS_PRSD_07 { doc /* 弁モジュール内の逆止弁が、1基のタンクが漏れても反応剤全体を失わないようにする。 */ }
            action <'F-EPS-PRSD-08'> F_EPS_PRSD_08 { doc /* STS-50では、通常の4セットに加えて4セットのタンクを積むEDO極低温パレットが初めて飛行した。 */ }
        }
        package <'SSD-FD-EVA-001'> FN_EVA {
            action <'F-EVA-01'> F_EVA_01 { doc /* EVAは乗員が与圧キャビンの保護環境を出て、宇宙服で宇宙の真空へ出る活動で、2回をペイロード用、1回をオービタの非常時用に確保する。 */ }
            action <'F-EVA-02'> F_EVA_02 { doc /* 各ミッションで宇宙服を2着搭載し、消耗品は2人・6時間のEVA 3回分を用意する。 */ }
            action <'F-EVA-03'> F_EVA_03 { doc /* EVAにはエアロックを使い、乗員が入った状態でエアロックを減圧して真空へ出る。これにより乗員室全体ではなく小さな容積だけを減圧できる。 */ }
            action <'F-EVA-04'> F_EVA_04 { doc /* EVAには、計画、計画外、非常の3つの区分がある。 */ }
            action <'F-EVA-05'> F_EVA_05 { doc /* EMUは、地球周回軌道でEVAを行う乗員に環境防護・可動性・生命維持・通信を提供する独立した人型のシステムである。 */ }
            action <'F-EVA-06'> F_EVA_06 { doc /* EMUは、脱出15分、有効作業6時間、進入15分、予備30分の、合計最大7時間のEVAに対応するよう設計されている。 */ }
            action <'F-EVA-07'> F_EVA_07 { doc /* 宇宙服組立（SSA）は胴体・手足・頭部を覆う人型の圧力容器で、服圧の保持、液冷の分配、酸素換気、EMU無線による心電図のダウンリンクなどを行う。 */ }
        }
        package <'SSD-FD-EVA-CHK-001'> FN_EVA_CHK {
            action <'F-EVA-CHK-01'> F_EVA_CHK_01 { doc /* EMU点検は着用前にEMUの各系を事前に点検するもので、続くミッドデッキ準備と着用準備でEMUと付属品を乗員が着用できる構成にする。 */ }
            action <'F-EVA-CHK-02'> F_EVA_CHK_02 { doc /* EMU点検はエアロックの右舷・左舷の2着を同時に行う手順で、3着目は点検中のEMU交換の後に同じ手順で点検し、そのときはEMU間の通信を確かめるため点検済みの1着をエアロックに残す。 */ }
            action <'F-EVA-CHK-03'> F_EVA_CHK_03 { doc /* エアロックの電源を入れるときはEMUを電池電源にしておき、EMUの電源を入れ直すたびにPWR RESTARTの表示とBITE灯が点くが、表示とトーンの試験はコールドリスタートのときにだけ行われる。 */ }
            action <'F-EVA-CHK-04'> F_EVA_CHK_04 { doc /* 主調圧器の点検ではEMUを服圧4.2〜4.4 psidで安定させて自動の漏れ点検を行い、LEAKAGE HIの表示（ΔP 0.3 psi超）が出た場合はFAILED LEAK CHECK（14.7/10.2 PSI）のキューカードに移る。 */ }
            action <'F-EVA-CHK-05'> F_EVA_CHK_05 { doc /* ファン・ポンプの点検では、O2 ACTをOFFにしたままのファンの運転を約2分以内にとどめ、LCVGに冷却水が流れて水温が下がることを確かめる。 */ }
            action <'F-EVA-CHK-06'> F_EVA_CHK_06 { doc /* SOPの点検では中間段のゲージで第1段の調圧を確かめ、運用飛行規則は第1段の調圧を600 psig未満に保てない場合を、計画・計画外EVAではEMUのNO-GO（非常時EVAではSCUでの救援待機に限りGO）とする。 */ }
            action <'F-EVA-CHK-07'> F_EVA_CHK_07 { doc /* SAFERの点検では自己試験で24個のスラスタの作動音を数え、GN2・電力の残量と電池電圧・製造番号をMCCに報告し、電源を入れている時間は約1分が望ましい。 */ }
            action <'F-EVA-CHK-08'> F_EVA_CHK_08 { doc /* REBAで動く12 Vの機器（手袋ヒータ・EMU TV）の点検では、電池の消耗と発熱を避けるため、指先に熱を感じたら手袋ヒータを切る。 */ }
            action <'F-EVA-CHK-09'> F_EVA_CHK_09 { doc /* ペイロードベイの投光器はEMUの熱的な限界を超えるため、EVA乗員が近くで作業する場合はミッドデッキ準備の時点で消し（冷えるまで最長6時間）、無線ビデオのヒータは映像の品質のためEVAの4時間以上前に入れる。 */ }
            action <'F-EVA-CHK-10'> F_EVA_CHK_10 { doc /* EVA乗員はEMUに刺激物を持ち込まないよう、EVA当日の前から衛生用品・炭化水素系製品の使用を控え、EMUに入れてよい品目は承認済み非EMU機器の表（4-11）で定める。 */ }
            action <'F-EVA-CHK-11'> F_EVA_CHK_11 { doc /* 着用後の窒素パージの時間はキャビン圧10.2 psiで8分、14.7 psiで12分とし、パージと前呼吸の間は手足を時々動かして冷やしすぎないようにする。 */ }
            action <'F-EVA-CHK-12'> F_EVA_CHK_12 { doc /* 10.2 psiキャビンの前呼吸は、45分以上を12.5 psi未満への減圧の前に行う途切れのない初期前呼吸と、EVA直前のEMU内の途切れのない最終前呼吸（10.2 psiで24時間なら40分、12時間なら75分）から成る。 */ }
            action <'F-EVA-CHK-13'> F_EVA_CHK_13 { doc /* EMU STATUSの表は服圧4.2〜4.4 psid（減圧後は4.2〜5.5 psid）、O2圧150〜950 psia、SOP圧5,410〜6,800 psia、CO2 0.2〜4.0 mmHgなどの正常値を示し、EMUデータのダウンリンクがないときは最初の6.5時間は1時間ごと、その後は10分ごとに状態をMCCへ報告する。 */ }
        }
        package <'SSD-FD-EVA-DPR-001'> FN_EVA_DPR {
            action <'F-EVA-DPR-01'> F_EVA_DPR_01 { doc /* 外部エアロックの空の容積は228 ft³で、EMU 2着を入れて減圧する容積は208 ft³である。 */ }
            action <'F-EVA-DPR-02'> F_EVA_DPR_02 { doc /* 減圧は前呼吸の完了後に始め、減圧中は服圧計が5.5を超えないことを見て、超えた場合は減圧を止めてMCCに確かめる。 */ }
            action <'F-EVA-DPR-03'> F_EVA_DPR_03 { doc /* エアロックを5.0 psiで止めてEMUの漏れ点検を行い、LEAKAGE HIの表示が出た場合はキューカード裏面のFAILED LEAK CHECK（5 PSI）へ移り、合格すればO2 ACTをEVAにしてから0 psiまで減圧する。 */ }
            action <'F-EVA-DPR-04'> F_EVA_DPR_04 { doc /* エアロックに戻った乗員はSCUをつないで昇華器の水を切り、水を切って2分経つまでは外部ハッチを閉じない。 */ }
            action <'F-EVA-DPR-05'> F_EVA_DPR_05 { doc /* 再与圧は内側ハッチの均圧弁でエアロックを5.0 psiまで戻して止め、2分間のΔPが0.1 psi以下であることでエアロックの気密を確かめてから、乗員室の圧力に合わせる。 */ }
            action <'F-EVA-DPR-06'> F_EVA_DPR_06 { doc /* SOPで呼吸している場合は再与圧の間もO2 ACTをEVAのままにし、減圧症の症状があればO2 ACTをPRESSのままにし、カフ1の症状が再与圧で消えた場合はカフ2として報告する。 */ }
            action <'F-EVA-DPR-07'> F_EVA_DPR_07 { doc /* トンネルアダプタ構成の減圧（25分）では、5 psiでの漏れ点検の後に後部モジュールの気密をMCCに確かめ、再与圧での気密の確認は4分間とする。 */ }
            action <'F-EVA-DPR-08'> F_EVA_DPR_08 { doc /* エアロックを乗員室の気密を保ったまま減圧・再与圧できなければEVA能力の喪失とし、いずれかのハッチの漏れによるエアロック圧の低下が0.2 psi/minを超えれば喪失とする。 */ }
            action <'F-EVA-DPR-09'> F_EVA_DPR_09 { doc /* EMUの正圧逃し弁が閉じたまま開かない故障は減圧中にだけ検知でき、弁を開けられなければ過加圧に対してフェイルセーフでないため、EMUはEVAにNO-GOとする。 */ }
            action <'F-EVA-DPR-10'> F_EVA_DPR_10 { doc /* EVA中は外部エアロックの上部・後部ハッチの保温カバーを閉じておき、開いた場合は乗員が次の都合のよい機会に戻って閉じる。真空中に保温カバーが開いているとエアロック内の水配管が凍るおそれがあるためである。 */ }
            action <'F-EVA-DPR-11'> F_EVA_DPR_11 { doc /* STS-125の2回目のEVAでは減圧弁の蓋を付けたまま減圧を始めたため、10.2から7 psiaへの減圧率が0.44 psia/minと遅く（通常は10.2から5 psiaで2.8 psia/min）、乗員が蓋を外して通常どおり減圧した。 */ }
            action <'F-EVA-DPR-12'> F_EVA_DPR_12 { doc /* STS-114では、EVA 2の後にエアロックを再び減圧して乗員が入る際、外部ハッチの右舷均圧弁がEMER位置で流れなくなり、左舷の均圧弁で減圧した（IFA STS-114-V-15）。 */ }
        }
        package <'SSD-FD-EVA-EMG-001'> FN_EVA_EMG {
            action <'F-EVA-EMG-01'> F_EVA_EMG_01 { doc /* 非常時EVAは計画外だがオービタと乗員の安全な帰還に必要なEVAで、オービタの機器が故障したときに行い、手順・工具・作業位置はどのミッションでも練習できるよう定めてある。 */ }
            action <'F-EVA-EMG-02'> F_EVA_EMG_02 { doc /* 想定するオービタの故障は放熱器アクチュエータ、ペイロードベイドア、隔壁ラッチ、中心線ラッチ、エアロックハッチ、RMS、隔壁カメラ、Ku帯アンテナ、ET扉で、故障ごとの処置（切り離し、ウインチ、ラッチ工具、手動操作など）を表に定める。 */ }
            action <'F-EVA-EMG-03'> F_EVA_EMG_03 { doc /* 着用中の真空中の給水は非常時EVAを行う場合に限る手順で、エアロックに入って外部ハッチを閉じ、SCUを通してEMUに給水する。 */ }
            action <'F-EVA-EMG-04'> F_EVA_EMG_04 { doc /* 着用中に電池を交換してもEMUが計算するTIME EV・TIME LFはリセットされず、リセットにはコールドリスタートが要る。 */ }
            action <'F-EVA-EMG-05'> F_EVA_EMG_05 { doc /* EMUのコールドリスタートはファンとO2を止めるため、エアロック圧8.0 psi以上でだけ行い、できるだけ速く行う。 */ }
            action <'F-EVA-EMG-06'> F_EVA_EMG_06 { doc /* 主母線Aを失ってEMU 2の給水・廃水弁が動かなくなった場合は、EMU 2をSCU 1につないで給水・再充填を行うことがある。 */ }
            action <'F-EVA-EMG-07'> F_EVA_EMG_07 { doc /* EMUの化学汚染が目視または検知器で確かめられた場合はヒドラジンの汚染除去の手順を行い、数の限られた検知管（Draeger）は汚染が疑われる場合にだけ使う。 */ }
            action <'F-EVA-EMG-08'> F_EVA_EMG_08 { doc /* 汚染が確かめられた場合は進入からEMUの脱衣までに1時間55分（ISSのスラスタによる汚染は2時間10分）、疑いの場合は55分（同1時間10分）のEMU消耗品を残すようEVA作業を後回しにし、SCUにつないだベークアウトはヘルメットのパージ弁を開ければLiOHを消費しない。 */ }
            action <'F-EVA-EMG-09'> F_EVA_EMG_09 { doc /* 減圧症治療アダプタ（BTA）は、減圧症にかかったEVA乗員の処置のためEMUを高圧治療室に変え、キャビン圧より8.0 psid高く加圧する。 */ }
            action <'F-EVA-EMG-10'> F_EVA_EMG_10 { doc /* BTAによる処置はカフ2・3では6 psidから始めて症状が消えなければ8 psidに上げ、カフ4では8 psidから始め、処置の時間と圧力の変更は地上の医師（Surgeon）が決める。 */ }
            action <'F-EVA-EMG-11'> F_EVA_EMG_11 { doc /* カフ4の症状は医学的緊急であるII型の減圧症によることがあり、急いで再与圧することが重要なため、患者1人だけの再与圧になることがある。 */ }
            action <'F-EVA-EMG-12'> F_EVA_EMG_12 { doc /* SAFERはEMUのPLSSの下に付ける単一系統の推進式背負い装置で、ISSなど大きな構造物にドッキング中でオービタが救出できない状況で離れたEVA乗員が自力で戻るためのもので、電池は最低13分、24個のGN2スラスタで6自由度の制御を行う。 */ }
            action <'F-EVA-EMG-13'> F_EVA_EMG_13 { doc /* EVA中のオービタは乗員のいる区域に応じてRCSジェットの禁止や駆動器の電源断などを構成し、この構成から外れるとEVA乗員がRCSの噴流を浴びるおそれがある。 */ }
            action <'F-EVA-EMG-14'> F_EVA_EMG_14 { doc /* ISSからシャトルのエアロックへの非常進入では、EV1が先にシャトルのエアロックの後部ハッチを準備して開け、EV2はシャトルのハッチが開いてからISSのクルーロックのハッチを閉じる。 */ }
        }
        package <'SSD-FD-EVA-MNT-001'> FN_EVA_MNT {
            action <'F-EVA-MNT-01'> F_EVA_MNT_01 { doc /* EVA後の手順はEMUの停止と脱衣、EMUの保守・再充填は電池とLiOHカートリッジの交換・充電と次のEVAのための清掃・給水、EVA後の帰還準備はEMUとエアロック機器の再構成と再収納である。 */ }
            action <'F-EVA-MNT-02'> F_EVA_MNT_02 { doc /* EVA後の手順は随意の手順を行わなければ45分、すべて行うと1時間25分で、再与圧でDCSの症状が消えた場合はEMUを脱がずに私的医療会議（PMC）でMCCに確かめる。 */ }
            action <'F-EVA-MNT-03'> F_EVA_MNT_03 { doc /* O2の再充填はO2圧が約850になれば完了とし、水の充填は水圧（WP）が8〜15 psiで約30秒安定すれば完了とし、満充填で給水タンクBの約6%を使う。 */ }
            action <'F-EVA-MNT-04'> F_EVA_MNT_04 { doc /* EMUへの給水はタンクAの出口を閉じて給水タンクBから行い、満充填には約15分かかる。 */ }
            action <'F-EVA-MNT-05'> F_EVA_MNT_05 { doc /* 水の再充填は外部エアロックの給水配管の温度が両区域で95°F以下のときに行い、これはSCUの細菌フィルタの寿命を守り、給水袋のヨウ素濃度が高くなる危険を減らすためである。 */ }
            action <'F-EVA-MNT-06'> F_EVA_MNT_06 { doc /* EMUの凝縮水はエアロック支援系を通してWCSのファンセパレータから廃水タンクへ捨て、その間はセパレータがあふれるおそれがあるためWCSの小便器を使わない。 */ }
            action <'F-EVA-MNT-07'> F_EVA_MNT_07 { doc /* LiOHカートリッジの交換では、10.2 psiキャビンを使った場合にカートリッジのキャップの前後に差圧が生じうるため、ポートを顔に向けず、キャップを外したポートの露出時間を短くする。 */ }
            action <'F-EVA-MNT-08'> F_EVA_MNT_08 { doc /* EMU電池のミッドデッキでの単独充電では、電池内の不動態化で充電完了と誤表示されることがあり、2〜3回充電を繰り返すと解消する。 */ }
            action <'F-EVA-MNT-09'> F_EVA_MNT_09 { doc /* SCUを通したEMU内での電池の充電は、確認には15分以上、満充電には最長20時間をかける。 */ }
            action <'F-EVA-MNT-10'> F_EVA_MNT_10 { doc /* EMU電池の交換はエアロックの電源を切りEMUの電源スイッチをSCU位置にして行い、電池を壁にぶつけてアルミ製のカバーを傷めないよう扱う。 */ }
            action <'F-EVA-MNT-11'> F_EVA_MNT_11 { doc /* EVA後の帰還準備（SAFERを搭載しない場合45分）ではEMU O2隔離弁とSCUのO2弁・給水弁を閉じ、着陸前にEMU TVとヘルメットライトを外して、EMUを着陸構成で拘束袋に固定し、外部ハッチの漏れが疑われる場合は内側ハッチの均圧弁をOFFにしてキャップを付ける。 */ }
            action <'F-EVA-MNT-12'> F_EVA_MNT_12 { doc /* 帰還前日のEVAは、単一シフトの飛行では就寝7時間前までにエアロックへの進入を終える場合に限る。再与圧、EVA後の手順、EMUの保守・再充填、EVA後の帰還準備、キャビンの収納などに最低7時間を要するためである。 */ }
            action <'F-EVA-MNT-13'> F_EVA_MNT_13 { doc /* STS-54では、EVA後にEMUにO2を再充填し、電池を一晩充電した。 */ }
        }
        package <'SSD-FD-EVA-OPS-001'> FN_EVA_OPS {
            action <'F-EVA-OPS-01'> F_EVA_OPS_01 { doc /* 10.2 psiaキャビンの手順は減圧症の危険を減らすため飛行医が定めたもので、計画EVAではEMU内の前呼吸を短くできる選択肢1・2（初期前呼吸60分、10.2 psiaで12時間または24時間、EMU内で75分または40分）を選び、10.2 psiaの調圧器がないため圧力とPPO2を手動で管理する。 */ }
            action <'F-EVA-OPS-02'> F_EVA_OPS_02 { doc /* マスク前呼吸はEV1・EV2が45分を終えるまで減圧を始めず、キャビンが10.2 psiaに達して1時間の前呼吸を終えるまで終えない。 */ }
            action <'F-EVA-OPS-03'> F_EVA_OPS_03 { doc /* 減圧中はキャビン圧とPPO2を図表に記入して弁の構成を変え、可燃性の増大を防ぐためキャビンのO2濃度を28.5%未満に保ち、14.7 CAB REG INLET SYS 1からN2を流す間はWCSを使わない。 */ }
            action <'F-EVA-OPS-04'> F_EVA_OPS_04 { doc /* 10.2 psiaの運用ではキャビン圧を10.0〜10.4 psia、PPO2を2.55〜2.80 psia（指示値）に手動で保ち、10.0 psiaの下限は冷却のための電力削減を避け、C&Wの上限10.6は前呼吸のPPN2 8.44 psiの限界を守るためである。 */ }
            action <'F-EVA-OPS-05'> F_EVA_OPS_05 { doc /* EMUの搭載替え（30分）ではエアロックのEMUとミッドデッキのEMUを入れ替え、搭載したEMUを点検する前にそのSCUのO2弁を閉じておく。 */ }
            action <'F-EVA-OPS-06'> F_EVA_OPS_06 { doc /* エアロックの空気循環系は非EVA時にエアロックへ調整空気を送るもので、ブースタファンにつなぐダクトは減圧のために乗員室とエアロックの間のハッチを閉じる前に外す。 */ }
            action <'F-EVA-OPS-07'> F_EVA_OPS_07 { doc /* カフチェックリストは手首のバンドに付けたアルミ合金の金具で綴じた約4×5インチのカードで、EVA作業の手順と参照データ、EMUの故障の診断と解決の補助を載せる。 */ }
            action <'F-EVA-OPS-08'> F_EVA_OPS_08 { doc /* 減圧症はカフ区分1〜4に分け、1はEVAを続けてEVA後のPMCで報告、2は作業場所を片付けてTERMINATE EVA、3は患者をエアロックへ補助しペイロードベイを安全にしてTERMINATE EVA、4はABORT EVAとして患者を単独で再与圧する。 */ }
            action <'F-EVA-OPS-09'> F_EVA_OPS_09 { doc /* TERMINATE EVAはEVA作業をやめてペイロードベイを片付け、エアロックに戻って再与圧することで、SCUで安定・是正できるEMUの問題ならその乗員は真空中でSCUにつないで救援に備え、もう1人がEVAを終えてよい。 */ }
            action <'F-EVA-OPS-10'> F_EVA_OPS_10 { doc /* 加圧したエアロックからEVA乗員を締め出してはならないが、乗員が大きく離れて再与圧の時間が重要なABORT EVAは例外で、離れた乗員は外部ハッチの均圧弁でエアロックを減圧して入れる。 */ }
            action <'F-EVA-OPS-11'> F_EVA_OPS_11 { doc /* MCCが判断するいずれかの消耗品の残りが30分になる時までにEVA乗員はエアロックへの進入を終えてSCUにつなぐ。30分は補充できない予備のSOPを使わないための予備である。 */ }
            action <'F-EVA-OPS-12'> F_EVA_OPS_12 { doc /* 計画EVAはMET 72時間より前には行わず、計画外EVAは最初の24時間には行わず72時間より前に行うには飛行医の健康評価とフライトディレクタの承認を要し、帰還日にはEVAを行わない。 */ }
            action <'F-EVA-OPS-13'> F_EVA_OPS_13 { doc /* 計画・計画外EVAは将来の非常時EVAの能力（再充填の消耗品など）を損なう場合は行わず、EVAの終わりにはペイロードベイを軌道離脱のために次のEVAが要らない構成にしておく。 */ }
            action <'F-EVA-OPS-14'> F_EVA_OPS_14 { doc /* 本書のキューカードはSAFER点検結果・SAFER状態の切り分け、DEPRESS/REPRESS（通常構成・トンネルアダプタ）、FAILED LEAK CHECKと、EMERGENCY AIRLOCK REPRESSのデカールである。 */ }
        }
        package <'SSD-FD-EVA-TLS-001'> FN_EVA_TLS {
            action <'F-EVA-TLS-01'> F_EVA_TLS_01 { doc /* EVA支援機器は作業に応じてエアロックの外に用意され、乗員をオービタ・RMSに固定し、機械的な補助を与え、移動を助ける。 */ }
            action <'F-EVA-TLS-02'> F_EVA_TLS_02 { doc /* 安全テザーはペイロードベイのどこへでも行けるよう乗員をオービタにつなぎ、エアロックを出る前に腰テザーに付けてEVA中は常に付けておく。 */ }
            action <'F-EVA-TLS-03'> F_EVA_TLS_03 { doc /* 運用飛行規則は、閉じたエアロックの中を除きEVA中は各乗員を安全テザーでオービタにつなぎ、工具は使用中は常に乗員にテザーでつなぐと定める。浮遊した工具はオービタに当たって損傷させるおそれがある。 */ }
            action <'F-EVA-TLS-04'> F_EVA_TLS_04 { doc /* EVAの付属品（LCVG、EMUの電池とライト、工具など）はミッドデッキ床のVolume H（MD23R）に収納する。 */ }
            action <'F-EVA-TLS-05'> F_EVA_TLS_05 { doc /* エアロック収納袋はEVA前後の物品の一時収納に使い、エアロックの減圧前に中身ごと取り出すが、EVAバッグ（カメラ・保温ミトン・工具キャディなど）はEVA中もエアロックに置く。 */ }
            action <'F-EVA-TLS-06'> F_EVA_TLS_06 { doc /* 左舷の軽量工具収納組立（TSA）は前後のトレイに調整式テザー、RMSロープリール、中心線ラッチ工具2個、3点ラッチ工具2個などを収め、扉を閉じるときはラッチの固定タブを矢印どうしが合う位置にする。 */ }
            action <'F-EVA-TLS-07'> F_EVA_TLS_07 { doc /* STS-114のEVA 2では左舷TSAの4個のラッチの1個が回らず、PGTでEVA用の手動オーバーライドボルトを緩めて開けたが、ボルトは規定の4 ft-lbに対し16 ft-lbで締められていた（IFA STS-114-V-18）。帰還は4個のうち3個のラッチが掛かっていれば支障ない。 */ }
            action <'F-EVA-TLS-08'> F_EVA_TLS_08 { doc /* ミニワークステーション（MWS）はEMUの前面に付けて工具を収め、作業場所で乗員をテザーで拘束し、携帯式足部拘束具はつま先ガイドとかかとクリップでEMUのブーツを固定する。 */ }
            action <'F-EVA-TLS-09'> F_EVA_TLS_09 { doc /* PGTは使用前に電池を入れて校正し、トリガで駆動して電池電圧と両方向の回転を確かめ、モード・トルク・回転数の設定をPGTの設定表と比べる。 */ }
            action <'F-EVA-TLS-10'> F_EVA_TLS_10 { doc /* PGTの標準設定は、トルクA1〜A7が2.5〜9.2 ft-lb、B1〜B7が12.0〜25.5 ft-lb、回転数10・30・60 rpm、スリープ15分・自動電源断30分で、多段トルクリミッタ（MTL）は2.5〜30.5の6段である。 */ }
            action <'F-EVA-TLS-11'> F_EVA_TLS_11 { doc /* PGTの異常表示（電池の高温・低温・低電圧、校正失敗、過電流など）では電源の入れ直しと再校正を試み、回復しなければ電源を切ってラチェット（手動）モードで使う。 */ }
            action <'F-EVA-TLS-12'> F_EVA_TLS_12 { doc /* RMSに付けた足部拘束具（MFR）・PADは、RMSがEMUに過大な荷重をかけない範囲でだけ使い、衝撃に最も弱いPLSSは直径2インチの球・2 ft/sで400 lbの衝撃まで認定されている。 */ }
        }
        package <'SSD-FD-GNC-001'> FN_GNC {
            action <'F-GNC-01'> F_GNC_01 { doc /* 機上の航法センサには、慣性計測装置（IMU）3台のほか、戦術航法装置（TACAN）、エアデータシステム、マイクロ波着陸システム（MLS）、電波高度計、GPSなどがある。 */ }
            action <'F-GNC-02'> F_GNC_02 { doc /* 2台のスタートラッカも航法系の一部である。 */ }
            action <'F-GNC-03'> F_GNC_03 { doc /* 軌道上では、スタートラッカで恒星の方位と仰角を測り、IMUを定期的にアラインメントする。 */ }
            action <'F-GNC-04'> F_GNC_04 { doc /* 軌道投入後、GN&C系はRCSとOMSを用いてオービタの姿勢と並進を制御し、機上の状態ベクトルは地上から通信アップリンクで定期的に更新される。 */ }
            action <'F-GNC-05'> F_GNC_05 { doc /* 上昇推力方向制御（ATVC）は、打上げ・第1段上昇中は3基のSSMEと2本のSRBの推力方向を、第2段上昇中はSSMEのみの推力方向を制御して、姿勢と軌道を制御する。 */ }
        }
        package <'SSD-FD-GNC-ACT-001'> FN_GNC_ACT {
            action <'F-GNC-ACT-01'> F_GNC_ACT_01 { doc /* 大気中の再突入では7枚の空力舵面を動かして機体を制御し、各舵面は冗長な電気駆動のサーボ弁で制御される油圧アクチュエータで駆動される（ボディフラップの3台のアクチュエータはサーボ弁を使わず、3系統の油圧系に固定で割り当てられる）。 */ }
            action <'F-GNC-ACT-02'> F_GNC_ACT_02 { doc /* サーボ弁は後部アビオニクスベイ4・5・6にある4台のASAで制御され、各ASAは各舵面の1つの弁を指令し、ASAの電源スイッチはパネルO14・O15・O16にある。 */ }
            action <'F-GNC-ACT-03'> F_GNC_ACT_03 { doc /* ASAからサーボ弁への指令と、舵面の位置・圧力のフィードバックをASAへ戻す経路をフライトコントロールチャネルと呼び、各舵面に4チャネルある。 */ }
            action <'F-GNC-ACT-04'> F_GNC_ACT_04 { doc /* 各エレボンのアクチュエータには3系統の油圧系から圧力が供給され、切替弁により主系統の圧力が約1,200〜1,500 psiaに下がると第1待機系統、さらに第2待機系統へ切り替わる。 */ }
            action <'F-GNC-ACT-05'> F_GNC_ACT_05 { doc /* サーボ弁の不具合で二次差圧（SEC ΔP）が2,025 psi以上の状態が120ミリ秒を超えると、ASAはそのサーボ弁をバイパスする切り離し指令を出し、FCS CHANNEL警報灯と「FCS CH X」のメッセージで知らせる。 */ }
            action <'F-GNC-ACT-06'> F_GNC_ACT_06 { doc /* パネルC3の4個のFCS CHANNELスイッチ（OVERRIDE・AUTO・OFF）は高いSEC ΔPによる自動の切り離しを制御し、OFFではそのチャネルを全アクチュエータでバイパスする。 */ }
            action <'F-GNC-ACT-07'> F_GNC_ACT_07 { doc /* ラダーとスピードブレーキはそれぞれ3台の可逆油圧モータを持ち、差動・混合ギアボックスを介して共通の4台の回転アクチュエータを駆動し、3台のうち2台の油圧モータが故障しても設計速度の約半分で動く。 */ }
            action <'F-GNC-ACT-08'> F_GNC_ACT_08 { doc /* ボディフラップは胴体後下端の3台のアクチュエータで駆動され、各アクチュエータは1系統の油圧と3台のASAの1台が制御するソレノイド弁を持ち、ボディフラップにはチャネルの切り離し機能はない。 */ }
            action <'F-GNC-ACT-09'> F_GNC_ACT_09 { doc /* ATVCは後部アビオニクスベイにある4台の装置で、各油圧ジンバルアクチュエータにジンバル指令と故障検出を与え、コールドプレートとフレオン系で冷却される。 */ }
            action <'F-GNC-ACT-10'> F_GNC_ACT_10 { doc /* 10基のアクチュエータが4つのATVCチャネルの指令電圧に応答し、各FCSチャネルのATVCは6つのSSMEドライバと4つのSRBドライバを持ち、各アクチュエータは4つのATVCから同じ指令を受ける。 */ }
            action <'F-GNC-ACT-11'> F_GNC_ACT_11 { doc /* 各アクチュエータの4つのサーボ弁は力の総和による多数決をとり、誤った指令が所定の時間を超えて続くとATVCが切り離しドライバでそのサーボ弁を外し、残りのチャネルで制御を続ける。 */ }
            action <'F-GNC-ACT-12'> F_GNC_ACT_12 { doc /* SSMEのピッチ作動器は取付けの中立位置から最大10.5°、ヨー作動器は最大8.5°エンジンをジンバルさせ、SRBのロック・チルト軸の±5°はピッチ・ヨーの±7°に相当する。 */ }
        }
        package <'SSD-FD-GNC-CCD-001'> FN_GNC_CCD {
            action <'F-GNC-CCD-01'> F_GNC_CCD_01 { doc /* GNCは自動とCSSの2つの運用モードを持ち、CSSでも乗員の指令はGPCを通って発行され、乗員と推進系・舵面の間に機械的なつながりはない完全なフライ・バイ・ワイヤ機である。 */ }
            action <'F-GNC-CCD-02'> F_GNC_CCD_02 { doc /* RHCはCDR・PLT・後部の3か所にあり、各RHCはピッチ・ロール・ヨーの各軸に3個ずつ計9個の変換器を持つ3重冗長で、1つの良い信号があれば機能する。 */ }
            action <'F-GNC-CCD-03'> F_GNC_CCD_03 { doc /* 上昇以外の段階ではRHCの変位がソフトウェアのデテントを超えるとその軸が自動からCSSに移るが、上昇中はパネルF2またはF4のCSSプッシュボタンを押す必要がある。 */ }
            action <'F-GNC-CCD-04'> F_GNC_CCD_04 { doc /* THCは軌道上のRCSジェットの並進を指令し、各THCは各軸の正負の方向に1個ずつ計6個の3接点スイッチを持つ。 */ }
            action <'F-GNC-CCD-05'> F_GNC_CCD_05 { doc /* ラダーペダルのRPTAは3個の変換器を持ち、自動の旋回協調のため滑空中は運用上使われず、接地後の滑走中に前輪の操向に使われる。 */ }
            action <'F-GNC-CCD-06'> F_GNC_CCD_06 { doc /* SBTCは上昇中のSSMEのスロットルと再突入中のスピードブレーキの2つの機能を持ち、各SBTCは変位に比例する電圧を出す3個の変換器を持つ。 */ }
            action <'F-GNC-CCD-07'> F_GNC_CCD_07 { doc /* ボディフラップスイッチはパネルL2とC3に1個ずつあり、主エンジンの熱防護と、再突入中にエレボンの変位を減らすピッチトリムのためのボディフラップの手動の位置決めを行う。 */ }
            action <'F-GNC-CCD-08'> F_GNC_CCD_08 { doc /* パネルC3とA6Uの24個のORBITAL DAPプッシュボタンで、DAPの構成（A・B）、制御モード（AUTO・INRTL・LVLH・FREE）、並進と回転のモードを選ぶ。 */ }
            action <'F-GNC-CCD-09'> F_GNC_CCD_09 { doc /* デバイスドライバユニット（DDU）はRHC・THC・SBTC・RPTAに直流と交流の電力を供給し、CDR・PLT・後部の各ステーションに1台ずつあって、それぞれ2系統の主母線の遮断器から給電される。 */ }
            action <'F-GNC-CCD-10'> F_GNC_CCD_10 { doc /* ADIの3本の角速度指針は機体の回転角速度を示し、上昇中の角速度はSRBまたはオービタのRGAから直接表示される。 */ }
            action <'F-GNC-CCD-11'> F_GNC_CCD_11 { doc /* HSIは航法点に対する機体の位置と方位・距離・コース/グライドパスの偏差を示し、上昇・再突入の誘導と比べる独立のソフトウェア源と、再突入中に個々の航法援助装置の健全性を評価する手段となる。 */ }
            action <'F-GNC-CCD-12'> F_GNC_CCD_12 { doc /* HUDは最終進入で飛行指令と情報を透過型のコンバイナに重ねて示す単一系統の装置で、冗長のために2本のデータバスにつながる。 */ }
            action <'F-GNC-CCD-13'> F_GNC_CCD_13 { doc /* SPIは再突入中にエレボン・ボディフラップ・ラダー・エルロン・スピードブレーキの実位置とスピードブレーキの指令位置を示すMEDSの表示である。 */ }
        }
        package <'SSD-FD-GNC-FCS-001'> FN_GNC_FCS {
            action <'F-GNC-FCS-01'> F_GNC_FCS_01 { doc /* 機体には4台のRGAがあり、各RGAはロール・ピッチ・ヨーの角速度を測る3個の1自由度レートジャイロを持ち、これらの角速度は上昇・再突入・軌道投入・軌道離脱でFCSへの主なフィードバックである。 */ }
            action <'F-GNC-FCS-02'> F_GNC_FCS_02 { doc /* RGAはペイロードベイ床下の後部隔壁にあり、フレオン冷却ループのコールドプレートで冷却される。 */ }
            action <'F-GNC-FCS-03'> F_GNC_FCS_03 { doc /* RGAの冗長管理は交換可能な中間値方式（IMVS）でデータを選び、妥当性限界による故障検出に加え、スピンモータ回転検出器（SMRD）で電源を失ったRGAを外す。 */ }
            action <'F-GNC-FCS-04'> F_GNC_FCS_04 { doc /* RGAは電力節約のため軌道上ではFCS点検時を除き切られ、軌道離脱準備とOPS 3移行の前に再び入れられ、RGAを切ったままのOPS 3移行は制御の喪失を招きうる。 */ }
            action <'F-GNC-FCS-05'> F_GNC_FCS_05 { doc /* 4台のAAはそれぞれ横（Y軸）と垂直（Z軸）の加速度を測る2個の加速度計を持ち、ミッドデッキ前部アビオニクスベイ1・2に置かれ、安定増強・第1段の荷重軽減・ADIの操舵誤差の表示に使われる。 */ }
            action <'F-GNC-FCS-06'> F_GNC_FCS_06 { doc /* SRB RGAは各SRBに2台あり、第1段上昇中だけピッチ・ヨーの角速度のフィードバックを与え、SRB分離の2〜3秒前に解除されてオービタRGAのデータに置き換えられる。 */ }
            action <'F-GNC-FCS-07'> F_GNC_FCS_07 { doc /* DAPは操縦の要求を解釈して機体の現状と比較し、適切な舵効への指令を生成する飛行制御ソフトウェアの中核で、飛行段階ごとに異なるDAPがある。 */ }
            action <'F-GNC-FCS-08'> F_GNC_FCS_08 { doc /* 遷移DAPはMECOから使われ、MECOの約20秒後に外部タンクの分離を自動で指令して下向きのRCSジェットで−Z方向へ4 ft/sまで並進させ、OMS-1・OMS-2の噴射ではOMSのTVCとRCSを使う。 */ }
            action <'F-GNC-FCS-09'> F_GNC_FCS_09 { doc /* 軌道上の飛行制御ソフトウェアはRCS DAP・OMS TVC DAP・姿勢処理モジュールとDAPの選択論理から成り、RCS DAPは主ジェットまたはバーニアジェットで姿勢と角速度を制御する。 */ }
            action <'F-GNC-FCS-10'> F_GNC_FCS_10 { doc /* OMS TVC DAPは誘導の要求速度をOMSのジンバル指令に変換し、OMSの点火・停止の指令と、OMSエンジンの故障時に姿勢を保つRCSの指令も生成する。 */ }
            action <'F-GNC-FCS-11'> F_GNC_FCS_11 { doc /* エアロジェットDAPはMM 304への移行（通常EI-5）から車輪停止まで働き、動圧に応じて舵面とRCSジェットを組み合わせる飛行適応型・閉ループの角速度指令型の制御で、ジェットの使用を徐々に減らして舵面の使用を増やす。 */ }
            action <'F-GNC-FCS-12'> F_GNC_FCS_12 { doc /* 再突入のロールモードはエルロンを主な舵効とするラップアラウンドDAPが標準で、後部RCSの推進薬が少ない（10%未満）場合や後部のヨージェットを失った場合は、ヨージェットを使わないNo Yaw Jetモードを使う。 */ }
        }
        package <'SSD-FD-GNC-GNS-001'> FN_GNC_GNS {
            action <'F-GNC-GNS-01'> F_GNC_GNS_01 { doc /* 航法の基本機能は機体の慣性位置と速度（状態ベクトル）を時間に対して正確に推定することで、ランデブ時には目標の位置と速度も推定する。 */ }
            action <'F-GNC-GNS-02'> F_GNC_GNS_02 { doc /* 状態ベクトルはM50座標系の位置（X・Y・Z、ft）と速度（ft/s）の6要素とGMTの時刻タグで表される。 */ }
            action <'F-GNC-GNS-03'> F_GNC_GNS_03 { doc /* 航法はIMU・航法センサのデータと重力・抗力・ベントのモデルで状態ベクトルを伝播し、時間とともに増える誤差は、地上のレーダ追跡に基づく新しい状態ベクトルまたは差分のアップリンクで修正される。 */ }
            action <'F-GNC-GNS-04'> F_GNC_GNS_04 { doc /* 航法はSuper-G積分方式で状態ベクトルを伝播し、惰行中は大気抗力の加速度のモデルを使い、REL NAVでランデブ航法を有効にすると目標の状態ベクトルも伝播する。 */ }
            action <'F-GNC-GNS-05'> F_GNC_GNS_05 { doc /* 軌道離脱・再突入では3台のIMUそれぞれに基づく3つの状態ベクトルを伝播し、交換可能な中間値選択で1つの状態ベクトルを誘導・飛行制御・表示に渡す。 */ }
            action <'F-GNC-GNS-06'> F_GNC_GNS_06 { doc /* 再突入では外部センサのデータを期待誤差の範囲と照合して取り込み（カルマンフィルタ）、HORIZ SIT表示の操作で取り込みの強制・禁止・自動を選べ、悪いセンサデータによる航法の汚染を防ぐ。 */ }
            action <'F-GNC-GNS-07'> F_GNC_GNS_07 { doc /* 3系統GPSの機体では、軌道離脱・再突入の間は42秒ごと（17,000 ft以下は9秒ごと）に選択したGPSのベクトルを取り込み、MLSが使えるときはGPSの更新を自動で禁止する。 */ }
            action <'F-GNC-GNS-08'> F_GNC_GNS_08 { doc /* 第1段の誘導は事前に計画した相対速度に対するロール・ピッチ・ヨーの姿勢表を使い、MPSのスロットルへも事前に定めたスロットル計画に従って指令を送る。 */ }
            action <'F-GNC-GNS-09'> F_GNC_GNS_09 { doc /* 第2段の誘導はPEG 1の周期的な閉ループ方式で、MECOの目標条件（速度・半径・経路角・軌道傾斜角・昇交点経度）へ機体を導き、主エンジンのスロットル指令を3 gを超えないように調整する。 */ }
            action <'F-GNC-GNS-10'> F_GNC_GNS_10 { doc /* 軌道上の誘導は、UNIV PTGで指定した機体軸を目標に向ける姿勢変化を計算し、PEG 7（外部ΔV）で点火時刻と速度変化を指定したOMSまたはRCSの噴射を指令する。 */ }
            action <'F-GNC-GNS-11'> F_GNC_GNS_11 { doc /* 再突入の誘導は温度・動圧・垂直加速度の制限から機体を守る抗力加速度のプロファイルを飛び、迎角とバンク角で抗力を調整し、方位誤差に応じてロールリバーサルを指令する。 */ }
            action <'F-GNC-GNS-12'> F_GNC_GNS_12 { doc /* TAEMの誘導はエネルギー対距離のプロファイルに従ってHACを回り、A/Lの誘導は外側グライドスロープからプレフレアと最終フレア（30〜80 ft）を経て接地まで滑走路中心線へ導く。 */ }
        }
        package <'SSD-FD-GNC-INS-001'> FN_GNC_INS {
            action <'F-GNC-INS-01'> F_GNC_INS_01 { doc /* オービタには3台のIMUがあり、各IMUは慣性安定化された4軸ジンバルの台座に3個の加速度計と2個の2軸ジャイロを載せ、GNCソフトウェアに慣性姿勢と速度のデータを与える。 */ }
            action <'F-GNC-INS-02'> F_GNC_INS_02 { doc /* 飛行は1台のIMUでも可能であるが、冗長のために3台を搭載し、IMUはフライトデッキの表示・制御パネルの前方にある航法ベースに取り付けられる。 */ }
            action <'F-GNC-INS-03'> F_GNC_INS_03 { doc /* ジンバルは外側から外ロール・ピッチ・内ロール・方位の順で、冗長な内ロールジンバルが全姿勢での使用を可能にし、ジンバルロックを防ぐ。 */ }
            action <'F-GNC-INS-04'> F_GNC_INS_04 { doc /* 3台のIMUの軸は互いにも機体軸ともずらして（スキュー）取り付けられ、姿勢による不具合が同時に1台を超えないようにするとともに、冗長管理による故障IMUの判定に使われる。 */ }
            action <'F-GNC-INS-05'> F_GNC_INS_05 { doc /* IMUはヒータだけに給電する暖機・待機モードと運転モードを持ち、冷えた状態から運転温度に達するまで約8時間かかり、GNC OPS 2・3・9のソフトウェア指令で運転モードに移る。 */ }
            action <'F-GNC-INS-06'> F_GNC_INS_06 { doc /* 運転指令を受けたIMUはジンバルをケージしてからジャイロを回し、安定化ループに給電して慣性基準となるまでに約85秒かかり、電力の節約のために切る場合を除いて、打上げ前から飛行の終わりまで運転モードのままとする。 */ }
            action <'F-GNC-INS-07'> F_GNC_INS_07 { doc /* IMU SOPは速度のM50座標への変換、レゾルバ出力のジンバル角への変換、表示用の加速度の計算、ソフトウェアBITE、スタートラッカまたは他のIMUによるずれに基づくトルク指令の計算を行う。 */ }
            action <'F-GNC-INS-08'> F_GNC_INS_08 { doc /* スタートラッカは−Y軸と−Z軸の2台で、IMUを載せた航法ベースの延長部に置かれ、IMUのアラインメントと、ランデブ時の目標の追尾・視線ベクトルの算出に使われる。 */ }
            action <'F-GNC-INS-09'> F_GNC_INS_09 { doc /* スタートラッカで得た2つの恒星の視線ベクトルで機体の慣性姿勢を定め、IMUの姿勢との差からトルク角を求めてジャイロのドリフトを除くが、IMUのずれが1.4°を超えるとHUDでまず1.4°以内に合わせる。 */ }
            action <'F-GNC-INS-10'> F_GNC_INS_10 { doc /* スタートラッカのアセンブリには冗長管理がなく、2台は独立していずれも全作業を行え、単独でも同時にも運用できる。 */ }
            action <'F-GNC-INS-11'> F_GNC_INS_11 { doc /* COASは無限遠に焦点を合わせた照準を投影する光学器具で、スタートラッカが使えないときのアラインメントには主にHUDが使われるがCOASも使え、乗員がATT REFボタンでマークした瞬間の3台のIMUのジンバル角が記録される。 */ }
            action <'F-GNC-INS-12'> F_GNC_INS_12 { doc /* IMUの熱制御は自動の内部ヒータ系と強制空冷系から成り、内部ヒータはIMUに電源を入れると働いて電源を切るまで動作する。 */ }
        }
        package <'SSD-FD-GNC-NAS-001'> FN_GNC_NAS {
            action <'F-GNC-NAS-01'> F_GNC_NAS_01 { doc /* 3系統のGPSを持たない機体は冗長に動作する3台のTACANを持ち、各TACANは前胴の下面と上面に1つずつアンテナを持ち、受動冷却でミッドデッキのアビオニクスベイに置かれる。 */ }
            action <'F-GNC-NAS-02'> F_GNC_NAS_02 { doc /* TACANはTACANまたはVORTACの地上局に対する斜距離と磁方位を求め、最大距離は400 n. mi.である。 */ }
            action <'F-GNC-NAS-03'> F_GNC_NAS_03 { doc /* 再突入では2台以上のTACANがロックすると、TACANの距離・方位がMLSの捕捉（約18,000 ft）まで状態ベクトルの更新に使われる。 */ }
            action <'F-GNC-NAS-04'> F_GNC_NAS_04 { doc /* TACANの冗長管理は距離・方位のデータの中間値を選び、故障を検出するとSM ALERTを点灯してGPCの故障メッセージを出す。 */ }
            action <'F-GNC-NAS-05'> F_GNC_NAS_05 { doc /* OV-105では3台のGPS受信機が冗長に動作し、各受信機は前胴の下面と上面のアンテナを持ち、前部アビオニクスベイに置かれた対流冷却の装置（13 lb・40 W）である。 */ }
            action <'F-GNC-NAS-06'> F_GNC_NAS_06 { doc /* GPSの選択フィルタは使える受信機が3台なら中間値選択、2台なら平均、1台ならその1台を選び、1台もなければ最後の有効なデータを伝播するが、有効なデータから18秒を超えるとそれを航法の更新に使わない。 */ }
            action <'F-GNC-NAS-07'> F_GNC_NAS_07 { doc /* エアデータ系は前胴下面の左右2本のプローブと4台のADTAから成り、左プローブの圧力・温度はADTA 1・3へ、右プローブはADTA 2・4へ導かれる。 */ }
            action <'F-GNC-NAS-08'> F_GNC_NAS_08 { doc /* ADTA SOPはADTAのデータから迎角・マッハ数・等価対気速度・真対気速度・動圧・気圧高度を計算し、4台の圧力が一致すれば各プローブの1組を平均してソフトウェアに渡す。 */ }
            action <'F-GNC-NAS-09'> F_GNC_NAS_09 { doc /* 各プローブは2台の交流モータの回転式電気機械アクチュエータで独立に展開し、展開時間は2台のモータで15秒、1台で30秒である。 */ }
            action <'F-GNC-NAS-10'> F_GNC_NAS_10 { doc /* 3台のMLSは着陸滑走路脇の地上局に対する斜距離・方位角・仰角を求めて進入・着陸の段階で使われ、各MLSはKu帯の送受信機と復号器から成る。 */ }
            action <'F-GNC-NAS-11'> F_GNC_NAS_11 { doc /* MLSの冗長管理は3台が有効なら距離・方位角・仰角の中間値を、2台なら平均を選ぶ。 */ }
            action <'F-GNC-NAS-12'> F_GNC_NAS_12 { doc /* 2台の電波高度計はC帯のパルスで最寄りの地表までの高度を0〜5,000 ftの範囲で測るが、航法には使われず乗員の監視用である。 */ }
        }
        package <'SSD-FD-GNC-OPS-001'> FN_GNC_OPS {
            action <'F-GNC-OPS-01'> F_GNC_OPS_01 { doc /* 上昇中はGNC系に問題があっても軌道へ向かうことが最も望ましく、再突入に必須なGNC系の故障許容をすべて恒久的に失った場合は初日のPLSに帰還する（A8-3）。 */ }
            action <'F-GNC-OPS-02'> F_GNC_OPS_02 { doc /* 再突入に必須なGNC系が故障許容をすべて失えば次のPLSで早期に終了し、4台構成の系（AA・RGA・FCSチャネルの位置フィードバック）は1故障後も公称の終了まで続けられる（A8-4）。 */ }
            action <'F-GNC-OPS-03'> F_GNC_OPS_03 { doc /* GNCのLRUへの電力またはデータ経路の冗長の喪失は、LRUの冗長の喪失とはみなさない（A8-10）。 */ }
            action <'F-GNC-OPS-04'> F_GNC_OPS_04 { doc /* GNCのパラメータは共通の冗長出力との差がI-loadのRM追従限界を超えると故障とし、冗長出力を持たないLRU（IMU・TACAN・MSBLSなど）ではパラメータの喪失をLRUの喪失とする（A8-51）。 */ }
            action <'F-GNC-OPS-05'> F_GNC_OPS_05 { doc /* 搭載のRMがジレンマを宣言したIMU・TACAN・ADTA・MLSの故障は、地上レーダのデータとの比較で故障したLRUを特定する（A8-52）。 */ }
            action <'F-GNC-OPS-06'> F_GNC_OPS_06 { doc /* 軌道離脱噴射の70分前にIMU間のアラインメントでIMUのRMのしきい値をリセットし、再突入日の軌道離脱前の恒星アラインメントを重要なアラインメントとする（A8-110）。 */ }
            action <'F-GNC-OPS-07'> F_GNC_OPS_07 { doc /* EIでのIMUの姿勢誤差が0.5°を超えると予測される場合は軌道離脱を行わず、公称の軌道離脱で0.25°を超える場合は軌道離脱を遅らせてアラインメントを行う（A4-151）。 */ }
            action <'F-GNC-OPS-08'> F_GNC_OPS_08 { doc /* 良いADTAが1台だけになればエアデータのG&Cへの取り込みを禁止してデフォルト/NAVDADのエアデータで飛び、エアデータをすべて失うか取り込まないときはシータ限界を守る（A8-111）。 */ }
            action <'F-GNC-OPS-09'> F_GNC_OPS_09 { doc /* GPCの故障による再割当てでは各GPCに同数のASAを割り当て、FA MDMまたはGPCの故障時は対応するFCSチャネルを切り、1つのアクチュエータに良いチャネルが2つだけ残れば両方をOVERRIDEにする（A8-107）。 */ }
            action <'F-GNC-OPS-10'> F_GNC_OPS_10 { doc /* FCS点検の第1部（二次アクチュエータ点検）は、ASAのヌルドライバ故障を調べるため、できる限り軌道離脱噴射の前にAPUまたは油圧の循環ポンプを使って行う（A8-104）。 */ }
            action <'F-GNC-OPS-11'> F_GNC_OPS_11 { doc /* GNCのGo/No-Goは操縦装置・スイッチ、TVC・ドライバ、空力舵面、センサ、専用表示ごとにMDF・次のPLS・初日のPLSとする故障数を定め、たとえばIMUの2台の故障は再突入に1台が要るため次の（または初日の）PLSとする（A8-1001）。 */ }
            action <'F-GNC-OPS-12'> F_GNC_OPS_12 { doc /* PASSのRGA・AA・舵面の故障検出・切り離し（FDIR）は最初の故障で終わり、以後は乗員による選択フィルタの管理が必要で、BFSの選択フィルタは常に乗員の管理を要する。 */ }
        }
        package <'SSD-FD-MECH-001'> FN_MECH {
            action <'F-MECH-01'> F_MECH_01 { doc /* 機械系は展開・格納・開閉を要する構成品で、アクティブベント系、ETアンビリカル扉、ペイロードベイドア、展開式放熱器、着陸・減速系を含み、それぞれを電気または油圧のアクチュエータで動かす。 */ }
            action <'F-MECH-02'> F_MECH_02 { doc /* 電気機械式アクチュエータ（PDU）は2基の3相交流モータを持ち、モータとリミットスイッチの電力はモータ制御組立（MCA）から供給される。 */ }
            action <'F-MECH-03'> F_MECH_03 { doc /* 着陸装置は前脚と左右の主脚から成る三脚式で、各脚は緩衝支柱と2組の車輪・タイヤを持ち、主脚の各車輪はアンチスキッド付きのブレーキを備える。 */ }
            action <'F-MECH-04'> F_MECH_04 { doc /* 乗員が脚下げを指令すると、油圧系1の圧力で各脚のアップロックフックが外れ、脚はばね・油圧アクチュエータ・空気力・重力で下がって、10秒以内に下げ位置でロックされる。 */ }
            action <'F-MECH-05'> F_MECH_05 { doc /* 4つの主脚車輪はそれぞれ電気油圧式ディスクブレーキとアンチスキッド系を備え、制動系は油圧系1・2を常用、系3を予備とし、3系統の主直流電源をすべて使う。 */ }
            action <'F-MECH-06'> F_MECH_06 { doc /* 前脚の油圧操舵アクチュエータは機長・操縦手のラダーペダルからの電子指令に応答し、GPCモードとキャスタモードがある。 */ }
            action <'F-MECH-07'> F_MECH_07 { doc /* ドラッグシュートは垂直安定板の基部に収納され、機首下げの前に機長または操縦手の冗長な指令で手動展開して、滑走中の減速を補助する。 */ }
            action <'F-MECH-08'> F_MECH_08 { doc /* アクティブベント系は、地上の大気から宇宙の真空まで、機体の非与圧区画を周囲の環境と均圧させる。 */ }
            action <'F-MECH-09'> F_MECH_09 { doc /* 外部タンク分離後は、露出した2つの後部アンビリカル開口をET扉で閉じ、再突入加熱から保護する。 */ }
            action <'F-MECH-10'> F_MECH_10 { doc /* ペイロードベイドアは、ペイロードの放出・回収のための開口を与え、中部胴体を構造的に支持し、ECLSSの放熱器を収める。各扉は1基の電気機械式アクチュエータで開閉し、計32個のラッチで閉じた状態に保持する。 */ }
        }
        package <'SSD-FD-MECH-ACT-001'> FN_MECH_ACT {
            action <'F-MECH-ACT-01'> F_MECH_ACT_01 { doc /* 機械系はオービタの展開・収納・開閉する構成品で、それぞれを電動または油圧のアクチュエータが動かす。 */ }
            action <'F-MECH-ACT-02'> F_MECH_ACT_02 { doc /* 機械系には能動ベント系・ETアンビリカル扉・ペイロードベイドア・展開式放熱器・着陸減速系があり、放熱器は2.9節、着陸減速系は2.14節で扱われる。 */ }
            action <'F-MECH-ACT-03'> F_MECH_ACT_03 { doc /* 電動アクチュエータ（PDU）は2つの3相交流モータ・ブレーキ・差動組立・歯車箱・リミットスイッチを持ち、ET扉のセンタラインラッチ以外はトルクリミッタも持つ。 */ }
            action <'F-MECH-ACT-04'> F_MECH_ACT_04 { doc /* アクチュエータのモータとリミットスイッチの電力はモータ制御組立（MCA）から供給され、MCAはパネルMA73CのMCA LOGICスイッチと遮断器で給電される。 */ }
            action <'F-MECH-ACT-05'> F_MECH_ACT_05 { doc /* 通常はアクチュエータの2つの交流モータが同時に動き（2モータ駆動）、1つだけで動かすと所定の位置まで2倍の時間がかかる。 */ }
            action <'F-MECH-ACT-06'> F_MECH_ACT_06 { doc /* MCAへのモータの入切の指令は、GPC、DPSの項目入力、またはハードワイヤのスイッチから出る。 */ }
            action <'F-MECH-ACT-07'> F_MECH_ACT_07 { doc /* 機械系を操作するときは常にタイマを使い、1モータの時間を過ぎても所定の状態にならなければ駆動の指令を続けない。 */ }
        }
        package <'SSD-FD-MECH-DEC-001'> FN_MECH_DEC {
            action <'F-MECH-DEC-01'> F_MECH_DEC_01 { doc /* 接地後、乗員はドラッグシュートを展開し、制動と前輪操向を始める。 */ }
            action <'F-MECH-DEC-02'> F_MECH_DEC_02 { doc /* ドラッグシュートは垂直尾翼の基部に収め、機首下げの前にCDRかPLTの冗長な指令で展開し、主エンジンのベルを守るため対地60（±20） ktで投棄する。 */ }
            action <'F-MECH-DEC-03'> F_MECH_DEC_03 { doc /* 展開時は火工品で収納部の扉を外し、モータが9 ftのパイロットシュートを出し、それが40 ftの主傘を引き出す。 */ }
            action <'F-MECH-DEC-04'> F_MECH_DEC_04 { doc /* 4つの主輪はそれぞれ電気油圧式のディスクブレーキとアンチスキッドを持つ。 */ }
            action <'F-MECH-DEC-05'> F_MECH_DEC_05 { doc /* 制動は油圧系1・2を能動、系3を予備とし、3つの主直流電気系をすべて使う冗長な構成で、主脚の荷重を検知して約1.9秒後から効く。 */ }
            action <'F-MECH-DEC-06'> F_MECH_DEC_06 { doc /* 前脚の油圧操向アクチュエータはラダーペダルの電子指令に応じ、GPCモードとキャスタモードがある。 */ }
            action <'F-MECH-DEC-07'> F_MECH_DEC_07 { doc /* 前輪操向は、主脚接地（WOW）・ピッチ角0°未満・前脚接地（WONG）の条件がそろってから有効になる。 */ }
        }
        package <'SSD-FD-MECH-LDG-001'> FN_MECH_LDG {
            action <'F-MECH-LDG-01'> F_MECH_LDG_01 { doc /* 降着装置は前脚と左右の主脚の3脚式で、前脚は前胴の下部、主脚は中胴に隣接する左右の翼の下部にあり、各脚は緩衝支柱と2つの車輪・タイヤを持つ。 */ }
            action <'F-MECH-LDG-02'> F_MECH_LDG_02 { doc /* 前脚は2枚、各主脚は1枚の扉を持ち、脚を下ろすと扉が自動で開く。 */ }
            action <'F-MECH-LDG-03'> F_MECH_LDG_03 { doc /* 展開を指令すると油圧系1の圧力でアップロックフックが外れ、脚はばね・油圧アクチュエータ・空気力・重力で下がり、10秒以内に下げ位置でロックされる。 */ }
            action <'F-MECH-LDG-04'> F_MECH_LDG_04 { doc /* 油圧系1の圧力が無いときは、指令の1秒後に各脚のアップロックフックの火工品が自動でフックを外す。 */ }
            action <'F-MECH-LDG-05'> F_MECH_LDG_05 { doc /* 脚は高度300±100 ft、最大312 KEASで展開する。 */ }
            action <'F-MECH-LDG-06'> F_MECH_LDG_06 { doc /* 脚は地上作業でだけ格納でき、飛行中には引き込めない。 */ }
            action <'F-MECH-LDG-07'> F_MECH_LDG_07 { doc /* 緩衝支柱は空気/油式の緩衝器で、着陸の衝撃を和らげる主な手段である。 */ }
            action <'F-MECH-LDG-08'> F_MECH_LDG_08 { doc /* ARMボタンで脚の展開弁の継電器を準備して火工品の制御器を活性化し、DNボタンで油圧系1・2の展開弁を開く。 */ }
        }
        package <'SSD-FD-MECH-OPS-001'> FN_MECH_OPS {
            action <'F-MECH-OPS-01'> F_MECH_OPS_01 { doc /* MMACSのGo/No-Go基準は、PLBD駆動モータを扉あたり2基、ラッチ駆動モータをギャングあたり2基として扱い、脚の展開系・制動・前輪操向の判定条件を示す。 */ }
            action <'F-MECH-OPS-02'> F_MECH_OPS_02 { doc /* ベント扉・PLBD・放熱器・ET扉・ペイロード保持ラッチなどの駆動機構は冗長のため2つのモータを持ち、駆動時間が1モータの時間を超えると故障とみなす。 */ }
            action <'F-MECH-OPS-03'> F_MECH_OPS_03 { doc /* ラッチギャングに閉用のモータが2基そろっていなくても、冗長側のモータで閉じられるので機体はフェイルセーフで、1つのギャングが外れたままでも突入できる。 */ }
            action <'F-MECH-OPS-04'> F_MECH_OPS_04 { doc /* 軌道上ではベント扉を通常すべて開けておき、扉1・2の閉の冗長を失ったときは反対側の扉に開の冗長があれば閉じる。 */ }
            action <'F-MECH-OPS-05'> F_MECH_OPS_05 { doc /* ET扉の閉の項目入力は、手動の閉操作がうまくいかず、センタラインラッチが収納されて両方の扉のラッチの準備が確かめられたとき、またはAOAのときだけ使う。 */ }
            action <'F-MECH-OPS-06'> F_MECH_OPS_06 { doc /* MMACSのGo/No-Go基準は、脚の油圧・火工品の展開系の2つの喪失で次のPLSとし、制動・前輪操向による方向制御はゼロ故障許容を判定条件とする。 */ }
        }
        package <'SSD-FD-MECH-PLB-001'> FN_MECH_PLB {
            action <'F-MECH-PLB-01'> F_MECH_PLB_01 { doc /* ペイロードベイドアはペイロードの展開・回収の開口となり、中胴の構造を支え、ECLSSの放熱器を収める。 */ }
            action <'F-MECH-PLB-02'> F_MECH_PLB_02 { doc /* ドアは左右2枚で、各ドアは伸縮継手でつないだ5つの区分から成り、長さ約60 ft・合計面積1,600 ft2である。 */ }
            action <'F-MECH-PLB-03'> F_MECH_PLB_03 { doc /* 右舷のドアは左舷のドアに重なってセンタラインの圧力・熱のシールとなるため、右舷を先に開けて後に閉める。 */ }
            action <'F-MECH-PLB-04'> F_MECH_PLB_04 { doc /* 各ドアは13のヒンジ（固定の5つと熱膨張を許す浮動の8つ）で中胴につながり、2つの3相交流モータを持つ1つの電動アクチュエータで開閉する。 */ }
            action <'F-MECH-PLB-05'> F_MECH_PLB_05 { doc /* ドアは合計32のラッチ（センタラインの16と前後の隔壁の各8）で閉じた状態に保たれる。 */ }
            action <'F-MECH-PLB-06'> F_MECH_PLB_06 { doc /* センタラインのラッチは4つずつ4組（ギャング）に分かれ、各組を1つの電動アクチュエータで駆動し、1組の開閉に20秒（2モータ）かかる。 */ }
            action <'F-MECH-PLB-07'> F_MECH_PLB_07 { doc /* 右舷のドアがセンタラインのフック、左舷のドアがローラを持ち、フックが回ってローラをつかむ。 */ }
        }
        package <'SSD-FD-MECH-VNT-001'> FN_MECH_VNT {
            action <'F-MECH-VNT-01'> F_MECH_VNT_01 { doc /* 能動ベント系は、大気中から真空へ移る間に与圧されない区画を外気と等圧にする。 */ }
            action <'F-MECH-VNT-02'> F_MECH_VNT_02 { doc /* 能動ベント系は胴体の左右各7つ、計14のベント口から成り、各扉は圧力シールと熱シールを持ち、電動アクチュエータで内側へ動く。 */ }
            action <'F-MECH-VNT-03'> F_MECH_VNT_03 { doc /* ベント扉は2モータ駆動でそれぞれ5秒で開閉し、一部の扉は地上のパージのための中間位置を持つ。 */ }
            action <'F-MECH-VNT-04'> F_MECH_VNT_04 { doc /* ベント扉はGNCのソフトウェアのシーケンスで操作し、秒読みのT-28秒にRSLSが開のシーケンスを呼ぶ。 */ }
            action <'F-MECH-VNT-05'> F_MECH_VNT_05 { doc /* ETとオービタの燃料・電気のアンビリカルは機体下面の2つの後部の開口から入り、左の空洞に液体水素、右の空洞に液体酸素のアンビリカルがある。 */ }
            action <'F-MECH-VNT-06'> F_MECH_VNT_06 { doc /* ET分離後、ET扉を閉じて露出した開口を突入の加熱から守り、扉はTPSのタイルで覆われる。 */ }
            action <'F-MECH-VNT-07'> F_MECH_VNT_07 { doc /* ET扉にはセンタラインラッチ（上昇中に扉を開いたまま保つ）とアップロックラッチ（閉じた扉を固定する）がある。 */ }
        }
        package <'SSD-FD-MPS-001'> FN_MPS {
            action <'F-MPS-01'> F_MPS_01 { doc /* SSMEは2本の固体ロケットモータの補助を受けながら、打上げから主エンジン燃焼停止（MECO）まで機体を所定速度へ加速する。 */ }
            action <'F-MPS-02'> F_MPS_02 { doc /* 3基のSSMEは再使用可能な可変推力の液体ロケットエンジンで、液体水素を燃料兼冷却材、液体酸素を酸化剤とし、推進薬は外部タンク内の別々のタンクから供給される。 */ }
            action <'F-MPS-03'> F_MPS_03 { doc /* 各エンジンの公称推力は海面で375,000 lb、真空中で470,000 lbである。 */ }
            action <'F-MPS-04'> F_MPS_04 { doc /* SSMEは電子コントローラを備え、点検・始動・運転・監視・停止の全機能を担う。 */ }
            action <'F-MPS-05'> F_MPS_05 { doc /* 油圧駆動のジンバルアクチュエータにより、各エンジンはピッチ・ヨー方向に首振りして推力方向を制御する。 */ }
            action <'F-MPS-06'> F_MPS_06 { doc /* MPSは、オービタの油圧系、電力系、マスターイベントコントローラ、データ処理系と重要なインタフェースを持つ。 */ }
        }
        package <'SSD-FD-MPS-CTL-001'> FN_MPS_CTL {
            action <'F-MPS-CTL-01'> F_MPS_CTL_01 { doc /* 制御器は低圧燃料ターボポンプ側の推力室・ノズル冷却材出口マニホールドに取り付けた与圧・温度調節された電子機器で、2台の冗長なディジタル計算機ユニット（DCU A・B）を持ち、通常はDCU Aが制御しDCU Bは作動しているが制御はしない。 */ }
            action <'F-MPS-CTL-02'> F_MPS_CTL_02 { doc /* エンジン制御要素への指示は毎秒50回（20ミリ秒ごと）更新され、二重冗長の構成により1つ目の故障の後も通常の運転を続け、2つ目の故障でフェイルセーフに停止する。 */ }
            action <'F-MPS-CTL-03'> F_MPS_CTL_03 { doc /* 制御器はエンジンのセンサ・弁・アクチュエータ・スパーク点火器とともに自己完結した制御・点検・監視の系を成し、飛行準備の確認、始動・停止の順序制御、推力と混合比の閉ループ制御、センサ励起、性能限界の監視、性能・保守データを受け持つ。 */ }
            action <'F-MPS-CTL-04'> F_MPS_CTL_04 { doc /* 制御器の電力は3系統の交流母線から冗長性を保つように供給され、各DCUは別々の母線から受電し、どの2母線を失っても失うエンジンは1基だけになるよう母線が割り当てられ、パネルR2には制御器ごとに2個（上がDCU A、下がDCU B）のMPS ENGINE POWERスイッチがある。 */ }
            action <'F-MPS-CTL-05'> F_MPS_CTL_05 { doc /* 各制御器は専用のEIU（GPCおよび制御器とつながる特殊なMDM）を通じてGPCの指令を受け、各EIUは1基のSSMEだけに専用で、3台のEIUは互いにつながらない。 */ }
            action <'F-MPS-CTL-06'> F_MPS_CTL_06 { doc /* 冗長セットの各GPCは割り当てられた飛行重要データバスにエンジン指令を出し（通常はGPC 1〜4がFC 5〜8）、各EIUは4つの指令を受ける。 */ }
            action <'F-MPS-CTL-07'> F_MPS_CTL_07 { doc /* EIUは受けた指令の伝送誤りを検査し、CIA 3のデータ選択論理で4つの指令を3つに減らして制御器へ送り、制御器は3つのうち2つ以上の有効な入力がないと指令経路故障とする。 */ }
            action <'F-MPS-CTL-08'> F_MPS_CTL_08 { doc /* 制御器はエンジンのセンサが与える圧力・温度・流量・ターボポンプ回転数・弁位置などを車両データテーブルにまとめ、3つの指令経路に対してデータは一次・二次の2経路でEIUへ送る。 */ }
            action <'F-MPS-CTL-09'> F_MPS_CTL_09 { doc /* 一次・二次のデータをともに失うとデータ経路故障となり、GPCは「MPS DATA C(L,R)」の故障メッセージを出してパネルF7の黄色のMAIN ENGINE STATUSライトを点灯させる。 */ }
            action <'F-MPS-CTL-10'> F_MPS_CTL_10 { doc /* 制御器がLH2流量計または主燃焼室圧力センサのデータを失うと混合比を制御できないため弁を最後の指令位置に保持する電気的ロックアップとなり、エンジンは推力を変えられないが停止の指令には従う。 */ }
            action <'F-MPS-CTL-11'> F_MPS_CTL_11 { doc /* 制御器は安全運転に重要な運転パラメータを監視し、高圧燃料ターボポンプ吐出温度1,860°R超、高圧酸化剤ターボポンプ吐出温度1,660°R超または720°R未満、中間シールパージ圧159 psia未満などのレッドラインを超えると、リミットが有効なら自動でエンジンを停止する。 */ }
            action <'F-MPS-CTL-12'> F_MPS_CTL_12 { doc /* 制御器は、レッドラインのパラメータが限界または妥当性の基準を60ミリ秒（制御器の20ミリ秒周期で3回連続）超えたときに限り処置し、データの一時的な乱れでは動作しない。 */ }
            action <'F-MPS-CTL-13'> F_MPS_CTL_13 { doc /* 制御器の動作には交流の3相すべてと100 Vrms以上の電圧が必要で、500ミリ秒を超えて100 Vrmsを下回るとチャネルの切替え（AからB）またはエンジン停止となる。 */ }
        }
        package <'SSD-FD-MPS-DMP-001'> FN_MPS_DMP {
            action <'F-MPS-DMP-01'> F_MPS_DMP_01 { doc /* LO2・LH2それぞれに直径8インチの外側・内側の充填排出弁が直列にあって打上げ前のETへの充填とMECO後のダンプに使われ、パネルR4のPROPELLANT FILL/DRAINスイッチ（OPEN・GND・CLOSE）でも操作できる。 */ }
            action <'F-MPS-DMP-02'> F_MPS_DMP_02 { doc /* 打上げ前、LO2は地上支援設備のLO2 T-0アンビリカルから外側・内側の充填排出弁とLO2供給配管マニホールドを通り、供給配管アンビリカル切離し部からETのLO2タンクへ入り、充填排出弁はスイッチをGNDにして打上げ処理システム（LPS）が制御する。 */ }
            action <'F-MPS-DMP-03'> F_MPS_DMP_03 { doc /* LH2は外側充填排出弁から入ってトッピング弁を通りエンジンを循環して熱調整した後ETへ送られてタンクのトッピングに使われ、LO2にはトッピング弁がなく熱調整に使ったLO2はエンジンのLO2ブリード弁と船外ブリード弁から船外へ捨てられる。 */ }
            action <'F-MPS-DMP-04'> F_MPS_DMP_04 { doc /* MECOの10秒後にLH2バックアップダンプ弁を2分間開き、LH2マニホールドの圧力で供給ライン逃がし弁が作動しないようにする。 */ }
            action <'F-MPS-DMP-05'> F_MPS_DMP_05 { doc /* ET分離後もSSMEに約1,700 lb、MPS供給ラインに約3,700 lbの推進薬が残って重心を約7インチ移動させ、残ったLH2は再突入時に大気の酸素と爆発性の混合気を作るおそれがある。 */ }
            action <'F-MPS-DMP-06'> F_MPS_DMP_06 { doc /* MPSダンプ（LO2・LH2同時）は完全に自動でMECOの2分後に始まり、MECO+20秒以降はMPS PRPLT DUMP SEQUENCEスイッチで手動で始めることもでき、LH2マニホールド圧が60 psiを超えるとMECO+2分より前に自動で始まる。 */ }
            action <'F-MPS-DMP-07'> F_MPS_DMP_07 { doc /* LO2ダンプでは、GPCがLO2マニホールド再加圧弁2個を開き、各制御器に主酸化剤弁（MOV）を開かせ、LO2プリバルブを開いてヘリウムの圧力でマニホールドのLO2をSSMEのノズルから押し出し、このダンプは推進的で約9〜11 fpsの軌道速度変化を与えて90秒間続く。 */ }
            action <'F-MPS-DMP-08'> F_MPS_DMP_08 { doc /* LH2ダンプはLO2ダンプと同時にGPCが内側・外側の充填排出弁、トッピング弁、LH2プリバルブを開いて行い、マニホールドのLH2はヘリウムの圧力を使わずに船外へ流れ出る。 */ }
            action <'F-MPS-DMP-09'> F_MPS_DMP_09 { doc /* ダンプ終了の15分後にGPCがLO2の内側・外側充填排出弁とLH2バックアップダンプ弁を開き、LO2・LH2のマニホールドを2分間同時に真空不活性化する。 */ }
            action <'F-MPS-DMP-10'> F_MPS_DMP_10 { doc /* 真空不活性化の後もLO2・LH2の内側充填排出弁は弁間の圧力上昇を防ぐため開いたままとし、OMS 2燃焼後のMM 106への移行時にはLH2系の2回目の真空不活性化（約3分）を行って、OMSの燃焼の振動で昇華した残りのLH2を排出する。 */ }
            action <'F-MPS-DMP-11'> F_MPS_DMP_11 { doc /* GH2のET加圧マニホールドは、MPSの電源断・隔離の後にパネルR4のH2 PRESS LINE VENTスイッチをOPENにして約1分間手動で真空不活性化する。 */ }
            action <'F-MPS-DMP-12'> F_MPS_DMP_12 { doc /* RTLSのダンプはMM 602で始まり、LO2はプリバルブとMOVから（動圧20 psf超では充填排出弁からも）ヘリウム加圧なしに自己沸騰で排出し、LH2はRTLSマニホールド加圧弁を通るヘリウムで2分間押し出しを補助する。 */ }
            action <'F-MPS-DMP-13'> F_MPS_DMP_13 { doc /* 再突入ではVREL 5,300 fpsでMANF PRESS LH2・LO2弁が開いてマニホールドを加圧し、地上でノズルにスロートプラグを付けるまで汚染物の侵入を防ぐ。 */ }
        }
        package <'SSD-FD-MPS-HE-001'> FN_MPS_HE {
            action <'F-MPS-HE-01'> F_MPS_HE_01 { doc /* MPSヘリウム系は4.7 ft3のタンク7個と17.3 ft3のタンク3個、調圧器・逆止弁・分配ライン・制御弁から成る。 */ }
            action <'F-MPS-HE-02'> F_MPS_HE_02 { doc /* ヘリウム系はエンジン内の飛行中のパージ、緊急の空圧停止でのエンジン弁の作動、PMSの空圧弁の作動に使われ、再突入では残りのヘリウムをパージと再加圧に使うが、OMSやRCSと違って推進薬タンクの加圧には使わない。 */ }
            action <'F-MPS-HE-03'> F_MPS_HE_03 { doc /* ヘリウム供給系は3基のエンジンごとの3系統と推進薬弁を操作する4つ目の空圧系統に分かれ、すべての弁はばねで一方に保持されて電気で他方へ作動し、タンク遮断弁はばねで閉・空圧で開となる。 */ }
            action <'F-MPS-HE-04'> F_MPS_HE_04 { doc /* タンクはチタンライナにガラス繊維を巻いた複合構造で、大タンクは直径40.3インチ・乾燥質量272 lb、小タンクは直径26インチ・73 lbで、打上げ前に4,100〜4,500 psiに充填される。 */ }
            action <'F-MPS-HE-05'> F_MPS_HE_05 { doc /* 4.7 ft3タンクのうち4個は後部胴体に、3個と17.3 ft3タンク3個はペイロードベイ下の中胴にあり、各大タンクは小タンク2個とつながって3個1組の3群を成し、各群は通常1基のエンジンだけに供給する（左・中央・右エンジンのヘリウム）。 */ }
            action <'F-MPS-HE-06'> F_MPS_HE_06 { doc /* 残る1個の4.7 ft3タンクは空圧ヘリウム供給タンクと呼ばれ、PMSのすべての空圧作動弁を動かす圧力を供給する。 */ }
            action <'F-MPS-HE-07'> F_MPS_HE_07 { doc /* 8個のタンク遮断弁が2個1組で各群と空圧タンクにつながり、エンジン系統では各組の2個が並列で二重冗長の供給回路の各脚の流れを制御し、各回路は逆止弁2個・フィルタ・遮断弁・調圧器・逃がし弁から成る。 */ }
            action <'F-MPS-HE-08'> F_MPS_HE_08 { doc /* エンジン系統の各タンク群には2個の調圧器が並列にあり、各調圧器は二重冗長の回路の1脚を730〜785 psiaに調圧して、主エンジンが必要とするヘリウムの全量を供給できる。 */ }
            action <'F-MPS-HE-09'> F_MPS_HE_09 { doc /* 空圧系統の調圧器は冗長でなく715〜770 psigに調圧し、その下流のLH2・LO2マニホールド調圧器はダンプとマニホールド加圧のときだけ使われる。 */ }
            action <'F-MPS-HE-10'> F_MPS_HE_10 { doc /* 空圧系統と左エンジン系統の間のクロスオーバ弁は冗長でない空圧調圧器のバックアップで、空圧ヘリウムの調圧器の故障や漏れのときに左エンジン系統から調圧したヘリウムを空圧の分配系へ送る。 */ }
            action <'F-MPS-HE-11'> F_MPS_HE_11 { doc /* 上昇中は4つのヘリウム系統が独立に動作するが、ダンプ・パージや漏れのときは相互接続弁（各エンジン系統にIN OPENとOUT OPENの2個、逆止弁で一方向に流す）で他の系統からヘリウムを引き込める。 */ }
            action <'F-MPS-HE-12'> F_MPS_HE_12 { doc /* 各SSMEにはエンジン系統のヘリウムで加圧されたマニホールドに電磁弁を持つ空圧制御組立が1基ずつあり、制御器の出力電子回路の指令で高圧酸化剤ターボポンプ中間シール空洞とプリバーナ酸化剤ドームのパージ、ポゴ系のポストチャージ、空圧停止を行う。 */ }
            action <'F-MPS-HE-13'> F_MPS_HE_13 { doc /* 再突入でVREL 5,300 fpsになるとヘリウムブローダウン弁が開いて後部区画・OMSポッド・LH2アンビリカル空洞を650秒間連続してパージし、ブローダウン弁は手動で操作できない。 */ }
        }
        package <'SSD-FD-MPS-OPS-001'> FN_MPS_OPS {
            action <'F-MPS-OPS-01'> F_MPS_OPS_01 { doc /* 機上ではMAIN ENGINE STATUSライトの赤（停止・停止後の段階）、出力30%未満、「SSME FAIL」メッセージをエンジン停止の手がかりとし、アボートにつながる判断には2つの手がかりを要する（A5-2）。 */ }
            action <'F-MPS-OPS-02'> F_MPS_OPS_02 { doc /* パネルC3のMAIN ENGINE LIMIT SHUT DNスイッチ（ENABLE・AUTO・INHIBIT）でリミットの有効・抑止を選び、AUTOでは1基の停止直後に残りのエンジンのリミットが抑止され、リミット抑止中のエンジン故障はおそらく機体の損傷を招く。 */ }
            action <'F-MPS-OPS-03'> F_MPS_OPS_03 { doc /* 1基停止でBFSを結合していない場合は、乗員ができるだけ早くスイッチをENABLE、AUTOの順に操作してリミットを再び有効にし、2基停止の場合はMECOまでリミットを抑止したままとする（A5-103）。 */ }
            action <'F-MPS-OPS-04'> F_MPS_OPS_04 { doc /* 指令経路故障のエンジンはGPCの指令で停止できないため、MECOの約30秒前（3基運転でVI = 23K fps、2基で24.5K fps、TALで22.5K fps）に交流電源スイッチとシャットダウン押しボタンで手動停止する（A5-106）。 */ }
            action <'F-MPS-OPS-05'> F_MPS_OPS_05 { doc /* データ経路故障の背後でエンジンが停止したとMCCが確かめたときは、そのエンジンの停止押しボタンを押して誘導・飛行制御のモードを切り替え、損傷した供給ラインを隔離するためプリバルブを閉じる（A5-105）。 */ }
            action <'F-MPS-OPS-06'> F_MPS_OPS_06 { doc /* 油圧・電気的ロックアップで最低出力より上に固着したエンジンは、3基運転のノミナル/ATOではMECO付近のLO2 NPSPを守るためVI = 23K fpsで停止押しボタンにより手動停止し、2基運転・RTLS・TALでは処置を要しない（A5-108）。 */ }
            action <'F-MPS-OPS-07'> F_MPS_OPS_07 { doc /* エンジン停止・制御器の冗長性の喪失・1チャネルの全レッドラインセンサの停止投票のときは、交流母線センサの単一故障で制御器への交流の1相を失わないよう、パネルR1の3個のAC BUS SNSRスイッチをOFFにする（A5-111）。 */ }
            action <'F-MPS-OPS-08'> F_MPS_OPS_08 { doc /* MPSエンジン系統の大きなヘリウム漏れは隔離でエンジンが停止しない限り隔離手順を行うが、主母線・APC・ALCの故障で脚Aの遮断弁が閉じている場合は、脚Bを閉じるとヘリウムの流れが止まって中間シールパージ圧の低下でレッドライン停止するため隔離を試みない（A5-151）。 */ }
            action <'F-MPS-OPS-09'> F_MPS_OPS_09 { doc /* 漏れなどでエンジンのヘリウムを補う相互接続は、通信がないときはタンク圧1,150 psiaか両調圧器の圧力が715（679）psia未満で行い、3基運転中は空圧系統だけを相互接続して必要ならその全量を使う（A5-152）。 */ }
            action <'F-MPS-OPS-10'> F_MPS_OPS_10 { doc /* ヘリウム漏れでエンジンをMECO前に手動停止するときは、交流電源スイッチではなく押しボタンで油圧的に停止し、これはMECO前の空圧停止よりヘリウムが少なくて済みMECO後のLO2ダンプ能力も残す（A5-153）。 */ }
            action <'F-MPS-OPS-11'> F_MPS_OPS_11 { doc /* ETのLH2アレージの漏れまたは3個のGH2流量制御弁の閉故障で低LH2 NPSPとなった場合は、最も早く複数エンジンの停止に耐える能力を得られるTALかACLSへのアボートを行う（A5-156）。 */ }
            action <'F-MPS-OPS-12'> F_MPS_OPS_12 { doc /* 挿入後にはMPSはほぼ無電力となり、パネルL4の主エンジン制御器への交流の遮断器18個を開き、パネルO17で4台のATVC・3台のEIU・2台のMECの電源を切り、ヘリウムタンク圧とA調圧器のハードウェア警報を抑止する。 */ }
            action <'F-MPS-OPS-13'> F_MPS_OPS_13 { doc /* 再突入でエンジンまたは空圧のヘリウム調圧器圧が800（810）psiaを超えたときは、ベント扉が閉じていれば直ちに対応するヘリウム遮断弁を閉じる（調圧器の開故障はベント扉が閉じていると約17秒で後部区画を過圧する）（A5-208）。 */ }
        }
        package <'SSD-FD-MPS-PMS-001'> FN_MPS_PMS {
            action <'F-MPS-PMS-01'> F_MPS_PMS_01 { doc /* 推進薬管理系（PMS）はマニホールド・分配ライン・弁から成り、ETのLO2・LH2をエンジンへ送るとともに、エンジンからETへ加圧ガスを送るラインを含む。 */ }
            action <'F-MPS-PMS-02'> F_MPS_PMS_02 { doc /* 後部胴体にはLO2用とLH2用の2本の直径17インチの供給配管マニホールドがあってそれぞれETの対応するラインにつながり、オービタ内で各エンジンへの3本の12インチ供給ラインに分かれる。 */ }
            action <'F-MPS-PMS-03'> F_MPS_PMS_03 { doc /* 各供給ラインのオービタとETの境界には切離し弁が2個（マニホールドのオービタ側とET側に1個ずつ）あり、4個ともET分離の前に自動で閉じられる。 */ }
            action <'F-MPS-PMS-04'> F_MPS_PMS_04 { doc /* 3本の12インチ供給ラインには各エンジンへのLO2・LH2を遮断または通すプリバルブがあり、大部分は自動で動作するが、パネルR4のLO2・LH2 PREVALVE LEFT・CTR・RIGHTスイッチ（OPEN・GPC・CLOSE）でも操作できる。 */ }
            action <'F-MPS-PMS-05'> F_MPS_PMS_05 { doc /* LH2・LO2の各マニホールドには直径1インチのラインが供給ライン逃がし遮断弁と逃がし弁へつながり、遮断弁がMECO後に自動で開くとマニホールドの過大な圧力を逃がし弁から船外へ逃がす。 */ }
            action <'F-MPS-PMS-06'> F_MPS_PMS_06 { doc /* アレージ加圧系はGO2用とGH2用の2本のET加圧マニホールドから成り、各マニホールドには各エンジンから1本ずつ計3本の直径0.63インチの加圧ラインがあって、ETに入る前に共通のマニホールドに合流する。 */ }
            action <'F-MPS-PMS-07'> F_MPS_PMS_07 { doc /* 上昇中のLO2タンク圧は固定オリフィスで20〜25 psigに保たれ、30 psigを超えるとLO2タンクのベント・逃がし弁から逃がされる。 */ }
            action <'F-MPS-PMS-08'> F_MPS_PMS_08 { doc /* LH2タンク圧は各SSMEの可変・固定オリフィスで32〜34 psiaに保たれ、流量制御弁は3個のLH2圧力トランスデューサの1つで制御されて32 psia未満で開き33 psiaで閉じ、28 psiaを下回るとパネルR2のMPS LH2 ULL PRESSスイッチをOPENにして3個の流量制御弁を全開にする。 */ }
            action <'F-MPS-PMS-09'> F_MPS_PMS_09 { doc /* 流量制御弁の制御系は単一系統で、アレージ圧センサ1は中央、2は左、3は右のSSMEの電子回路だけにつながり、流量制御弁1個の閉故障ではアレージ圧は28.0 psiaを下回らないが、2個が閉故障すると28.0 psia以上に保てない（A5-154）。 */ }
            action <'F-MPS-PMS-10'> F_MPS_PMS_10 { doc /* 推進薬の低液位による停止のため、LO2の枯渇は供給配管マニホールド内の4個のセンサで、LH2の枯渇はLH2タンク底部の4個のセンサで検知し、いずれかの系で4個のうち2個が乾きを示すとGPCが制御器にMECOを指令する。 */ }
            action <'F-MPS-PMS-11'> F_MPS_PMS_11 { doc /* MPSの弁は電気式か空圧式で、大きな荷重のかかる液体推進薬の流れの制御には空圧弁を、気体推進薬の流れのような軽い荷重には電気弁を用いる。 */ }
            action <'F-MPS-PMS-12'> F_MPS_PMS_12 { doc /* 空圧弁のうちタイプ1（開閉ともに空圧を要する双安定弁）は17インチ切離し弁・プリバルブ・充填排出弁・LH2の4インチ再循環切離し弁に、タイプ2（ばねで一方の位置に戻る弁）はLH2 RTLSダンプ弁・逃がし遮断弁・トッピング弁などに使われる。 */ }
            action <'F-MPS-PMS-13'> F_MPS_PMS_13 { doc /* LO2・LH2のマニホールド圧は、OMS/MPS MEDS表示の2個のMPS PRESS ENG MANFメータとBFS GNC SYS SUMM 1（MANF P LH2・LO2）で監視できる。 */ }
        }
        package <'SSD-FD-MPS-SSME-001'> FN_MPS_SSME {
            action <'F-MPS-SSME-01'> F_MPS_SSME_01 { doc /* 3基のSSMEは再使用可能な高性能の可変推力液体ロケットエンジンで、液体水素を燃料兼冷却材、液体酸素を酸化剤とし、2基のプリバーナで高圧・比較的低温の部分燃焼を行ってから主燃焼室で高圧・高温の完全燃焼を行う二段燃焼サイクルを用いる。 */ }
            action <'F-MPS-SSME-02'> F_MPS_SSME_02 { doc /* エンジンは中央（1番）・左（2番）・右（3番）と呼ばれ、各エンジンは30回の始動で15,000秒の運転に耐えるよう設計され、混合比は絞り範囲全体で6:1、ノズル面積比は77.5:1、長さ14 ft・ノズル出口径7.5 ft、質量は約7,000 lbである。 */ }
            action <'F-MPS-SSME-03'> F_MPS_SSME_03 { doc /* 推力は定格の67〜109%の範囲を1%刻みで絞ることができ、100%は海面375,000 lb・真空470,000 lb、104%は海面393,800 lb・真空488,800 lb、109%は海面417,300 lb・真空513,250 lbに相当する。 */ }
            action <'F-MPS-SSME-04'> F_MPS_SSME_04 { doc /* 3基のエンジンには同じ推力指令が同時に与えられ、通常はGPCからエンジン制御器を通じて自動で与えられるが、一部の非常時には操縦士のスピードブレーキ/推力制御器で手動で絞ることができる。 */ }
            action <'F-MPS-SSME-05'> F_MPS_SSME_05 { doc /* SSMEの主要構成要素は、燃料・酸化剤のターボポンプ、プリバーナ、高温ガスマニホールド、主燃焼室、ノズル、酸化剤熱交換器、推進薬弁である。 */ }
            action <'F-MPS-SSME-06'> F_MPS_SSME_06 { doc /* 低圧燃料ターボポンプは液体水素を30 psiaから276 psiaへ、高圧燃料ターボポンプは276 psiaから6,515 psiaへ昇圧し、高圧ポンプの吐出は主燃料弁の後で主燃焼室の冷却・プリバーナ供給・ノズル冷却の3経路に分かれる。 */ }
            action <'F-MPS-SSME-07'> F_MPS_SSME_07 { doc /* 低圧酸化剤ターボポンプは液体酸素を100 psiaから422 psiaへ、高圧酸化剤ターボポンプの主ポンプは422 psiaから4,300 psiaへ昇圧し、その吐出の一部は低圧酸化剤ターボポンプのタービン駆動と主酸化剤弁経由の主燃焼室への供給に使われる。 */ }
            action <'F-MPS-SSME-08'> F_MPS_SSME_08 { doc /* 高圧酸化剤ターボポンプのタービンとポンプは同じ軸にあるため、両者の間の空洞をMPSのエンジン用ヘリウムで運転中連続してパージし、空洞のヘリウム圧が運転限界を下回ると主エンジン制御器がエンジンを自動停止する。 */ }
            action <'F-MPS-SSME-09'> F_MPS_SSME_09 { doc /* 主噴射器の中心には二重冗長の点火器を持つ小さな点火室があり、始動時に燃焼を始めさせて、燃焼が自立する約3秒後に切られる。 */ }
            action <'F-MPS-SSME-10'> F_MPS_SSME_10 { doc /* 酸化剤熱交換器は高圧酸化剤ターボポンプ吐出の液体酸素を気化してタンク加圧とポゴ抑制に供し、ポゴ抑制系は高圧酸化剤ターボポンプ入口ダクトに取り付けた0.6 ft3のアキュムレータで機体からの低周波の流れの振動を抑える。 */ }
            action <'F-MPS-SSME-11'> F_MPS_SSME_11 { doc /* エンジン停止時にはポゴアキュムレータをMPSヘリウムで加圧して高圧酸化剤ターボポンプ入口に正圧を与え、MECOに伴う加速度の急減によるタービンのキャビテーションと破損を防ぐ。 */ }
            action <'F-MPS-SSME-12'> F_MPS_SSME_12 { doc /* 各エンジンの5個の推進薬弁（酸化剤プリバーナ酸化剤弁・燃料プリバーナ酸化剤弁・主酸化剤弁・主燃料弁・冷却材制御弁）は油圧で駆動されて制御器の電気信号で制御され、バックアップとしてMPSエンジン用ヘリウムで全閉できる。 */ }
        }
        package <'SSD-FD-MPS-TVC-001'> FN_MPS_TVC {
            action <'F-MPS-TVC-01'> F_MPS_TVC_01 { doc /* オービタの3系統の油圧系は各SSMEへ油圧を供給してエンジン弁の作動と推力方向制御を行い、3系統はパネルR4のHYDRAULICS MPS/TVC ISOL VLVスイッチ（各系統1個）で制御されるTVC弁へ分配される。 */ }
            action <'F-MPS-TVC-02'> F_MPS_TVC_02 { doc /* 3個のMPS/TVC遮断弁を開くと5個の油圧作動エンジン弁に油圧がかかり、各エンジンの弁はすべて同じ系統（中央エンジンは1系統、左は2系統、右は3系統）から油圧を受ける。 */ }
            action <'F-MPS-TVC-03'> F_MPS_TVC_03 { doc /* 各エンジン弁のアクチュエータは制御器のチャネルA/サーボ弁1とチャネルB/サーボ弁2の二重冗長の信号で制御され、油圧系が故障すると油圧作動弁はすべてそのエンジンのヘリウムで吹き閉じられる。 */ }
            action <'F-MPS-TVC-04'> F_MPS_TVC_04 { doc /* 制御器が5個の油圧作動エンジン弁のいずれかを想定外の位置に検知すると5個の弁すべてを最後の位置で油圧的に隔離する油圧ロックアップとなり、弁のドリフトは抑えられるが防げず、停止は指令でも手動でもエンジンのヘリウムによる空圧で行われる。 */ }
            action <'F-MPS-TVC-05'> F_MPS_TVC_05 { doc /* MPS/TVC遮断弁は6台の主エンジンTVCアクチュエータへの油圧供給にも開く必要があり、各SSMEにヨー用とピッチ用の2台のサーボアクチュエータがあって、オービタの推力構造とSSMEのパワーヘッドに取り付けられる。 */ }
            action <'F-MPS-TVC-06'> F_MPS_TVC_06 { doc /* 各サーボアクチュエータは3系統のうち2系統（主系統と待機の副系統）から油圧を受け、専用の切替弁が主系統の圧力の喪失時に自動で副系統へ切り替えてアクチュエータの機能を保つ。 */ }
            action <'F-MPS-TVC-07'> F_MPS_TVC_07 { doc /* アクチュエータの主/副の系統は、中央エンジンがピッチ1/3・ヨー3/1、左エンジンがピッチ2/1・ヨー1/2、右エンジンがピッチ3/2・ヨー2/3である。 */ }
            action <'F-MPS-TVC-08'> F_MPS_TVC_08 { doc /* ピッチ・アクチュエータはエンジンを据付けの零位置から上下に最大10.5°、ヨー・アクチュエータは左右に最大8.5°首振りさせ、左右エンジンの零位置はX軸から10°上・3.5°外向き、中央エンジンは16°上である。 */ }
            action <'F-MPS-TVC-09'> F_MPS_TVC_09 { doc /* 軌道上ではHYDRAULICS MPS/TVC ISOL VLV SYS 1〜3スイッチをCLOSEにして、遮断弁下流の油圧漏れから守る。 */ }
            action <'F-MPS-TVC-10'> F_MPS_TVC_10 { doc /* 軌道上は主エンジンを格納位置から首振りさせる必要がなく、遮断弁を閉じている間は各MPS/TVC機器内の油圧の供給・戻りラインがつながって熱調整のため作動油が循環する。 */ }
            action <'F-MPS-TVC-11'> F_MPS_TVC_11 { doc /* T-3分25秒にジンバル試験が始まって各ジンバル・アクチュエータを所定の伸縮の動作で動かし、すべて正常ならT-2分15秒にエンジンを所定の位置へ首振りさせて点火まで保つ。 */ }
            action <'F-MPS-TVC-12'> F_MPS_TVC_12 { doc /* MPSダンプの後、SSMEは空力加熱を減らすためノズルを内側に寄せた再突入の格納位置へ首振りされる。 */ }
            action <'F-MPS-TVC-13'> F_MPS_TVC_13 { doc /* 軌道離脱準備ではATVCを再び通電し、軌道上でずれた主エンジンのノズルを再突入の格納位置へ戻すとともに、滑空中に自動で行うドラッグシュート展開のためのSSMEの再配置に備える。 */ }
        }
        package <'SSD-FD-OMS-001'> FN_OMS {
            action <'F-OMS-01'> F_OMS_01 { doc /* OMSは、軌道投入、軌道の円化、軌道遷移、ランデブ、軌道離脱のための推力を供給し、各OMSポッドはRCSへ1,000 lb以上の推進薬を供給できる。 */ }
            action <'F-OMS-02'> F_OMS_02 { doc /* OMSは後部胴体の両側にある独立した2つのポッドに収められ、ポッドには後部RCSも同居する（OMS/RCSポッド）。 */ }
            action <'F-OMS-03'> F_OMS_03 { doc /* 各ポッドにOMSエンジン1基と推進薬の加圧・貯蔵・分配機器があり、OMSエンジン1基だけでも噴射でき、左右のポッドを結ぶクロスフィード配管で一方のポッドの推進薬を他方のポッドのエンジンへ送れる。 */ }
            action <'F-OMS-04'> F_OMS_04 { doc /* 燃料はモノメチルヒドラジン、酸化剤は四酸化二窒素で、ヘリウムで加圧されて供給され、接触すると着火する（ハイパーゴリック）。 */ }
            action <'F-OMS-05'> F_OMS_05 { doc /* 各OMSエンジンの推力は6,087 lbである。 */ }
            action <'F-OMS-06'> F_OMS_06 { doc /* 軌道離脱噴射の目標データは地上で計算され、アップリンクで機上のGPCに格納される。 */ }
        }
        package <'SSD-FD-OMS-ENG-001'> FN_OMS_ENG {
            action <'F-OMS-ENG-01'> F_OMS_ENG_01 { doc /* 各OMSエンジンの推力は6,087 lbで、典型的な機体重量では2基で約2 ft/s²（0.06 g）の加速度を生じ、満載のタンクを使い切ると約1,000 ft/sの速度変化が得られる。 */ }
            action <'F-OMS-ENG-02'> F_OMS_ENG_02 { doc /* 各OMSエンジンは1,000回の始動と累積15時間の噴射ができ、噴射の最短時間は2秒である。 */ }
            action <'F-OMS-ENG-03'> F_OMS_ENG_03 { doc /* 二元推進薬弁組立は燃料弁2個と酸化剤弁2個をそれぞれ直列に持ち、漏れに対する冗長な防護となる一方、推進薬を流すには直列の両方の弁が開く必要がある。 */ }
            action <'F-OMS-ENG-04'> F_OMS_ENG_04 { doc /* ボール弁はばねで閉に保たれた空気圧ピストンで開閉され、GPCの指令で動くソレノイド式の制御弁がピストンへの窒素の流れを制御し、2個の制御弁が両方働かないとボール弁は開かない。 */ }
            action <'F-OMS-ENG-05'> F_OMS_ENG_05 { doc /* 燃料は燃焼室を囲む冷却ジャケットを通って燃焼室を冷やしてから噴射器に達し、酸化剤は二元推進薬弁から噴射器へ直接送られる。 */ }
            action <'F-OMS-ENG-06'> F_OMS_ENG_06 { doc /* 燃料噴射器温度は冷却ジャケットを出た燃料の温度で燃焼室壁の温度を間接的に示し、噴射中は約218°F、安全な運転の限界は260°Fである。 */ }
            action <'F-OMS-ENG-07'> F_OMS_ENG_07 { doc /* 噴射していないときのエンジン入口圧は推進薬タンク圧（通常254 psi）に一致し、噴射中は燃料が約220〜235 psi、酸化剤が約200〜206 psiに下がり、入口圧は推進薬流量の間接的な指標となる。 */ }
            action <'F-OMS-ENG-08'> F_OMS_ENG_08 { doc /* GN2系は各エンジンの燃焼室の脇にある球形のタンク（ボール弁の作動とパージ10回分）から、圧力隔離弁・調圧器・逆止弁・アキュムレータを経て制御弁とパージ弁へ窒素を送る。 */ }
            action <'F-OMS-ENG-09'> F_OMS_ENG_09 { doc /* 調圧器はタンク圧（最大3,000 psig）を作動圧315〜360 psigに下げ、19立方インチのアキュムレータは圧力隔離弁が閉じていても少なくとも1回はボール弁を作動させられる。 */ }
            action <'F-OMS-ENG-10'> F_OMS_ENG_10 { doc /* 噴射が終わると自動の噴射シーケンスにより、推力停止の0.36秒後に直列2個のパージ弁が開いて窒素が燃焼室と噴射器を2秒間吹き抜け、残った燃料を除いて安全な再始動を可能にする。 */ }
            action <'F-OMS-ENG-11'> F_OMS_ENG_11 { doc /* エンジンの故障検知は冗長管理ソフトウェアが行い、PASSは速度比較（MECO後のみ）と燃焼室圧比較を、BFSは燃焼室圧比較だけを使う。 */ }
            action <'F-OMS-ENG-12'> F_OMS_ENG_12 { doc /* 燃料噴射器温度が260°Fを超え、燃料入口圧がエンジンの製造番号（101〜117）ごとに定めた上限以上であれば、ボール弁より下流の燃料の閉塞としてエンジンを喪失とする（A6-3C）。 */ }
            action <'F-OMS-ENG-13'> F_OMS_ENG_13 { doc /* SODBは安全なエンジン運転の最低高度を70,000 ftとし、通常運用での噴射間の最小休止時間を240秒とする。 */ }
        }
        package <'SSD-FD-OMS-HE-001'> FN_OMS_HE {
            action <'F-OMS-HE-01'> F_OMS_HE_01 { doc /* 各ポッドのヘリウム加圧系は、高圧ヘリウムタンク、ヘリウム圧力隔離弁2個、二重調圧器組立2組、酸化剤タンク側だけの並列の蒸気隔離弁、直並列の逆止弁組立、逃し弁から成る。 */ }
            action <'F-OMS-HE-02'> F_OMS_HE_02 { doc /* 1基のヘリウムタンクが燃料タンクと酸化剤タンクの両方を加圧するため両タンクが同じ圧力に保たれて混合比の誤りが避けられ、ヘリウムタンクの使用圧力範囲は4,800〜390 psiaである。 */ }
            action <'F-OMS-HE-03'> F_OMS_HE_03 { doc /* 推進薬の残量が最大ブローダウン（OMSタンクで約39%）を下回ると、タンク内に残ったヘリウムの圧力だけでそのタンクの推進薬を使い切ることができる。 */ }
            action <'F-OMS-HE-04'> F_OMS_HE_04 { doc /* ヘリウム圧力弁A・Bは並列でヘリウムの冗長な経路となり、ばねで閉・ソレノイドで開く弁で、噴射以外は閉じておき、スイッチがGPC位置なら自動の噴射シーケンスが噴射の開始時に開き終了時に閉じる。 */ }
            action <'F-OMS-HE-05'> F_OMS_HE_05 { doc /* 圧力弁を手動で開くときはAとBの間に2秒置き、急な圧力変化によるウォータハンマを防ぐ。 */ }
            action <'F-OMS-HE-06'> F_OMS_HE_06 { doc /* 各調圧器組立は流量制限器と直列の一次・二次の調圧器を持ち、通常は一次（正常流量で252〜262 psig）が制御し、一次が故障すると二次（259〜269 psig）が圧力制御を続ける。 */ }
            action <'F-OMS-HE-07'> F_OMS_HE_07 { doc /* 酸化剤タンクへの加圧配管の蒸気隔離弁は、逆止弁を透過した酸化剤の蒸気が上流へ移って燃料系に入り、ハイパーゴリック反応を起こすのを防ぐ。 */ }
            action <'F-OMS-HE-08'> F_OMS_HE_08 { doc /* 逆止弁組立は4個の独立した逆止弁を直並列につないだもので、並列の経路がヘリウムの冗長な経路を、直列が逆流に対する冗長な防護を与え、各組立の入口にフィルタがある。 */ }
            action <'F-OMS-HE-09'> F_OMS_HE_09 { doc /* 逆止弁の下流の逃し弁は推進薬タンクを過圧から守り、破裂板は303〜313 psigで破れ、逃し弁は286 psigで開いて280 psigで再着座する。 */ }
            action <'F-OMS-HE-10'> F_OMS_HE_10 { doc /* ヘリウムタンク圧が390 psia未満になるか、すべての加圧経路が閉じた場合は、ヘリウムタンクを喪失とする（A6-1）。 */ }
            action <'F-OMS-HE-11'> F_OMS_HE_11 { doc /* 漏れているヘリウム系は、ヘリウムタンク圧が正常な推進薬タンク圧を保てる限り、両エンジンへの供給に使ってアレージ容積を増やしてよい（A6-202）。 */ }
            action <'F-OMS-HE-12'> F_OMS_HE_12 { doc /* IOA（1988年）は、並列の一方の圧力弁の流れの制限は両弁を開くOMS-1・OMS-2では検出できないが、発射台での予圧とOMS-2以後の噴射では弁を単独で使うため検出できるとして指摘を取り下げた。 */ }
        }
        package <'SSD-FD-OMS-OPS-001'> FN_OMS_OPS {
            action <'F-OMS-OPS-01'> F_OMS_OPS_01 { doc /* 6 fps未満の速度変化にはRCSを使い、6 fpsを超える場合はエンジンの寿命の点で始動回数を減らすため1基の噴射が好まれ、大きな速度変化や重要な噴射には2基を使う。 */ }
            action <'F-OMS-OPS-02'> F_OMS_OPS_02 { doc /* OMS噴射はMM 104、105、202、302でのみ行え、OMSの推進薬投棄はMM 102、103、304、601、602で行える。 */ }
            action <'F-OMS-OPS-03'> F_OMS_OPS_03 { doc /* 乗員はMNVR表示で2基・1基・RCSを選び、PEG 4またはPEG 7の目標を入れて誘導に噴射解を計算させ、点火の15秒前に点滅するEXECの表示でEXECキーを押して点火を許可する。 */ }
            action <'F-OMS-OPS-04'> F_OMS_OPS_04 { doc /* 噴射シーケンスは選ばれたエンジンに応じてヘリウム蒸気隔離弁とGN2制御弁を開く指令を出し、エンジン故障フラグを監視して、乗員がOMS ENGスイッチをOFFにして故障を確認すると停止指令を出す。 */ }
            action <'F-OMS-OPS-05'> F_OMS_OPS_05 { doc /* 軌道上のOMS噴射の準備ではOMS/MPS表示でヘリウムタンク圧が1,500 psiaを超え、N2タンク圧が564 psiaを超えることを確かめ、限界内でなければ噴射しない。 */ }
            action <'F-OMS-OPS-06'> F_OMS_OPS_06 { doc /* OMSのレッドラインはタンク内に捕捉される644 lb、分散、急角度の軌道離脱のΔV、軌道離脱の延期日（156 lb）、エンジン故障（106 lb）などを確保し、違反して推進薬の融通もできなければ次のPLSで軌道離脱する（A6-303A）。 */ }
            action <'F-OMS-OPS-07'> F_OMS_OPS_07 { doc /* OMSの推進薬は左右のポッドの不均衡でY方向の重心のずれをゼロにするよう管理され、インタコネクトの予定は軌道離脱の前の重心を改善するために変更できる（A6-353B）。 */ }
            action <'F-OMS-OPS-08'> F_OMS_OPS_08 { doc /* 着陸時のOMS推進薬は各ポッド22%以下とし、1,000 lb（約8%）のOMS推進薬はX方向の重心を1.5インチ後方へ、Y方向を0.5インチ左右へ動かす。 */ }
            action <'F-OMS-OPS-09'> F_OMS_OPS_09 { doc /* OMSの故障管理（A6-51）は、ヘリウムタンク・ヘリウムレグ・GN2タンク・GN2アキュムレータ・推進薬タンク・入口配管・エンジンの1〜2箇所の漏れや故障について、上昇の段階ごとの処置と噴射の構成（2基2ポッドTETP、1基良好ポッドSEGPなど）を定める。 */ }
            action <'F-OMS-OPS-10'> F_OMS_OPS_10 { doc /* 1基のOMSエンジンを失った場合は残るOMSエンジンとRCSの+Xジェット4基が残り2つの軌道離脱手段となり、+Xジェットを噴射したことがなければEOMまで続ける前に試験噴射する（A6-107B）。 */ }
            action <'F-OMS-OPS-11'> F_OMS_OPS_11 { doc /* OMS/RCSのGo/No-Go基準では、OMSエンジン2基の喪失、推進薬タンク1基の漏れ、入口配管1本の漏れ、クロスフィードの2流路の喪失が次のPLSで突入する理由になる（A6-1001）。 */ }
            action <'F-OMS-OPS-12'> F_OMS_OPS_12 { doc /* OMS噴射中は44.8 kbpsの高速GNCダウンリストが必要で、OMSのPcや入口圧など故障モードの判定に要る値は低速のダウンリストにないためである（A6-103）。 */ }
        }
        package <'SSD-FD-OMS-PSD-001'> FN_OMS_PSD {
            action <'F-OMS-PSD-01'> F_OMS_PSD_01 { doc /* 推進薬貯蔵・分配系は各ポッドの燃料タンク1基と酸化剤タンク1基、推進薬供給配管、クロスフィード配管、隔離弁、クロスフィード弁から成る。 */ }
            action <'F-OMS-PSD-02'> F_OMS_PSD_02 { doc /* 両ポッドのOMS推進薬で、65,000 lbのペイロードを積んだオービタに1,000 ft/sの速度変化を与えられる。 */ }
            action <'F-OMS-PSD-03'> F_OMS_PSD_03 { doc /* 燃料と酸化剤は各ポッド内のドーム付き円筒形のチタン製タンクに貯蔵され、タンクはヘリウム系で加圧され、内部は前室と後室に分かれる。 */ }
            action <'F-OMS-PSD-04'> F_OMS_PSD_04 { doc /* 後端の推進薬取得・保持組立は前後室を仕切るメッシュスクリーンと取得装置から成り、無重量下ではスクリーンの表面張力が後室に推進薬を保持する。 */ }
            action <'F-OMS-PSD-05'> F_OMS_PSD_05 { doc /* 取得装置は4本のスタブギャラリとコレクタマニホールドから成り、コレクタのガス阻止スクリーンがガスの吸込みを防ぐため、RCSによる推進薬の沈降操作なしにOMSエンジンを点火できる。 */ }
            action <'F-OMS-PSD-06'> F_OMS_PSD_06 { doc /* 推進薬タンクの公称の使用圧力は250 psi、最大使用圧力の限界は313 psiaである。 */ }
            action <'F-OMS-PSD-07'> F_OMS_PSD_07 { doc /* 各タンクの静電容量式の計測系は前後のプローブとトータライザから成り、トータライザはOMS弁の動作情報からどのエンジンがどのタンクで噴射しているかを判断して、全量・後室量・低レベルの信号を出す。 */ }
            action <'F-OMS-PSD-08'> F_OMS_PSD_08 { doc /* トータライザは噴射開始から14.8秒間は既定の流量で表示量を減じてからプローブの出力で更新し、残量が5%に下がると低レベル信号を出す。 */ }
            action <'F-OMS-PSD-09'> F_OMS_PSD_09 { doc /* タンク隔離弁A・Bは各ポッドで推進薬タンクとエンジン・クロスフィード弁の間に並列に置かれ、三相（2相でも可）の交流モータで駆動され、パネルO8のLEFT・RIGHT OMS TANK ISOLATIONスイッチ（OPEN・GPC・CLOSE）で制御される。 */ }
            action <'F-OMS-PSD-10'> F_OMS_PSD_10 { doc /* 弁が指令位置に達すると電動機制御組立の論理が弁アクチュエータの電力を切り、各スイッチの上のトークバックは弁のマイクロスイッチにより開・過渡（バーバーポール）・閉を示す。 */ }
            action <'F-OMS-PSD-11'> F_OMS_PSD_11 { doc /* 後室量が11%未満でスクリーンが露出しているときは、ヘリウムの吸込みを防ぐため、OMSエンジンを再始動する前にRCSの+Xジェット2基で15秒の沈降噴射を行う（A6-102）。 */ }
            action <'F-OMS-PSD-12'> F_OMS_PSD_12 { doc /* 打上げ時の搭載量はポッドあたり燃料2,038〜4,711.5 lb・酸化剤3,362〜7,743.5 lbの範囲とし、TAEMインタフェースでは酸化剤1,707 lb・燃料1,032 lb未満（搭載量の約22%）とする。 */ }
            action <'F-OMS-PSD-13'> F_OMS_PSD_13 { doc /* STS-114では最初の打上げ試行の後に電源を再投入するとトータライザの出力が既知の特性どおり無作為な値となり、5%未満の表示で警報が出たが、OMSアシストの14秒後にプローブから正しい値に更新された。 */ }
        }
        package <'SSD-FD-OMS-THM-001'> FN_OMS_THM {
            action <'F-OMS-THM-01'> F_OMS_THM_01 { doc /* OMSの熱制御はOMS機器を囲むポッド内面のストリップヒータと断熱材で行い、クロスフィード配管は巻付けヒータと断熱材で調整され、ヒータがタンクと配管の推進薬の凍結を防ぐ。 */ }
            action <'F-OMS-THM-02'> F_OMS_THM_02 { doc /* 各OMS/RCSポッドは8つのヒータ区域に分かれ、各区域のA・B素子は素子ごとのサーモスタットで55〜75°Fに制御され、パネルA14のRCS/OMS HEATERS LEFT POD・RIGHT PODのA AUTO・B AUTOスイッチで操作される。 */ }
            action <'F-OMS-THM-03'> F_OMS_THM_03 { doc /* 後部胴体のクロスフィード配管は11のヒータ区域に分かれ、各区域をA・B系統が並列に加熱して制御サーモスタットが55〜75°Fに保ち、各回路には故障して入りっぱなしのヒータに備える過温度サーモスタットがある。 */ }
            action <'F-OMS-THM-04'> F_OMS_THM_04 { doc /* ポッド内とクロスフィード配管のサーモスタット付近の温度センサの値は、SM SPEC 89 PRPLT THERMAL表示（POD・OMS CRSFDの項目）とテレメトリに送られる。 */ }
            action <'F-OMS-THM-05'> F_OMS_THM_05 { doc /* OMSの推進薬の温度が40°F未満か100°F超になると推進薬タンクを喪失とし、これは安全に始動・運転できることが分かっているエンジンの設計仕様の範囲である（A6-2C）。 */ }
            action <'F-OMS-THM-06'> F_OMS_THM_06 { doc /* クロスフィード配管の温度が40°F未満か125°F超になるとクロスフィード配管を喪失とし、30°F未満では酸化剤が凍って配管を破損・閉塞するおそれがある（A6-6A）。 */ }
            action <'F-OMS-THM-07'> F_OMS_THM_07 { doc /* ポッドのヒータはA・Bのパッチが重ねて貼られて両方を入れると剥離のおそれがあるため同時には使わず、クロスフィード配管のヒータはA・B回路を1本に巻いたもので両方を同時に入れられる（A6-251A）。 */ }
            action <'F-OMS-THM-08'> F_OMS_THM_08 { doc /* 上昇中（OPS 1）はポッドのヒータをすべて切り（ポッドは打上げ前に高温のGN2で温められる）、突入のための着席時からもポッドのヒータは切っておく（A6-254B・C）。 */ }
            action <'F-OMS-THM-09'> F_OMS_THM_09 { doc /* クロスフィード配管のヒータは軌道上では一方（AかB）を入れ、突入のための着席時からはA・B両方を入れて突入中も入れたままにする（A6-255B・C）。 */ }
            action <'F-OMS-THM-10'> F_OMS_THM_10 { doc /* 推進薬を含む機器を守る重要なヒータ回路はすべて冗長で、AとBの両方を失って姿勢でも熱の限界を保てなければ、次のPLSで突入する（A6-252）。 */ }
            action <'F-OMS-THM-11'> F_OMS_THM_11 { doc /* 故障処置手順（MAL 11.3）は、SPEC 89やBFS THERMAL表示の限界外れに対してA14でもう一方のヒータ・サーモスタット回路へ切り替えて切り分け、ポッドでA・B回路を同時に使うとヒータが焼損すると注意する。 */ }
            action <'F-OMS-THM-12'> F_OMS_THM_12 { doc /* STS-114では左上部Yウェブの構造温度がSRB点火時から不規則な指示となり（IFA STS-114-V-03）、ヒータの性能は冗長な計測で監視された。 */ }
        }
        package <'SSD-FD-OMS-TVC-001'> FN_OMS_TVC {
            action <'F-OMS-TVC-01'> F_OMS_TVC_01 { doc /* OMSエンジンはジンバル架台に取り付けられ、2基の電気機械式アクチュエータでヨーとピッチに振られ、デジタルオートパイロットまたは手動操縦の指令で推力の向きを制御して噴射中の機体を操舵する。 */ }
            action <'F-OMS-TVC-02'> F_OMS_TVC_02 { doc /* 1基で噴射するときは推力を重心に向け、2基のときは両方の推力をX軸に平行にし、1基の噴射ではRCSによるロール制御が必要になる。 */ }
            action <'F-OMS-TVC-03'> F_OMS_TVC_03 { doc /* TVC系はジンバルリング組立、ジンバルアクチュエータ組立2組、ジンバルアクチュエータ制御器2台から成る。 */ }
            action <'F-OMS-TVC-04'> F_OMS_TVC_04 { doc /* 各アクチュエータは冗長な2台のブラシレス直流電動機と歯車列、1本のジャッキねじとナットチューブ、冗長な直線位置フィードバック変換器を持ち、一次・二次の駆動系は分離されて同時には運転されない。 */ }
            action <'F-OMS-TVC-05'> F_OMS_TVC_05 { doc /* 一次の電子制御器からのGPCの位置指令で一次の直流電動機が動き、一次が働かないときは二次の電子制御器からの指令で二次の電動機が動き、各駆動系のノーバック装置が待機系の逆駆動を防ぐ。 */ }
            action <'F-OMS-TVC-06'> F_OMS_TVC_06 { doc /* 作動・待機の制御チャネルの電気インタフェース・電源・電子制御要素は別々の筐体（作動・待機アクチュエータ制御器）に収められてOMS/RCSポッドの構造に取り付けられ、両者は電気的・機械的に互換である。 */ }
            action <'F-OMS-TVC-07'> F_OMS_TVC_07 { doc /* ジンバルの可動範囲はピッチ±6°・ヨー±7°である。 */ }
            action <'F-OMS-TVC-08'> F_OMS_TVC_08 { doc /* TVC指令SOPはピッチ・ヨーのアクチュエータ指令とアクチュエータ電源選択の離散信号を出し、OMS-1・OMS-2、軌道巡航、軌道離脱、軌道離脱巡航、RTLSアボート（MM 104、105、201、301、302、303、601）で働く。 */ }
            action <'F-OMS-TVC-09'> F_OMS_TVC_09 { doc /* 乗員はMNVR表示の項目入力（PRI 28・29、SEC 30・31）でピッチ・ヨーのアクチュエータの一次・二次の電動機を選ぶか、電動機を切ることができる。 */ }
            action <'F-OMS-TVC-10'> F_OMS_TVC_10 { doc /* ジンバルの故障検知は動くべきときに閾値以上動いたかを確かめ、故障の計数がIロード値の4に達するとアクチュエータを故障と宣言し、乗員はMNVR表示の項目入力で二次のアクチュエータ電子回路を選ぶ。 */ }
            action <'F-OMS-TVC-11'> F_OMS_TVC_11 { doc /* OMS TVCにはFF MDMからのイネーブル離散信号とFA MDMからの指令が必要である。 */ }
            action <'F-OMS-TVC-12'> F_OMS_TVC_12 { doc /* 上昇中の高動圧域でTVCの動きが2つの情報源で確認された場合は、エンジンベルが空力で損傷したおそれがあるため、アボートの推進薬投棄を含むすべての用途でそのエンジンを故障とし、OMS ENGスイッチを直ちにOFFにする（A6-101A）。 */ }
        }
        package <'SSD-FD-OMS-XFD-001'> FN_OMS_XFD {
            action <'F-OMS-XFD-01'> F_OMS_XFD_01 { doc /* 一方のポッドのOMSエンジンに他方のポッドの推進薬を送ることをOMSクロスフィードといい、ポッド間の推進薬重量の均衡を取るときや、エンジンまたはタンクが故障したときに行う。 */ }
            action <'F-OMS-XFD-02'> F_OMS_XFD_02 { doc /* クロスフィード配管はタンク隔離弁と二元推進薬弁の間で左右のOMS推進薬配管を結び、各配管には並列2個のクロスフィード弁があって推進薬の冗長な流路となる。 */ }
            action <'F-OMS-XFD-03'> F_OMS_XFD_03 { doc /* クロスフィードを組むときは受け側のタンク隔離弁を閉じ（左右のタンクは通常は直接つながない）、供給側と受け側のクロスフィード弁を開いて一方のタンクから他方のエンジンへの流路を作る。 */ }
            action <'F-OMS-XFD-04'> F_OMS_XFD_04 { doc /* OMSクロスフィード、RCSクロスフィード、OMS－RCSインタコネクトには同じクロスフィード配管を使い、RCSクロスフィード弁がRCSの推進薬配管をこの配管につなぐ。 */ }
            action <'F-OMS-XFD-05'> F_OMS_XFD_05 { doc /* インタコネクトはRCSタンク隔離弁を閉じてRCSクロスフィード弁を開いた後にOMSクロスフィード弁の1個（B弁）を開き、非供給側のOMSクロスフィード弁を閉じたままにする順序で組み、OMSとRCSのタンクが直接つながるのを防ぐ。 */ }
            action <'F-OMS-XFD-06'> F_OMS_XFD_06 { doc /* インタコネクトは通常1つのOMSポッドが両側のRCSに供給するもので軌道上では手動で組まれ、最も重要な用途は上昇アボートで、そのときは自動で組まれる。 */ }
            action <'F-OMS-XFD-07'> F_OMS_XFD_07 { doc /* RCSタンクはOMSエンジンが必要とする流量を支えられないため、後部RCSからOMSへ推進薬を送ることはない。 */ }
            action <'F-OMS-XFD-08'> F_OMS_XFD_08 { doc /* クロスフィード配管の圧力変換器は計測誤差（34 psia）が大きいため、軌道上ではRCSマニホールドの圧力でクロスフィード配管の状態を確かめてからタンクから再加圧し、酸化剤49 psia・燃料35 psia未満なら配管を故障とする（A6-61B）。 */ }
            action <'F-OMS-XFD-09'> F_OMS_XFD_09 { doc /* 軌道上のインタコネクトはORBITAL DAPでFREEを選んでから、パネルO7で後部RCSタンク隔離弁を閉じてRCSクロスフィード弁を開き、O8で供給側のOMSクロスフィード弁Bを開いて、SPEC 23のOMS PRESS ENAで計量を始める手順で組む。 */ }
            action <'F-OMS-XFD-10'> F_OMS_XFD_10 { doc /* インタコネクト中のOMS推進薬の使用量はRCSジェットの作動回数から噴射時間の積分で求められ、計量シーケンスが左右のOMS推進薬の累計を保持する。 */ }
            action <'F-OMS-XFD-11'> F_OMS_XFD_11 { doc /* OMSタンクを自動で再加圧するソフトウェアもあるが、OMSやRCSの漏れに推進薬を送り続けるため通常は使わない。 */ }
            action <'F-OMS-XFD-12'> F_OMS_XFD_12 { doc /* SODBは、OMS－RCSインタコネクトを上昇アボート（正の+X沈降力がある場合）、OMS噴射中、軌道上の運用に限り、加速度や推進薬量が制約を外れる突入の段階では認めない。 */ }
            action <'F-OMS-XFD-13'> F_OMS_XFD_13 { doc /* 推進薬が故障したときの混合クロスフィード（OMS SSR-1）では、メモリの読み書きでタンク隔離弁とクロスフィード弁の指令を設定し、使えるタンクを反対側のエンジンにつなぐ。 */ }
        }
        package <'SSD-FD-PLS-001'> FN_PLS {
            action <'F-PLS-01'> F_PLS_01 { doc /* PDRSは、ペイロードなどの物体を遠隔で保持・操作し、物体や作業を遠隔で監視するためのハードウェア・ソフトウェア・インタフェースで、RMS、マニピュレータ位置決め機構（MPM）、保持ラッチ（MRL）、MCIU、専用の表示・操作器を含む。 */ }
            action <'F-PLS-02'> F_PLS_02 { doc /* RMSはPDRSの機械アームで、ペイロードの放出・回収、EVA乗員の足部拘束具や作業台の足場の提供、宇宙ステーションの構成品の結合、ペイロードベイの点検などを行う。 */ }
            action <'F-PLS-03'> F_PLS_03 { doc /* アームは6つの関節と先端のエンドエフェクタを持ち、長さ50フィート3インチ、6自由度である。 */ }
            action <'F-PLS-04'> F_PLS_04 { doc /* MCIUは、SM GPC、表示・操作器、RMSとの情報のやり取りを取り扱い、故障条件を解析し、エンドエフェクタの自動捕獲・解放の手順を制御する。 */ }
            action <'F-PLS-05'> F_PLS_05 { doc /* ODSはシャトルを国際宇宙ステーション（ISS）にドッキングさせるためのもので、外部エアロック、トラス組立、APDSの3つの主要構成品から成り、ペイロードベイの576隔壁より後方に置かれる。 */ }
            action <'F-PLS-06'> F_PLS_06 { doc /* 外部エアロックは、ドッキング後に2機の間に気密の内部トンネルを形成する。 */ }
            action <'F-PLS-07'> F_PLS_07 { doc /* APDSは、ほぼ同一のドッキング機構を各機に取り付けて、捕獲、動的減衰、位置合わせ、ハードドッキングを行う。 */ }
        }
        package <'SSD-FD-PLS-ARM-001'> FN_PLS_ARM {
            action <'F-PLS-ARM-01'> F_PLS_ARM_01 { doc /* RMSはPDRSの機械の腕で、ペイロードの展開・回収、EVAの足場、宇宙ステーションの組立、ペイロードベイの点検に使い、最大586,000 lbを動かせる。 */ }
            action <'F-PLS-ARM-02'> F_PLS_ARM_02 { doc /* アームは6つの関節を構造部材（ブーム）でつなぎ、先端にエンドエフェクタを持ち、長さ50 ft 3 in・直径15 inである。 */ }
            action <'F-PLS-ARM-03'> F_PLS_ARM_03 { doc /* アームの重量は905 lb、系全体では994 lbである。 */ }
            action <'F-PLS-ARM-04'> F_PLS_ARM_04 { doc /* RMSは地上の重力の下では関節モータが腕の重さを動かせないため、無重量の環境でだけ運用できる。 */ }
            action <'F-PLS-ARM-05'> F_PLS_ARM_05 { doc /* 各関節のモータはブレーキで静止状態に保たれ、ブレーキの解除には28 V DCを加え続ける必要がある。 */ }
            action <'F-PLS-ARM-06'> F_PLS_ARM_06 { doc /* 各関節のデジタルサーボ電力増幅器（SPA）は主母線Aの+28 V DCを関節の駆動に合わせ、肩の予備駆動増幅器は主母線Bの電力で選んだ関節を駆動する。 */ }
            action <'F-PLS-ARM-07'> F_PLS_ARM_07 { doc /* 上腕・下腕のブームは薄肉の黒鉛/エポキシ複合材の円管で、端のフランジはアルミ合金である。 */ }
            action <'F-PLS-ARM-08'> F_PLS_ARM_08 { doc /* 打上げ時は肩のブレースで肩ピッチの歯車列への荷重を抑え、軌道上で解除するが、軌道上で再びラッチすることはできない。 */ }
        }
        package <'SSD-FD-PLS-CTL-001'> FN_PLS_CTL {
            action <'F-PLS-CTL-01'> F_PLS_CTL_01 { doc /* MCIUの主な機能はSM GPC・表示操作部・RMSとの情報の交換と評価で、データの処理、故障への対応、エンドエフェクタの自動捕獲・解放の論理を受け持つ。 */ }
            action <'F-PLS-CTL-02'> F_PLS_CTL_02 { doc /* RMSの飛行では予備のMCIUを積むのが普通で、故障したMCIUを飛行中に交換できる。 */ }
            action <'F-PLS-CTL-03'> F_PLS_CTL_03 { doc /* 並進ハンドコントローラ（THC）は、ソフトウェアで定めた分解点（POR）の3次元の直線運動を手動で指令する。 */ }
            action <'F-PLS-CTL-04'> F_PLS_CTL_04 { doc /* 回転ハンドコントローラ（RHC）はピッチ・ヨー・ロールの指令を出し、握りに速度保持・速度切替・捕獲/解放のスイッチを持つ。 */ }
            action <'F-PLS-CTL-05'> F_PLS_CTL_05 { doc /* 軌道上の運用は2人の操作員で行い、R1は左舷の後部飛行甲板でアームの軌跡を、R2は右舷でDPSの入力・PRLA・カメラを操作する。 */ }
            action <'F-PLS-CTL-06'> F_PLS_CTL_06 { doc /* RMSは組込み試験で重大な故障を検知し、パネルA8Uの表示灯とDPS表示に出し、テレメトリで地上へ送れる。 */ }
            action <'F-PLS-CTL-07'> F_PLS_CTL_07 { doc /* MCIUは、ABE・表示操作部・SM GPCとの通信のつながり、エンドエフェクタの機能、自身の健全性を監視する。 */ }
        }
        package <'SSD-FD-PLS-MPM-001'> FN_PLS_MPM {
            action <'F-PLS-MPM-01'> F_PLS_MPM_01 { doc /* MPMはトルクチューブ、その上の台座、MRL、投棄系から成る。 */ }
            action <'F-PLS-MPM-02'> F_PLS_MPM_02 { doc /* 左舷のMPMは肩の取付点（X=679.5）とX=911.05・1189・1256.5の3つの台座から成り、各台座は2つの45°の受け台と保持ラッチを持つ。 */ }
            action <'F-PLS-MPM-03'> F_PLS_MPM_03 { doc /* MPMの駆動系は2重の冗長モータでトルクチューブを回し、アームを収納位置からペイロードベイ外の運用位置へ回転させる。 */ }
            action <'F-PLS-MPM-04'> F_PLS_MPM_04 { doc /* アームは左舷の縦通材に沿って後・中・前の3か所でラッチされ、保持ラッチは冗長モータで駆動される2重の回転面である。 */ }
            action <'F-PLS-MPM-05'> F_PLS_MPM_05 { doc /* アームやOBSSを受け台に戻せないときは、ペイロードベイドアを閉められるよう投棄でき、左舷には肩と3つの台座の4つの分離点がある。 */ }
            action <'F-PLS-MPM-06'> F_PLS_MPM_06 { doc /* 肩の取付点の配線束は、支持部を分離する前に冗長な火工品式ギロチンで切断する。 */ }
            action <'F-PLS-MPM-07'> F_PLS_MPM_07 { doc /* 右舷のMPMの台座はOBSSを支え、前方のMPMはラッチ時にOBSSへヒータ電力を与える。 */ }
        }
        package <'SSD-FD-PLS-ODS-001'> FN_PLS_ODS {
            action <'F-PLS-ODS-01'> F_PLS_ODS_01 { doc /* ODSはISSへのドッキングに使い、外部エアロック・トラス組立・APDSの3つから成る。 */ }
            action <'F-PLS-ODS-02'> F_PLS_ODS_02 { doc /* ODSはペイロードベイの576隔壁の後方、トンネルアダプタの後ろにある。 */ }
            action <'F-PLS-ODS-03'> F_PLS_ODS_03 { doc /* 外部エアロックは、ドッキング後に2つの宇宙機の間の気密な通路となる。 */ }
            action <'F-PLS-ODS-04'> F_PLS_ODS_04 { doc /* トラス組立はドッキング系の構成品を収める構造の基盤で、ペイロードベイに取り付けられ、ランデブ・ドッキング用のカメラ・照明などを収める。 */ }
            action <'F-PLS-ODS-05'> F_PLS_ODS_05 { doc /* APDSは、ほぼ同じドッキング機構を両方の機体に付けて、捕獲・動的な減衰・整列・ハードドッキングを行う。 */ }
            action <'F-PLS-ODS-06'> F_PLS_ODS_06 { doc /* 機構の主な構成品は12対の構造フックを持つ基部リング、3枚の花弁を持つ伸縮する案内リング、6つの電磁ブレーキなどで、オービタ側が能動、ISS側が受動である。 */ }
            action <'F-PLS-ODS-07'> F_PLS_ODS_07 { doc /* 後部飛行甲板の2つの操作パネルと外部エアロック床下の9つの電子箱が、機構に電力と論理制御を与える。 */ }
        }
        package <'SSD-FD-PLS-OPS-001'> FN_PLS_OPS {
            action <'F-PLS-OPS-01'> F_PLS_OPS_01 { doc /* RMSの運用の前に肩のブレースを解除し、荷物を持つ運用ではMPMを展開しておく。 */ }
            action <'F-PLS-OPS-02'> F_PLS_OPS_02 { doc /* RMSの点検は約1時間の手順で1飛行に1回だけ行い、問題に対処する時間を取るためできるだけ早く組む。 */ }
            action <'F-PLS-OPS-03'> F_PLS_OPS_03 { doc /* RMSのGo/No-Go基準は、肩のブレースの解除・投棄系・MPMの収納モータ・MRLなどの喪失の数について、受け台から出す・荷物なし・つかむ・荷物ありの各運用を続けられるかを示す。 */ }
            action <'F-PLS-OPS-04'> F_PLS_OPS_04 { doc /* EVAは、PDRS（エンドエフェクタの解放、MPMの収納、MRLのラッチ、肩のブレースの解除、RMSの受け台への収納）の故障に対して冗長の1段として扱われる。 */ }
            action <'F-PLS-OPS-05'> F_PLS_OPS_05 { doc /* RMSとペイロードを投棄しなければならないときは、宇宙に浮かぶ物体を減らすため、できる限り1つにまとめて投棄する。 */ }
            action <'F-PLS-OPS-06'> F_PLS_OPS_06 { doc /* 回収の可能性を残すため、展開するペイロードのPRLA・AKAは回収が選択肢でなくなるまで閉じず、故障したPRLAはEVAで開閉することを考える。 */ }
            action <'F-PLS-OPS-07'> F_PLS_OPS_07 { doc /* CCTVのカメラは肝心なときに故障しやすいので、RMSの運用には少なくとも2つのよいカメラの視野を用意する。 */ }
        }
        package <'SSD-FD-PLS-PRL-001'> FN_PLS_PRL {
            action <'F-PLS-PRL-01'> F_PLS_PRL_01 { doc /* 展開しないペイロードはボルト止めの受動の保持具で、展開するペイロードはモータ駆動の能動の保持具で固定する。 */ }
            action <'F-PLS-PRL-02'> F_PLS_PRL_02 { doc /* オービタのペイロード保持系は、1回の飛行で最大3つのペイロードを3軸で支える。 */ }
            action <'F-PLS-PRL-03'> F_PLS_PRL_03 { doc /* 取付点は左右の縦通材とベイ底の中心線に3.933 in間隔にあり、縦通材の124点・キールの75点を展開するペイロードに使える。 */ }
            action <'F-PLS-PRL-04'> F_PLS_PRL_04 { doc /* ブリッジ金具はペイロードの荷重をオービタ構造へ伝え、PRLAとAKAの構造の取付面となる。 */ }
            action <'F-PLS-PRL-05'> F_PLS_PRL_05 { doc /* 1つのペイロードには通常3〜4個の縦通材のラッチがあり、X・Z方向の荷重を受ける2つの主ラッチと、Z方向だけを受ける安定ラッチから成る。 */ }
            action <'F-PLS-PRL-06'> F_PLS_PRL_06 { doc /* キールのラッチは側方の荷重を受け、閉じるとペイロードをY方向にベイの中心へ寄せるので、縦通材のラッチより先に閉じる。 */ }
            action <'F-PLS-PRL-07'> F_PLS_PRL_07 { doc /* PAYLOAD RETENTION LATCHESスイッチをLATCHにすると、選んだラッチの2重の電動機に交流電力が加わって閉じる。 */ }
        }
        package <'SSD-FD-RCS-001'> FN_RCS {
            action <'F-RCS-01'> F_RCS_01 { doc /* RCSは、前部・左・右の3つのモジュールに分かれて配置されている。 */ }
            action <'F-RCS-02'> F_RCS_02 { doc /* 噴射器は計44基で、主噴射器38基（各870 lb）とバーニア噴射器6基（各24 lb）から成る。 */ }
            action <'F-RCS-03'> F_RCS_03 { doc /* バーニア噴射器は、軌道上の精密な姿勢制御にのみ使用される。 */ }
            action <'F-RCS-04'> F_RCS_04 { doc /* 前部RCSは主噴射器14基とバーニア2基を、後部の各モジュールは主噴射器12基とバーニア2基を持つ。 */ }
            action <'F-RCS-05'> F_RCS_05 { doc /* 酸化剤は四酸化二窒素、燃料はモノメチルヒドラジンで、いずれも常温で貯蔵でき接触で着火するハイパーゴリック推進薬である。 */ }
            action <'F-RCS-06'> F_RCS_06 { doc /* OMS-2噴射後は、残留速度の打ち消し、姿勢保持、軌道上運用のための小さな並進に使用される。 */ }
            action <'F-RCS-07'> F_RCS_07 { doc /* OMSエンジンが故障した場合は、OMS－後部RCS連結でOMS推進薬を後部RCSへ送り、後部RCSの+X噴射器で予定の噴射を完了できる。 */ }
        }
        package <'SSD-FD-RCS-HEP-001'> FN_RCS_HEP {
            action <'F-RCS-HEP-01'> F_RCS_HEP_01 { doc /* 各RCS（前部・左・右）は、ヘリウムタンク2基、ヘリウム隔離弁4個、調圧器4個、逆止弁2組、逃し弁2個と、充填・排出用の接続口を持つ。 */ }
            action <'F-RCS-HEP-02'> F_RCS_HEP_02 { doc /* 2基のヘリウムタンクは、それぞれ燃料タンクと酸化剤タンクに個別にヘリウムを送り、推進薬タンクのアレージ圧を与える。 */ }
            action <'F-RCS-HEP-03'> F_RCS_HEP_03 { doc /* ヘリウムタンクが故障した場合に公称のアレージ圧のままで最大のΔVが得られる推進薬量を最大ブローダウンといい、前部RCSで22%、後部RCSで24%である。 */ }
            action <'F-RCS-HEP-04'> F_RCS_HEP_04 { doc /* ヘリウム隔離弁は2個ずつ並列で、前部はパネルO8のFWD RCS He PRESS A・B、後部はパネルO7のAFT LEFT・AFT RIGHT RCS He PRESS A・Bのスイッチ（OPEN・GPC・CLOSE）で操作し、各スイッチが燃料側と酸化剤側の2個の弁を制御する。 */ }
            action <'F-RCS-HEP-05'> F_RCS_HEP_05 { doc /* ヘリウム隔離弁はソレノイド弁で、電気負荷制御組立を通した瞬時の通電で開いて磁気ラッチされ、ラッチ周りのソレノイドへの通電でばねとヘリウム圧により閉じる。 */ }
            action <'F-RCS-HEP-06'> F_RCS_HEP_06 { doc /* 計量シーケンスは、推進薬タンクのアレージ圧が300 psiaを超えると、軌道上で高圧ヘリウム隔離弁を自動的に閉じる。 */ }
            action <'F-RCS-HEP-07'> F_RCS_HEP_07 { doc /* 調圧器組立は2組が並列で、各組に一次・二次の2段が直列にあり、一次段は242〜248 psig、二次段は253〜259 psigに調圧し、一次段が開故障すると二次段が調圧する。 */ }
            action <'F-RCS-HEP-08'> F_RCS_HEP_08 { doc /* 逆止弁組立は4個のポペットを直並列に配し、直列の配置で推進薬蒸気の逆流を抑えて上流のヘリウム漏れ時にもタンクの圧力を保ち、並列の配置で1個の閉故障時にも加圧を確保する。 */ }
            action <'F-RCS-HEP-09'> F_RCS_HEP_09 { doc /* 逃し弁組立はバースト膜・フィルタ・逃し弁から成り、膜は324〜340 psigで破れ、逃し弁は最小315 psigで開いて310 psigで再着座し、調圧器の全開故障時のヘリウム流量を処理できる。 */ }
            action <'F-RCS-HEP-10'> F_RCS_HEP_10 { doc /* ヘリウムの供給圧は、パネルO3のロータリスイッチをRCS He X10にしてRCS/OMS/PRESSのOXID・FUEL計器で監視する。 */ }
            action <'F-RCS-HEP-11'> F_RCS_HEP_11 { doc /* 運用飛行規則A6-1は、RCSのヘリウムタンクを圧力400（456）psia未満か、加圧経路がすべて閉じた場合に喪失とし、400 psiaは4噴射器の流量で推進薬タンク圧が公称を下回る値である。 */ }
            action <'F-RCS-HEP-12'> F_RCS_HEP_12 { doc /* 運用飛行規則A6-58は、冗長な加圧経路が残っている限り、調圧器の経路を切り分けるためにRCSをブローダウンで運転しないと定める。 */ }
        }
        package <'SSD-FD-RCS-HTR-001'> FN_RCS_HTR {
            action <'F-RCS-HTR-01'> F_RCS_HTR_01 { doc /* 前部RCSモジュールとOMS/RCSポッドには、推進薬を安全な温度に保ち、各主・バーニア噴射器の噴射器を安全な作動温度に保つ電気ヒータがある。 */ }
            action <'F-RCS-HTR-02'> F_RCS_HTR_02 { doc /* 主噴射器のヒータは各20 W（後ろ向きの4基は30 W）、バーニア噴射器のヒータは各10 Wである。 */ }
            action <'F-RCS-HTR-03'> F_RCS_HTR_03 { doc /* 前部RCSには輻射パネル上の6か所にヒータがあり、各OMS/RCSポッドは9つのヒータゾーンに分かれ、各ゾーンをA・Bのヒータ系が並列に制御する。 */ }
            action <'F-RCS-HTR-04'> F_RCS_HTR_04 { doc /* 前部RCSのパネルヒータはパネルA14のFWD RCSスイッチで操作し、A AUTOかB AUTOでは左右のパネルのサーモスタットが約55°FでON、約75°FでOFFにする。 */ }
            action <'F-RCS-HTR-05'> F_RCS_HTR_05 { doc /* 後部RCSのヒータはパネルA14のLEFT POD・RIGHT PODのA AUTO・B AUTOスイッチで操作し、サーモスタットが各ポッドの9つのゾーンを概ね55〜75°Fに保つ。 */ }
            action <'F-RCS-HTR-06'> F_RCS_HTR_06 { doc /* 噴射器のヒータはパネルA14のFWD・AFT RCS JET 1〜5スイッチ（番号はマニホールド）で操作し、AUTOでは各噴射器のサーモスタットが、主噴射器では約66〜76°FでON・約94〜109°FでOFF、バーニアでは約140〜150°FでON・約184〜194°FでOFFにする。 */ }
            action <'F-RCS-HTR-07'> F_RCS_HTR_07 { doc /* 主噴射器のヒータは上昇中はOFF（発射場の気温が50°F未満の場合を除く）で、ほかの飛行段階ではONとし、バーニアのヒータは打上げ前にONにして突入ではOFFにする（A6-251C）。 */ }
            action <'F-RCS-HTR-08'> F_RCS_HTR_08 { doc /* ポッドのヒータは各ヒータパッチにA・B両方の回路が入っており、両系を同時に使うとパッチが過熱して剥がれるため片方の系だけを使い、上昇中（OPS 1）はすべてOFFとする（A6-254）。 */ }
            action <'F-RCS-HTR-09'> F_RCS_HTR_09 { doc /* 前部RCSモジュールのヒータは、SMのGPCが動いていないときはOFFとし、故障でONのままになったヒータがSMで知らされずにマニホールドの配管を過熱させるのを防ぐ（A6-253）。 */ }
            action <'F-RCS-HTR-10'> F_RCS_HTR_10 { doc /* 主噴射器のヒータは、燃料・酸化剤の噴射器温度がともに50（55）°F未満へ下がると喪失とし、低温では噴射器の弁座が収縮して漏れるおそれがある（A6-9）。 */ }
            action <'F-RCS-HTR-11'> F_RCS_HTR_11 { doc /* 主噴射器のヒータがOFFに故障した場合は、手動の噴射、優先度の変更、姿勢の変更で噴射器温度を42（47）°F超に保ち、噴射器温度が162（157）°Fを超えている間は原則として噴射しない（A6-257）。 */ }
            action <'F-RCS-HTR-12'> F_RCS_HTR_12 { doc /* 後部RCSのタンク温度が68（70）°F未満になると、突入時のZOT（燃料・酸化剤の爆発的反応）を避けるため、非干渉の範囲で姿勢を変えて推進薬を温める（A6-258）。 */ }
        }
        package <'SSD-FD-RCS-JET-001'> FN_RCS_JET {
            action <'F-RCS-JET-01'> F_RCS_JET_01 { doc /* RCSの噴射器は計44基（主噴射器38基・バーニア噴射器6基）で、前部に主噴射器14基と横向きのバーニア2基、後部の各ポッドに主噴射器12基とバーニア2基があり、後部のバーニアは一方の組が横向き、他方の組が下向きである。 */ }
            action <'F-RCS-JET-02'> F_RCS_JET_02 { doc /* 主噴射器の真空推力は各870 lb、バーニア噴射器は各24 lbで、バーニアは軌道上の精密な姿勢制御にだけ使われ、狭い姿勢不感帯と推進薬の節約に用いる。 */ }
            action <'F-RCS-JET-03'> F_RCS_JET_03 { doc /* 各噴射器は推進薬を供給するマニホールドと噴流の向きで識別され、記号の1番目がポッド（F・L・R）、2番目がマニホールド番号（1〜5）、3番目が噴流の向き（A・F・L・R・U・D）を表す。 */ }
            action <'F-RCS-JET-04'> F_RCS_JET_04 { doc /* 各噴射器は燃料・酸化剤それぞれ1個のソレノイド式パイロット・ポペット弁を持ち、噴射指令で通電されると推進薬の液圧で主弁ポペットが開き、指令が終わるとばねと圧力で閉じる。 */ }
            action <'F-RCS-JET-05'> F_RCS_JET_05 { doc /* 主噴射器の噴射器板は燃料・酸化剤1対の孔（ダブレット）84組をシャワーヘッド状に配し、外周の追加の燃料孔で燃焼室壁を冷却し、バーニアは1対の孔だけを持つ。 */ }
            action <'F-RCS-JET-06'> F_RCS_JET_06 { doc /* 燃焼室はコロンビウム製で二ケイ化コロンビウムの被覆を持ち、ノズルは輻射冷却で、燃焼室とノズルの周りの断熱材が2,000〜2,400°Fの熱を機体構造へ放射させない。 */ }
            action <'F-RCS-JET-07'> F_RCS_JET_07 { doc /* 各噴射器の電気接続箱には、ヒータ、燃焼室圧力（Pc）トランスデューサ、漏れ検知用の燃料・酸化剤の噴射器温度トランスデューサ、推進薬弁の配線が接続される。 */ }
            action <'F-RCS-JET-08'> F_RCS_JET_08 { doc /* 38基の主噴射器には燃焼不安定の保護があり、弁の電源線を燃焼室の外壁に巻き付けて、燃焼不安定による焼損で電線が切れると弁が閉じ、その噴射器を以後使えなくする。 */ }
            action <'F-RCS-JET-09'> F_RCS_JET_09 { doc /* 主噴射器の定常噴射は1〜150秒が最大で、1ミッションの緊急時の上限は後部（+X）で800秒、前部（-X）で300秒であり、バーニアは2時間あたり275秒までの連続噴射が許される。 */ }
            action <'F-RCS-JET-10'> F_RCS_JET_10 { doc /* 下向きのバーニア1基を失うと制御能力が足りずバーニアモード全体を失うが、横向きのバーニア1基の喪失では、一部のRMS荷重下の運用を除いて制御を保てる。 */ }
            action <'F-RCS-JET-11'> F_RCS_JET_11 { doc /* 運用飛行規則A6-8は、GPCの指令がないのに噴射するもの（fail-on）、指令があっても噴射しないもの（fail-off）、噴射器弁からの漏れ（主噴射器で酸化剤の噴射器温度30°F未満・燃料20°F未満、バーニアで130°F未満）を噴射器の喪失と定める。 */ }
            action <'F-RCS-JET-12'> F_RCS_JET_12 { doc /* 運用飛行規則A6-153は主噴射器の連続噴射の運用限界を150秒、バーニアを275秒とし、バーニアには1時間あたり1000回以下の噴射指令という制約もある。 */ }
        }
        package <'SSD-FD-RCS-OPS-001'> FN_RCS_OPS {
            action <'F-RCS-OPS-01'> F_RCS_OPS_01 { doc /* 上昇中のRCSは外部タンクと結合した惰行中の回転制御とET分離時の-Z並進に使われ、ET分離の-Z並進は自動で行う唯一のRCSの並進である。 */ }
            action <'F-RCS-OPS-02'> F_RCS_OPS_02 { doc /* 異常時には、SSME 2基を失った場合のOMS-RCS連結（自動）と単発エンジンのロール制御、OMS噴射中の姿勢保持の補助（RCSラップアラウンド）、OMSの早期停止時の軌道調整、アボート時の推進薬投棄の補助にRCSを使う。 */ }
            action <'F-RCS-OPS-03'> F_RCS_OPS_03 { doc /* OMS-2噴射の後は残留速度の打ち消し、姿勢保持、軌道上の小さな並進に使われ、軌道上の姿勢保持には通常バーニア噴射器を選ぶ。 */ }
            action <'F-RCS-OPS-04'> F_RCS_OPS_04 { doc /* 前部RCSに残った推進薬は、重心の調整が必要なら突入インタフェースの前に前部のヨー噴射器で燃やして投棄できる。 */ }
            action <'F-RCS-OPS-05'> F_RCS_OPS_05 { doc /* 系統を閉じるときはマニホールドからヘリウムタンクへ向かって、開くときはヘリウムタンクからマニホールドへ向かって操作する（SCOMの経験則）。 */ }
            action <'F-RCS-OPS-06'> F_RCS_OPS_06 { doc /* 運用飛行規則A6-52は、前部RCSのHe・推進薬タンクの漏れ・故障と、後部RCSの1〜2基のHe・推進薬タンクの漏れ・故障について、打上げ〜OMS-1、OMS-1〜OMS-2、OMS-2〜軌道離脱の段階ごとの処置を定める。 */ }
            action <'F-RCS-OPS-07'> F_RCS_OPS_07 { doc /* A6-60は、マニホールドを通常は開とし、漏れの切り分け、RMが示すON故障・漏れの噴射器の隔離、電源断に伴う系統の保護、指令経路やRJDの回復不能な喪失の場合にだけ閉じると定める。 */ }
            action <'F-RCS-OPS-08'> F_RCS_OPS_08 { doc /* A6-61は、燃料・酸化剤の両方のマニホールド圧が130 psia超なら隔離弁で直接再加圧し、両方が130 psia未満なら弁のバウンスとZOTを避けるため段階的な再加圧の手順を使うと定める。 */ }
            action <'F-RCS-OPS-09'> F_RCS_OPS_09 { doc /* A6-156は、RMの検知機能（fail-off・leak・on・全体）を失った場合の処置を噴射器の種類とDAPごとに定め、軌道上の主噴射器は1方向・1ポッドあたり1基で姿勢を保てるが、時間・安全上重要な事象には2基が要るとする。 */ }
            action <'F-RCS-OPS-10'> F_RCS_OPS_10 { doc /* 後部RCSの軌道離脱レッドライン（A6-305）は、軌道離脱準備、OMSエンジン故障時の姿勢制御、軌道離脱の延期などの推進薬を確保し、突入（EI〜マッハ1）には重心位置に応じて1,175か1,375 lbを予約する。 */ }
            action <'F-RCS-OPS-11'> F_RCS_OPS_11 { doc /* OMSの推進薬はタンクの供給の制約で突入中のRCSに使えないため、RCSの突入レッドラインを守るためにOMS-RCS連結を使い、急角度の軌道離脱の保護より優先する（A6-354）。 */ }
            action <'F-RCS-OPS-12'> F_RCS_OPS_12 { doc /* A6-1001のGo/No-Goでは、後部RCSのHeか推進薬タンクの漏れ1件で次のPLSに入り、同じ側の後部主マニホールド2つの喪失でも次のPLSとする（いずれも突入の制御が1故障で失われうるため）。 */ }
        }
        package <'SSD-FD-RCS-PRP-001'> FN_RCS_PRP {
            action <'F-RCS-PRP-01'> F_RCS_PRP_01 { doc /* 各RCSモジュールには燃料タンクと酸化剤タンクが1基ずつあり、前部と各ポッドのタンクの公称満載量は酸化剤1,464 lb、燃料923 lbである。 */ }
            action <'F-RCS-PRP-02'> F_RCS_PRP_02 { doc /* 各タンクはヘリウムで加圧されて推進薬を内蔵の表面張力式推進薬捕捉装置へ押し出し、前部RCSのタンクは主に低重力用に、後部RCSのタンクは高重力・低重力の両方で働くよう設計されている。 */ }
            action <'F-RCS-PRP-03'> F_RCS_PRP_03 { doc /* 後部RCSのタンクには、アボートと突入の段階で正しく働くよう、突入用コレクタ、サンプ、ガストラップが組み込まれている。 */ }
            action <'F-RCS-PRP-04'> F_RCS_PRP_04 { doc /* タンク隔離弁は推進薬タンクとマニホールド隔離弁の間にある交流電動弁で、前部RCSと後部の1/2マニホールド系には1対、後部の3/4/5マニホールド系にはA・Bの2対が並列に入る。 */ }
            action <'F-RCS-PRP-05'> F_RCS_PRP_05 { doc /* タンク隔離弁のスイッチをOPENにすると電動機制御組立が交流電動弁のアクチュエータに給電し、弁が指令位置に達すると電動機制御組立の論理が給電を断つ。 */ }
            action <'F-RCS-PRP-06'> F_RCS_PRP_06 { doc /* 後部のタンク隔離弁は、スイッチがGPC位置のとき、OPS 1・3・6で自動クロスフィードのためにGPCから開閉を指令できる。 */ }
            action <'F-RCS-PRP-07'> F_RCS_PRP_07 { doc /* マニホールド隔離弁のうち1〜4番は交流電動弁で、MANIFOLD ISOLATIONスイッチが燃料・酸化剤の1対ずつを操作し、GPC位置はOPS 2・8でだけ使える。 */ }
            action <'F-RCS-PRP-08'> F_RCS_PRP_08 { doc /* 5番マニホールドの弁はバーニア噴射器だけに推進薬を送るソレノイド式のラッチ弁で、そのスイッチはGPC位置へのばね戻りである。 */ }
            action <'F-RCS-PRP-09'> F_RCS_PRP_09 { doc /* 一方の後部ポッドの推進薬系を噴射器から切り離す必要がある場合は、交流電動の後部RCSクロスフィード弁を開き、他方のポッドの推進薬で左右の噴射器へ供給できる。 */ }
            action <'F-RCS-PRP-10'> F_RCS_PRP_10 { doc /* 後部RCSの噴射器はストレートフィード、クロスフィード（一方のRCSから後部の全噴射器へ）、連結（OMSの推進薬から後部の全噴射器へ）のいずれかで推進薬を受け、前部RCSは後部RCSとのクロスフィードもOMSとの連結もできない。 */ }
            action <'F-RCS-PRP-11'> F_RCS_PRP_11 { doc /* 推進薬量はGPCが圧力・容積・温度（PVT）法で6基のタンクの使用可能量として計算し、対になるタンクの量の差があらかじめ定めた許容値を超えるかどうかで漏れを検知する。 */ }
            action <'F-RCS-PRP-12'> F_RCS_PRP_12 { doc /* 燃料と酸化剤の量の差が9.5%を超えると該当するRCSの赤色警報灯が点灯してBACKUP C/W ALARMが作動し、PASSでは同じモジュールの後続の漏れも検知できるよう9.5%のバイアスを加える。 */ }
        }
        package <'SSD-FD-RCS-RJD-001'> FN_RCS_RJD {
            action <'F-RCS-RJD-01'> F_RCS_RJD_01 { doc /* RJDは、GPCの噴射指令を推進薬の二元弁を開くのに必要な電圧に変換し、燃焼過程を開始させる。 */ }
            action <'F-RCS-RJD-02'> F_RCS_RJD_02 { doc /* RJDは燃焼室圧の離散信号を生成し、実際に噴射したことの表示として冗長管理へ送る。 */ }
            action <'F-RCS-RJD-03'> F_RCS_RJD_03 { doc /* Pc離散信号は、燃焼室圧が36 psiに達するとONになり、26 psiを下回るまでONを保つ。 */ }
            action <'F-RCS-RJD-04'> F_RCS_RJD_04 { doc /* 上昇・突入時は、DAPの噴射器選択論理が38個の噴射器のON・OFF指令をRCS指令サブシステム運用プログラムへ出し、これが各RJDへの二重の噴射指令AとBを生成する。 */ }
            action <'F-RCS-RJD-05'> F_RCS_RJD_05 { doc /* MDMの故障処置の表には、前方MDM（FF1〜FF4）と後方MDM（FA1〜FA4）に対応する前部RJD（RJDF 1A・1B・2A・2B）と後部RJD（RJDA 1A・1B・2A・2B）のDRIVERスイッチ（パネルO14〜O16）が挙げられている。 */ }
            action <'F-RCS-RJD-06'> F_RCS_RJD_06 { doc /* 主噴射器のRJDにはLOGICとDRIVERの電源スイッチが計16個あり、軌道上のRCS噴射試験ではこれらをONにして試験を行う。 */ }
            action <'F-RCS-RJD-07'> F_RCS_RJD_07 { doc /* バーニアを失った場合の手順（LOSS OF VERNIERS）では、バーニアのRJD（L5・F5・R5 DRIVER）をOFFにする。 */ }
            action <'F-RCS-RJD-08'> F_RCS_RJD_08 { doc /* 主噴射器のRJDは、乗員の起床中（近傍運用・ペイロード放出・ランデブを含む）はすべてONとし、乗員の就寝中と貨物室外のEVA中は電源を切る（A6-151）。 */ }
            action <'F-RCS-RJD-09'> F_RCS_RJD_09 { doc /* RJDの故障率は試験で100億時間に1回とされ、就寝中に電源を切るのは就寝中の乗員の対応が遅れるためである（A6-151の根拠）。 */ }
            action <'F-RCS-RJD-10'> F_RCS_RJD_10 { doc /* RJDのロジック電源回路の故障をテレメトリで検知した場合は、電源を切ると2つのマニホールドの噴射器を恒久的に失うため、就寝中も電源を入れたままにする（A6-151C）。 */ }
            action <'F-RCS-RJD-11'> F_RCS_RJD_11 { doc /* fail-onはRJDの弁電源出力が高に故障するか燃料・酸化剤の両弁が開故障すると起こり、fail-offはRJDの出力離散信号が低に故障するか弁の一方が閉故障すると起こる（A6-8）。 */ }
            action <'F-RCS-RJD-12'> F_RCS_RJD_12 { doc /* 1つのRJDへの電源（冗長な2系統とも）かRJDの機能を回復できないほど失うと、そのマニホールドの噴射器をすべて失うため、マニホールドを閉じたままにする（A6-60E）。 */ }
        }
        package <'SSD-FD-RCS-RM-001'> FN_RCS_RM {
            action <'F-RCS-RM-01'> F_RCS_RM_01 { doc /* RCSの冗長管理（RM）ソフトウェアは、噴射器の故障の検知と通報、噴射器の可用性、SPEC 23 RCS、SPEC 51 BFS OVERRIDE、マニホールド状態の処理から成る。 */ }
            action <'F-RCS-RM-02'> F_RCS_RM_02 { doc /* RMが検知する故障はfail-off・fail-on・fail-leakで、通報はマスタアラーム、パネルF7の黄色のRCS JETと赤色のBACKUP C/W ALARMの点灯、故障メッセージから成るクラス2の警報である。 */ }
            action <'F-RCS-RM-03'> F_RCS_RM_03 { doc /* RMが使う噴射器のパラメータは、Pc離散信号、CMD B、ドライバ出力離散信号、酸化剤・燃料の噴射器温度である。 */ }
            action <'F-RCS-RM-04'> F_RCS_RM_04 { doc /* fail-offは、CMD BがあるのにPc離散信号がない状態が3周期続くと検知し、故障フラグを立てて通報し、ポッドの限度に達していなければその噴射器を選択解除する。 */ }
            action <'F-RCS-RM-05'> F_RCS_RM_05 { doc /* fail-onは、CMD Bが出ていないのにドライバ出力離散信号がある状態が3周期続くと検知し、OPS 2（8）でAUT MANF CLが有効なら該当するマニホールドの弁に閉指令を送る。 */ }
            action <'F-RCS-RM-06'> F_RCS_RM_06 { doc /* fail-leakは、酸化剤か燃料の噴射器温度がRMの限界を3周期続けて下回ると検知し、ポッドの限度に達していなければその噴射器を選択解除し、バーニアの故障はOPS 2と8でだけ通報する。 */ }
            action <'F-RCS-RM-07'> F_RCS_RM_07 { doc /* 噴射器可用表は噴射器ごとに1ビットを持ち、ビットがONならDAPがその噴射器に噴射を指令でき、RMが使えないと判定した噴射器には噴射を指令しない。 */ }
            action <'F-RCS-RM-08'> F_RCS_RM_08 { doc /* SPEC 23のPRI JET FAIL LIM（I-load値2、変更可）はRMがポッドごとに自動で選択解除する主噴射器の数の上限で、ポッドの計数が限度に達すると以後の故障は通報するだけで選択解除しない。 */ }
            action <'F-RCS-RM-09'> F_RCS_RM_09 { doc /* RMはマニホールド弁の状態を独自に評価し、状態が閉になると（手動で閉じた、通信障害、乗員の入力、一部のジレンマ）そのマニホールドの噴射器を可用表から外す。 */ }
            action <'F-RCS-RM-10'> F_RCS_RM_10 { doc /* マニホールドのRMは4つのマイクロスイッチ離散信号（OX OP・OX CL・FU OP・FU CL）から、ジレンマ（RCS RM DLMA）と電源故障（RCS PWR FAIL）を検知する。 */ }
            action <'F-RCS-RM-11'> F_RCS_RM_11 { doc /* RMのフラグ・状態・計数はOPSの移行をまたいで引き継がれるが、BFSを結合するとすべて消去されて初期化される。 */ }
            action <'F-RCS-RM-12'> F_RCS_RM_12 { doc /* BFSにはSPEC 23がなく、BFSは結合されたときだけfail-offとfail-onを通報し、fail-leakは通報しない。 */ }
        }
        package <'SSD-FD-STR-001'> FN_STR {
            action <'F-STR-01'> F_STR_01 { doc /* オービタ構造は、前部胴体、主翼、中部胴体、ペイロードベイドア、後部胴体、前部RCS、垂直尾翼、OMS/RCSポッド、ボディフラップの9つの主要部分に分かれ、大部分は通常のアルミニウム製で、再使用型表面断熱材で保護される。 */ }
            action <'F-STR-02'> F_STR_02 { doc /* 前部胴体は与圧された乗員室を収め、前部RCSモジュール、ノーズキャップ、前脚格納部、前脚と前脚扉を支持する。 */ }
            action <'F-STR-03'> F_STR_03 { doc /* 3層の乗員室は2219アルミニウム合金板を溶接した与圧容器で、ECLSS、アビオニクス、GN&C機器、IMU、表示・操作器、スタートラッカ、就寝・廃棄物処理・座席などの乗員設備を支持する。 */ }
            action <'F-STR-04'> F_STR_04 { doc /* 乗員室は14.7±0.2 psiaに与圧され、ECLSSにより窒素80%・酸素20%の組成に保たれる。乗員室は16 psiaで設計されている。 */ }
            action <'F-STR-05'> F_STR_05 { doc /* 中部胴体は前部胴体・後部胴体・主翼と結合し、ペイロードベイドアとそのヒンジ、固定金具、前部主翼グラブ、各種の搭載機器を支持して、ペイロードベイを形成する。 */ }
            action <'F-STR-06'> F_STR_06 { doc /* 後部胴体は、左右のOMS/RCSポッド、主翼後桁、中部胴体、オービタ／外部タンクの後部結合部、主エンジン、後部熱シールド、ボディフラップ、垂直尾翼、2つのT-0打上げアンビリカルパネルを支持し、これらと結合する。 */ }
            action <'F-STR-07'> F_STR_07 { doc /* 後部胴体の内部推力構造は3基のSSMEとその低圧ターボポンプ・推進薬配管を支持する。 */ }
            action <'F-STR-08'> F_STR_08 { doc /* ボディフラップは再突入時に3基のSSMEを熱的に遮蔽し、大気圏飛行中のピッチトリムを与える。 */ }
        }
        package <'SSD-FD-STR-AFT-001'> FN_STR_AFT {
            action <'F-STR-AFT-01'> F_STR_AFT_01 { doc /* 後胴は外殻・推力構造・内部の二次構造から成る。 */ }
            action <'F-STR-AFT-02'> F_STR_AFT_02 { doc /* 後胴は中胴の主縦通材への荷重経路、前部隔壁を越える主翼桁の連続、ボディフラップの支持を受け持つ。 */ }
            action <'F-STR-AFT-03'> F_STR_AFT_03 { doc /* 内部の推力構造は3基のSSMEを支え、上部が上のSSMEを、下部が下の2基を支える。 */ }
            action <'F-STR-AFT-04'> F_STR_AFT_04 { doc /* オービタ/ETの2つの後部結合点は、縦通材の金具で結合する。 */ }
            action <'F-STR-AFT-05'> F_STR_AFT_05 { doc /* 内部の推力構造は主に28本の拡散接合したチタンのトラス部材から成る（OV-105は鍛造品）。 */ }
            action <'F-STR-AFT-06'> F_STR_AFT_06 { doc /* 各OMS/RCSポッドはOMS・RCSの推進の構成品をすべて収め、11本のボルトで後胴に取り付けられる。 */ }
            action <'F-STR-AFT-07'> F_STR_AFT_07 { doc /* ポッドは162 dBの音響と−170〜+135°Fの温度に耐える。 */ }
        }
        package <'SSD-FD-STR-CRM-001'> FN_STR_CRM {
            action <'F-STR-CRM-01'> F_STR_CRM_01 { doc /* 3層の乗員室は2219アルミ合金板を溶接した気密の圧力容器で、側面ハッチ・中甲板からエアロックへのハッチ・エアロックからペイロードベイへのハッチを持つ。 */ }
            action <'F-STR-CRM-02'> F_STR_CRM_02 { doc /* 圧力殻の約300の貫通部はプレートと金具で封じられる。 */ }
            action <'F-STR-CRM-03'> F_STR_CRM_03 { doc /* 乗員室は、両者の間の熱伝導を小さくするため、前胴の中に4つの取付点だけで支えられる。 */ }
            action <'F-STR-CRM-04'> F_STR_CRM_04 { doc /* 乗員室は14.7±0.2 psia・窒素80%・酸素20%に保たれ、設計圧力は16 psiaである。 */ }
            action <'F-STR-CRM-05'> F_STR_CRM_05 { doc /* エアロックをペイロードベイに置いたときの乗員室の容積は2,553 ft3である。 */ }
            action <'F-STR-CRM-06'> F_STR_CRM_06 { doc /* 前方の6枚の窓はそれぞれ3枚の板ガラスから成り、最も内側の板（0.625 in）は乗員室の圧力に耐える圧力ペインである。 */ }
            action <'F-STR-CRM-07'> F_STR_CRM_07 { doc /* 前方の窓の外側の板は前胴に、中央と内側の板は乗員室に取り付けられ、各窓に冗長なシールが使われる。 */ }
        }
        package <'SSD-FD-STR-FWD-001'> FN_STR_FWD {
            action <'F-STR-FWD-01'> F_STR_FWD_01 { doc /* オービタの構造は9つの主要区分（前胴・翼・中胴・PLBD・後胴・前部RCS・垂直尾翼・OMS/RCSポッド・ボディフラップ）に分かれ、大部分は通常のアルミニウムで再使用の表面断熱材に守られる。 */ }
            action <'F-STR-FWD-02'> F_STR_FWD_02 { doc /* 前胴は上下の部分から成って与圧乗員室を囲み、前部RCSモジュール・ノーズキャップ・前脚格納部・前脚・前脚扉を支える。 */ }
            action <'F-STR-FWD-03'> F_STR_FWD_03 { doc /* 前胴は2024アルミ合金のスキン・ストリンガのパネル・フレーム・隔壁で造られ、主フレームの間隔は30〜36 inである。 */ }
            action <'F-STR-FWD-04'> F_STR_FWD_04 { doc /* ノーズキャップは強化炭素・炭素（RCC）の再使用TPSで、ノーズキャップと構造の境に熱障壁を持つ。 */ }
            action <'F-STR-FWD-05'> F_STR_FWD_05 { doc /* 前部のオービタ/ET結合金具は、Xo=378隔壁と前脚格納部の後方の外板構造にある。 */ }
            action <'F-STR-FWD-06'> F_STR_FWD_06 { doc /* 前部RCSモジュールは16本の留め具で前胴の機首部と前部隔壁に固定され、取付け・取外しができる。 */ }
            action <'F-STR-FWD-07'> F_STR_FWD_07 { doc /* 前胴は、Xo=582の柔軟な膜でペイロードベイと仕切られる。 */ }
        }
        package <'SSD-FD-STR-MID-001'> FN_STR_MID {
            action <'F-STR-MID-01'> F_STR_MID_01 { doc /* 中胴は前胴・後胴・翼とつながり、ペイロードベイドア・ヒンジ・固定金具・前部翼グラブなどを支えてペイロードベイを形作る。 */ }
            action <'F-STR-MID-02'> F_STR_MID_02 { doc /* 中胴は主にアルミニウムの構造で、長さ60 ft・幅17 ft・高さ13 ft、重量約13,502 lbである。 */ }
            action <'F-STR-MID-03'> F_STR_MID_03 { doc /* 中胴は12の主フレーム組立で安定させる。 */ }
            action <'F-STR-MID-04'> F_STR_MID_04 { doc /* 縦通材は主な曲げ部材であるとともに、ペイロードベイのペイロードからの縦方向の荷重を受ける。 */ }
            action <'F-STR-MID-05'> F_STR_MID_05 { doc /* シルの縦通材は、マニピュレータアーム・Ku帯アンテナ・ペイロードベイドアの作動系の取付けの基盤となる。 */ }
            action <'F-STR-MID-06'> F_STR_MID_06 { doc /* 翼の前方の側壁は主脚の内側の支えとなり、脚の横方向の荷重はすべて中胴が受ける。 */ }
            action <'F-STR-MID-07'> F_STR_MID_07 { doc /* 飛行データの解析から、下部の中胴の縦通材に捩り帯を足し、降下時の熱勾配に対して正の安全余裕を確保した。 */ }
        }
        package <'SSD-FD-STR-OPS-001'> FN_STR_OPS {
            action <'F-STR-OPS-01'> F_STR_OPS_01 { doc /* 圧力ペインか冗長ペインが故障したときは客室圧を10.2 psiに下げ、軌道上では次のPLSで帰還する。 */ }
            action <'F-STR-OPS-02'> F_STR_OPS_02 { doc /* 窓系には与圧の冗長が必要で、熱ペインは与圧の冗長にならない。 */ }
            action <'F-STR-OPS-03'> F_STR_OPS_03 { doc /* 熱ペインは破片が欠けたときに故障とみなし、RTLSの境界より前に前方の窓か側面ハッチの熱ペインが故障したらRTLSでアボートする。 */ }
            action <'F-STR-OPS-04'> F_STR_OPS_04 { doc /* ビューポートを使わないときは外側の覆いを閉じておく。 */ }
            action <'F-STR-OPS-05'> F_STR_OPS_05 { doc /* オービタの姿勢は、TPSの接着層の温度を−170°Fより高く、突入時の最高温度未満に保つよう管理する。 */ }
            action <'F-STR-OPS-06'> F_STR_OPS_06 { doc /* 軌道デブリに対しては、ペイロードベイを前に向ける姿勢などで過ごす時間を飛行前の計画と実時間の運用で最小にする。 */ }
            action <'F-STR-OPS-07'> F_STR_OPS_07 { doc /* 軌道離脱の準備の姿勢の手順の前にすべての熱の制約を満たすことが解析で示されれば、軌道離脱の実時間の熱解析は要らない。 */ }
        }
        package <'SSD-FD-STR-WNG-001'> FN_STR_WNG {
            action <'F-STR-WNG-01'> F_STR_WNG_01 { doc /* 翼の4本の主桁は、熱荷重を抑えるため波形のアルミニウムで造られる。 */ }
            action <'F-STR-WNG-02'> F_STR_WNG_02 { doc /* 前桁は再使用のRCCの前縁構造の取付けとなり、後桁はエレボンと油圧・電気の構成品の取付けとなる。 */ }
            action <'F-STR-WNG-03'> F_STR_WNG_03 { doc /* エレボンは大気中の飛行制御を行い、各翼で2つの区分に分かれ、各区分は3つのヒンジで支えられ、33°上・18°下まで動く。 */ }
            action <'F-STR-WNG-04'> F_STR_WNG_04 { doc /* 翼は上面の引張ボルトの継手と下面のせん断継手で胴体に取り付けられる。 */ }
            action <'F-STR-WNG-05'> F_STR_WNG_05 { doc /* ボディフラップは突入中に3基のSSMEを熱から守り、大気中の飛行でピッチのトリムを与える。 */ }
            action <'F-STR-WNG-06'> F_STR_WNG_06 { doc /* 垂直尾翼は構造のフィン・ラダー/スピードブレーキ・翼端・下部後縁から成り、ラダーは2つに割れてスピードブレーキになる。 */ }
            action <'F-STR-WNG-07'> F_STR_WNG_07 { doc /* フィンは前桁の根元の2本の引張ボルトで後胴の前部隔壁に、後桁の根元の8本のせん断ボルトで後胴の上面に取り付けられる。 */ }
            action <'F-STR-WNG-08'> F_STR_WNG_08 { doc /* 垂直尾翼の構造は163 dBの音響と最高350°Fに耐えるよう設計される。 */ }
        }
        package <'SSD-FD-TCS-001'> FN_TCS {
            action <'F-TCS-01'> F_TCS_01 { doc /* ATCSは、2系統のフレオン21冷却ループ、アビオニクス用コールドプレート網、液液熱交換器、放熱器・FES・アンモニアボイラの3種のヒートシンクから成る。 */ }
            action <'F-TCS-02'> F_TCS_02 { doc /* オービタ内部の温度は、断熱材、ヒータ、パージによっても管理される。 */ }
            action <'F-TCS-03'> F_TCS_03 { doc /* オービタの外面温度は、約90分の軌道1周ごとに−200°Fから+200°Fまで変動する。 */ }
            action <'F-TCS-04'> F_TCS_04 { doc /* ペイロードベイドアは、軌道到達後まもなく開かれ、機体各系の排熱のためにECLSSの放熱器を露出させる。 */ }
        }
        package <'SSD-FD-TCS-PTC-001'> FN_TCS_PTC {
            action <'F-TCS-PTC-01'> F_TCS_PTC_01 { doc /* オービタ内部の温度は、内部断熱材、ヒータ、パージによって飛行の各段階で管理される。 */ }
            action <'F-TCS-PTC-02'> F_TCS_PTC_02 { doc /* Kaptonの反射膜とDacronのメッシュを交互に重ね、シリカ布で覆ったキルト状の断熱ブランケットが、受動熱制御として機体の各部を覆った。 */ }
            action <'F-TCS-PTC-03'> F_TCS_PTC_03 { doc /* OMS/RCSポッドは内面の断熱材とストリップヒータで熱制御され、A・B2系統のヒータがサーモスタットで55〜75°Fに保たれる。 */ }
            action <'F-TCS-PTC-04'> F_TCS_PTC_04 { doc /* 燃料電池の生成水配管や給水・廃水のダンプ配管にも、凍結防止用のサーモスタット制御ヒータがある。 */ }
            action <'F-TCS-PTC-05'> F_TCS_PTC_05 { doc /* パージ・ベント・ドレン系は、非与圧区画にパージガスを流して熱調整と有害ガスの滞留防止を行い、湿度と温度を一定に保つ。 */ }
            action <'F-TCS-PTC-06'> F_TCS_PTC_06 { doc /* 着陸後は、ベントドア1・2・6・8・9をパージ位置にして地上冷却を行う。 */ }
        }
        package <'SSD-FD-TPS-001'> FN_TPS {
            action <'F-TPS-01'> F_TPS_01 { doc /* TPSは、高温での安定性と重量効率で選ばれた材料で構成される受動系である。 */ }
            action <'F-TPS-02'> F_TPS_02 { doc /* 強化炭素－炭素（RCC）は、主翼前縁、機首キャップ（機首直後下面のチャインパネルを含む）、前部オービタ／外部タンク構造結合部の周辺に使われ、再突入時に2,300°Fを超える部位を保護する。 */ }
            action <'F-TPS-03'> F_TPS_03 { doc /* 高温再使用表面断熱材（HRSI）タイルは2,300°F未満の部位を保護し、再突入時の放射率を得るための黒色コーティングを持つ。 */ }
            action <'F-TPS-04'> F_TPS_04 { doc /* 後に開発された黒色のFRCIタイルが、一部の部位でHRSIタイルを置き換えた。 */ }
            action <'F-TPS-05'> F_TPS_05 { doc /* 白色の低温再使用表面断熱材（LRSI）タイルは、前・中・後部胴体、垂直尾翼、主翼上面、OMS/RCSポッドの一部に使われる。 */ }
            action <'F-TPS-06'> F_TPS_06 { doc /* コーティングしたノーメックスフェルトの再使用表面断熱材（FRSI）の白色ブランケットは、ペイロードベイドア上面、中・後部胴体側面の一部、主翼上面の一部、OMS/RCSポッドの一部に使われ、700°F未満の部位を保護する。 */ }
        }
        package <'SSD-FD-SRB-001'> FN_SRB {
            action <'F-SRB-01'> F_SRB_01 { doc /* 2本のSRBは、シャトルを射点から高度約150,000 ftまで持ち上げる主推力を担う。 */ }
            action <'F-SRB-02'> F_SRB_02 { doc /* 各SRBの海面推力は打上げ時で約3,300,000 lbで、3基のSSMEの推力が確認された後に点火される。 */ }
            action <'F-SRB-03'> F_SRB_03 { doc /* 燃焼終了後に分離され、パラシュートで大西洋に着水し、回収・点検・整備のうえ再使用された。 */ }
            action <'F-SRB-04'> F_SRB_04 { doc /* SRBの推力方向制御用の油圧系も、ヒドラジン式の補助動力装置で駆動される。 */ }
        }
        package <'SSD-FD-SRB-ATT-001'> FN_SRB_ATT {
            action <'F-SRB-ATT-01'> F_SRB_ATT_01 { doc /* ETは各SRBの後部フレームで2つの横の振れ止めと斜めの結合でつながり、SRBの前端は前部スカートでETに結合する。 */ }
            action <'F-SRB-ATT-02'> F_SRB_ATT_02 { doc /* SRBの分離は両方のSRBの頭部の燃焼圧が50 psi以下になったときに始まり、センサの偏りに備えて点火からの時間でも分離する。 */ }
            action <'F-SRB-ATT-03'> F_SRB_ATT_03 { doc /* 分離の手順ではATVCがアクチュエータを中立に戻してSSMEを第2段の構成にし、SRBの推力が100,000 lb未満になるようにする。 */ }
            action <'F-SRB-ATT-04'> F_SRB_ATT_04 { doc /* SRBは火工品の発火の指令から30 ms以内にETから分離する。 */ }
            action <'F-SRB-ATT-05'> F_SRB_ATT_05 { doc /* 前部の結合点は1本のボルトで保持された玉（SRB）と受け（ET）から成り、ボルトは両端にNSIの圧力カートリッジを持ち、射場安全系のクロスストラップの配線も通す。 */ }
            action <'F-SRB-ATT-06'> F_SRB_ATT_06 { doc /* 後部の結合点は上・斜め・下の3本の支柱から成り、各支柱のボルトは両端にNSIの圧力カートリッジを持ち、上の支柱はSRBとETからオービタへのアンビリカルも通す。 */ }
            action <'F-SRB-ATT-07'> F_SRB_ATT_07 { doc /* 各SRBの両端に4基ずつの分離モータ（BSM）があり、分離時に1.02秒燃焼してSRBをETから離す。 */ }
        }
        package <'SSD-FD-SRB-AVN-001'> FN_SRB_AVN {
            action <'F-SRB-AVN-01'> F_SRB_AVN_01 { doc /* 各SRBは前部スカートと結合リングに1つずつ統合電子組立（IEA）を持ち、後部IEAは点火の指令とノズルの推力方向制御のため前部IEAとオービタのアビオニクスにつながる。 */ }
            action <'F-SRB-AVN-02'> F_SRB_AVN_02 { doc /* 各IEAは多重化/多重分離器（MDM）を持つ。 */ }
            action <'F-SRB-AVN-03'> F_SRB_AVN_03 { doc /* SRBの電力はオービタの主直流母線A・B・CからSRB母線A・B・Cへ供給し、主母線Cが母線A・Bの、主母線Bが母線Cの予備となるので、オービタの主母線が1つ故障してもSRBの母線はすべて給電され続ける。 */ }
            action <'F-SRB-AVN-04'> F_SRB_AVN_04 { doc /* SRBの直流電圧は公称28 V、上限32 V・下限24 Vである。 */ }
            action <'F-SRB-AVN-05'> F_SRB_AVN_05 { doc /* SRBのレートジャイロ組立（SRGA）は、入替え可能な中間値選択でSRBのピッチ・ヨーの角速度を与え、20回のミッション向けに設計されている。 */ }
            action <'F-SRB-AVN-06'> F_SRB_AVN_06 { doc /* 射場安全系（RSS）は各SRBに1つあり、地上局からのarmとfireの2つの指令を受け、機体が打上げ軌道のレッドラインを外れたときだけ使う。 */ }
            action <'F-SRB-AVN-07'> F_SRB_AVN_07 { doc /* 2本のSRBのRSSの分配器はクロスストラップされ、一方がarmや破壊の信号を受けると他方にも送られる。 */ }
            action <'F-SRB-AVN-08'> F_SRB_AVN_08 { doc /* 分離の手順でSRBのRSSの電源を切り、回収系の電源を入れる。 */ }
        }
        package <'SSD-FD-SRB-HDP-001'> FN_SRB_HDP {
            action <'F-SRB-HDP-01'> F_SRB_HDP_01 { doc /* 打上げ前、各SRBは後部スカートで4組のボルトとナットにより移動発射台に固定され、離昇時に小さな爆薬で切られる。 */ }
            action <'F-SRB-HDP-02'> F_SRB_HDP_02 { doc /* 2本のSRBは積み重ねた全体の重量を支え、その荷重を構造を通して移動発射台へ伝える。 */ }
            action <'F-SRB-HDP-03'> F_SRB_HDP_03 { doc /* 各保持ボルトは両端にナットがあり、上のナットだけが破断式で、点火の指令で2つのNSIが作動する。 */ }
            action <'F-SRB-HDP-04'> F_SRB_HDP_04 { doc /* 点火の指令はオービタの計算機からMECを経て移動発射台の保持PICへ送られ、打上げ前の最後の16秒にPICの低電圧を監視し、低電圧なら打上げを保留する。 */ }
            action <'F-SRB-HDP-05'> F_SRB_HDP_05 { doc /* 点火の指令は、3基のSSMEが定格の90%以上で、SSMEの故障やPICの低電圧が無く、地上の保留も無いときに出る。 */ }
            action <'F-SRB-HDP-06'> F_SRB_HDP_06 { doc /* PICは、GPCから出てMECが28 V DCに整形したarm・fire 1・fire 2の3つの信号がそろったときだけ火工品を発火させる。 */ }
            action <'F-SRB-HDP-07'> F_SRB_HDP_07 { doc /* 点火の順序は、PICがS&A装置の火工品を点火し、S&Aの薬が起爆剤を、起爆剤がモータの点火器を、点火器がモータの推進薬を点火する。 */ }
        }
        package <'SSD-FD-SRB-MTR-001'> FN_SRB_MTR {
            action <'F-SRB-MTR-01'> F_SRB_MTR_01 { doc /* 2本のSRBはこれまでに飛んだ最大の固体推進薬のモータで、初めて再使用を前提に設計された。 */ }
            action <'F-SRB-MTR-02'> F_SRB_MTR_02 { doc /* 各SRBは海面で約3,300,000 lbの推力を出し、打上げと第1段上昇の推力の71.4%を担い、高度約150,000 ftまで機体を持ち上げる。 */ }
            action <'F-SRB-MTR-03'> F_SRB_MTR_03 { doc /* 推進薬は2分あまりで燃え尽き、その時点でSRBを投棄する。 */ }
            action <'F-SRB-MTR-04'> F_SRB_MTR_04 { doc /* 各SRBは長さ約149 ft・直径12 ftで、打上げ時の重量は約1,300,000 lb（うち推進薬約1,100,000 lb）である。 */ }
            action <'F-SRB-MTR-05'> F_SRB_MTR_05 { doc /* 推進薬は過塩素酸アンモニウム（69.6%）・アルミニウム（16%）・酸化鉄（0.4%）・結合剤（12.04%）・硬化剤（1.96%）の混合である。 */ }
            action <'F-SRB-MTR-06'> F_SRB_MTR_06 { doc /* 前部セグメントの11点の星形と後部の二重截頭円錐の穿孔で、点火時の高い推力を打上げ約50秒後に約3分の1下げ、最大動圧での過大な応力を防ぐ。 */ }
            action <'F-SRB-MTR-07'> F_SRB_MTR_07 { doc /* SRBは4つのモータセグメントから成る対で使い、同じ原料のバッチから対で充填して推力の不釣合いを小さくする。 */ }
            action <'F-SRB-MTR-08'> F_SRB_MTR_08 { doc /* 各ノズルは膨張比7.72:1で、燃焼中に浸食・炭化する炭素布の内張りを持つ。 */ }
            action <'F-SRB-MTR-09'> F_SRB_MTR_09 { doc /* 打上げ0.23秒後に燃焼圧が563.5 psiaに達して離昇し、0.6秒後に最大（公称914 psia）となる。 */ }
        }
        package <'SSD-FD-SRB-REC-001'> FN_SRB_REC {
            action <'F-SRB-REC-01'> F_SRB_REC_01 { doc /* 回収は高高度の気圧スイッチでノーズキャップのスラスタを作動させて始まり、分離188秒後・高度15,700 ftでノーズキャップを外してパイロットシュートを出す。 */ }
            action <'F-SRB-REC-02'> F_SRB_REC_02 { doc /* 直径54 ftのドローグシュートはSRBを安定させ、270,000 lbの荷重に耐え、重量は約1,200 lbである。 */ }
            action <'F-SRB-REC-03'> F_SRB_REC_03 { doc /* 低高度の気圧スイッチで高度5,500 ft・分離243秒後にフラスタムを前部スカートから分離し、ドローグシュートがそれを引き離す。 */ }
            action <'F-SRB-REC-04'> F_SRB_REC_04 { doc /* 分離277秒後に76 ft/sで着水し、空の燃焼室に空気が残って前端を約30 ft水面に出して浮かぶ。 */ }
            action <'F-SRB-REC-05'> F_SRB_REC_05 { doc /* 主傘は着水後に海水作動の放出装置（SWAR）で外れ、回収船が来るまでSRBにつながれる。 */ }
            action <'F-SRB-REC-06'> F_SRB_REC_06 { doc /* 回収したSRBは発射場へ曳航して分解・洗浄し、モータセグメント・点火器・ノズルを製造元へ送って再整備するが、ノーズキャップとノズルの延長部は回収しない。 */ }
        }
        package <'SSD-FD-SRB-TVC-001'> FN_SRB_TVC {
            action <'F-SRB-TVC-01'> F_SRB_TVC_01 { doc /* 各ノズルは推力方向制御のためジンバルし、後部の可撓軸受をジンバル機構とし、全軸のジンバル能力は8°である。 */ }
            action <'F-SRB-TVC-02'> F_SRB_TVC_02 { doc /* 各SRBは2つの独立した油圧動力装置（HPU）を持ち、各HPUはAPU・燃料供給・油圧ポンプ・リザーバ・マニホールドから成る。 */ }
            action <'F-SRB-TVC-03'> F_SRB_TVC_03 { doc /* APUはヒドラジンを燃料とし、軸動力で油圧ポンプを回し、2つの系は打上げ28秒前からSRB分離まで動く。 */ }
            action <'F-SRB-TVC-04'> F_SRB_TVC_04 { doc /* 各燃料タンクは22 lbのヒドラジンを収め、400 psiの窒素で加圧する。 */ }
            action <'F-SRB-TVC-05'> F_SRB_TVC_05 { doc /* 各HPUは両方のサーボアクチュエータにつながり、主の油圧が2,050 psi未満になると切替弁が副の油圧に切り替え、APUは113%の速度で両方のアクチュエータに足りる油圧を出す。 */ }
            action <'F-SRB-TVC-06'> F_SRB_TVC_06 { doc /* 各SRBはロックとチルトの2つの油圧ジンバルサーボアクチュエータを持ち、ノズルを動かして推力の方向を制御する。 */ }
            action <'F-SRB-TVC-07'> F_SRB_TVC_07 { doc /* 各アクチュエータの4つの独立したサーボ弁は力の和による多数決で、1つの誤った指令が動きに影響しないようにし、続くときはその弁の油圧を切り離す。 */ }
            action <'F-SRB-TVC-08'> F_SRB_TVC_08 { doc /* APU/HPUと油圧系は20回のミッションに再使用できる。 */ }
        }
    }
    // ---- 物理配置（SSD-PHY-ORB-001 の区画と機器）
    package Physical {
        part def Compartment { doc /* オービタの区画（図43） */ }
        part def <'PHY-CT-01'> PHY_CT_01 { doc /* S帯PMトランスポンダ（XPNDR）（数量：2、通信・追跡（C&T）） */ }
        part def <'PHY-CT-02'> PHY_CT_02 { doc /* S帯PMクワッドアンテナ（数量：4（各アンテナが前方・後方の2ビームを持ち、実質8アンテナ）、通信・追跡（C&T）） */ }
        part def <'PHY-CT-03'> PHY_CT_03 { doc /* Ku帯展開アセンブリ（DA、高利得アンテナ）（数量：1、通信・追跡（C&T）） */ }
        part def <'PHY-CT-04'> PHY_CT_04 { doc /* Ku帯電子アセンブリ（EA1・EA2）（数量：2、通信・追跡（C&T）） */ }
        part def <'PHY-CT-05'> PHY_CT_05 { doc /* UHF送受信機（ATC送受信機）（数量：1（IFM配置図の箱数）、通信・追跡（C&T）） */ }
        part def <'PHY-CT-06'> PHY_CT_06 { doc /* ACCU（音声中央制御装置）（数量：1箱（内部に冗長なACCU 2系統）、通信・追跡（C&T）） */ }
        part def <'PHY-CT-07'> PHY_CT_07 { doc /* S 帯の信号処理・増幅機器（プリアンプ・電力増幅器・アンテナ切替・NSP・COMSEC・FM 信号処理器・FM 送信機・GCIL）（数量：プリアンプ 2・電力増幅器 2・アンテナ切替 1・NSP 2・COMSEC 1・FM 信号処理器 2・FM 送信機 2・GCIL 1、通信・追跡（C&T）） */ }
        part def <'PHY-CT-08'> PHY_CT_08 { doc /* S 帯 FM 半球アンテナ・UHF 下面アンテナ（数量：半球アンテナ 2・UHF アンテナ 1、通信・追跡（C&T）） */ }
        part def <'PHY-CT-09'> PHY_CT_09 { doc /* Ku 帯信号処理器（KuSP）（数量：1、通信・追跡（C&T）） */ }
        part def <'PHY-CT-10'> PHY_CT_10 { doc /* PCMMU（PCM マスタユニット）（数量：2、通信・追跡（C&T）） */ }
        part def <'PHY-CT-11'> PHY_CT_11 { doc /* SSOR（宇宙対宇宙オービタ無線）と SSOR アンテナ（数量：SSOR 2・アンテナ 2、通信・追跡（C&T）） */ }
        part def <'PHY-CT-12'> PHY_CT_12 { doc /* VCU（映像制御装置：RCU（遠隔制御装置）と VSU（映像切替装置）の2つの LRU）（数量：1（RCU 1・VSU 1）、通信・追跡（C&T）） */ }
        part def <'PHY-DPS-01'> PHY_DPS_01 { doc /* GPC（汎用計算機、IBM AP-101S）（数量：5、データ処理系（DPS）） */ }
        part def <'PHY-DPS-02'> PHY_DPS_02 { doc /* MMU（モジュラーメモリユニット）（数量：2、データ処理系（DPS）） */ }
        part def <'PHY-DPS-03'> PHY_DPS_03 { doc /* MDM（マルチプレクサ／デマルチプレクサ）（数量：オービタ20（DPS用13・OI用7）＋SRB用4、データ処理系（DPS）） */ }
        part def <'PHY-DPS-04'> PHY_DPS_04 { doc /* IDP（統合表示処理装置、MEDS）（数量：4（ほかにMDU 11・ADC 4・キーボード3）、データ処理系（DPS）） */ }
        part def <'PHY-DPS-05'> PHY_DPS_05 { doc /* MTU（マスタタイミングユニット）（数量：1（内部に発振器2）、データ処理系（DPS）） */ }
        part def <'PHY-DPS-06'> PHY_DPS_06 { doc /* データバス網（飛行重要 FC1〜8・ペイロード・打上げ・大容量記憶・表示/キーボード・計装/PCMMU・計算機間通信）（数量：1式（バス 28本）、データ処理系（DPS）） */ }
        part def <'PHY-DPS-07'> PHY_DPS_07 { doc /* EIU（エンジンインタフェースユニット）・MEC（マスターイベントコントローラ）（数量：EIU 3・MEC 2、データ処理系（DPS）） */ }
        part def <'PHY-GNC-01'> PHY_GNC_01 { doc /* IMU（慣性計測装置）（数量：3、誘導・航法・制御（GN&C）） */ }
        part def <'PHY-GNC-02'> PHY_GNC_02 { doc /* スタートラッカ（ST）（数量：2（−Y軸用・−Z軸用）、誘導・航法・制御（GN&C）） */ }
        part def <'PHY-GNC-03'> PHY_GNC_03 { doc /* TACAN（戦術航法装置）／GPS受信機（数量：TACAN 3（三重GPS未改修機）／GPS受信機3（OV-105）、誘導・航法・制御（GN&C）） */ }
        part def <'PHY-GNC-04'> PHY_GNC_04 { doc /* ADTA（エアデータ変換器）とエアデータプローブ（数量：ADTA 4・プローブ2、誘導・航法・制御（GN&C）） */ }
        part def <'PHY-GNC-05'> PHY_GNC_05 { doc /* MLS（マイクロ波着陸システム。F-GNC-01とIFMの表記はMSBLS）（数量：3（各セットはKu帯受信送信機と復号器）、誘導・航法・制御（GN&C）） */ }
        part def <'PHY-GNC-06'> PHY_GNC_06 { doc /* ATVC（上昇推力方向制御装置）（数量：4、誘導・航法・制御（GN&C）） */ }
        part def <'PHY-RCS-01'> PHY_RCS_01 { doc /* 前部RCS噴射器（主噴射器・バーニア噴射器）（数量：16（主14、バーニア2）、姿勢制御系（RCS）） */ }
        part def <'PHY-RCS-02'> PHY_RCS_02 { doc /* 後部RCS噴射器（主噴射器・バーニア噴射器）（数量：28（各ポッドに主12・バーニア2）、姿勢制御系（RCS）） */ }
        part def <'PHY-RCS-03'> PHY_RCS_03 { doc /* 前部RCS推進薬タンク・ヘリウムタンク（数量：推進薬タンク2（燃料1・酸化剤1）、ヘリウムタンク2、姿勢制御系（RCS）） */ }
        part def <'PHY-RCS-04'> PHY_RCS_04 { doc /* 後部RCS推進薬タンク・ヘリウムタンク（数量：各ポッドに推進薬タンク2（燃料1・酸化剤1）とヘリウムタンク2（計：推進薬タンク4、ヘリウムタンク4）、姿勢制御系（RCS）） */ }
        part def <'PHY-RCS-05'> PHY_RCS_05 { doc /* RJDF（前部反動噴射器ドライバ）（数量：2（RJDF 1・RJDF 2）、姿勢制御系（RCS）） */ }
        part def <'PHY-RCS-06'> PHY_RCS_06 { doc /* 後部 RCS クロスフィード弁・マニホールド隔離弁（数量：各ポッド：クロスフィード弁 2対・マニホールド隔離弁 5対、姿勢制御系（RCS）） */ }
        part def <'PHY-RCS-07'> PHY_RCS_07 { doc /* RJDA（後部反動噴射器ドライバ）（数量：2、姿勢制御系（RCS）） */ }
        part def <'PHY-RCS-08'> PHY_RCS_08 { doc /* RCS ヒータ（前部モジュールのパネルヒータ・ポッドのヒータ区域・噴射器ヒータ）（数量：1式、姿勢制御系（RCS）） */ }
        part def <'PHY-EPS-01'> PHY_EPS_01 { doc /* 燃料電池発電装置（FC）（数量：3、電力系（EPS）） */ }
        part def <'PHY-EPS-02'> PHY_EPS_02 { doc /* PRSD極低温反応剤タンク（H2・O2タンク組）（数量：最大5組（1組はH2タンク1個とO2タンク1個。搭載組数はミッションと機体で異なる）、電力系（EPS）） */ }
        part def <'PHY-EPS-03'> PHY_EPS_03 { doc /* 静止型インバータ（INV）（数量：9（交流母線3系統×各3相）、電力系（EPS）） */ }
        part def <'PHY-EPS-04'> PHY_EPS_04 { doc /* 電力制御アセンブリ（PCA）と配電アセンブリ（DA）（数量：DA 3、PCA：前方・中部・後部の各1〜3と後部4〜6、電力系（EPS）） */ }
        part def <'PHY-EPS-05'> PHY_EPS_05 { doc /* モータ制御アセンブリ（MCA）（数量：10（前方3・中部4・後部3）、電力系（EPS）） */ }
        part def <'PHY-ECLSS-01'> PHY_ECLSS_01 { doc /* 大気再生系（ARS）の床下機器：キャビンファン・キャビン熱交換器・水酸化リチウム（LiOH）キャニスタ・水冷却ループ水ポンプ（数量：キャビンファン2基（A・B）、LiOHキャニスタ2個（装着）＋予備最大30個、水ポンプ3台（ループ1に2台、ループ2に1台）、環境制御・生命維持（ECLSS）） */ }
        part def <'PHY-ECLSS-02'> PHY_ECLSS_02 { doc /* 供給水タンク・廃水タンク（給水・廃水系）（数量：供給水タンク4基（A〜D、各使用可能容量165ポンド）、廃水タンク1基（165ポンド）、環境制御・生命維持（ECLSS）） */ }
        part def <'PHY-ECLSS-03'> PHY_ECLSS_03 { doc /* 与圧系（PCS）窒素タンク（GN2）（数量：OV-103・OV-105は標準の6基構成、OV-104は5基（系統1に2基、系統2に3基）。ミッションキットとして追加タンクを搭載することがある、環境制御・生命維持（ECLSS）） */ }
        part def <'PHY-ECLSS-04'> PHY_ECLSS_04 { doc /* 能動熱制御系（ATCS）フレオン冷却ループのポンプパッケージ（フレオンポンプ・アキュムレータ）とフレオン／水熱交換器（数量：フレオンループ2系統、各ループにポンプ2台とアキュムレータ1基、環境制御・生命維持（ECLSS）） */ }
        part def <'PHY-ECLSS-05'> PHY_ECLSS_05 { doc /* 放熱器パネル（ATCS）（数量：各ペイロードベイドアに4枚（前方2枚は展開式、後方2枚は固定式）、環境制御・生命維持（ECLSS）） */ }
        part def <'PHY-ECLSS-06'> PHY_ECLSS_06 { doc /* フラッシュエバポレータ系（FES）とアンモニアボイラ系（数量：FES：高負荷エバポレータ1基とトッピングエバポレータ1基、コントローラ3台（プライマリA・プライマリB・セカンダリ）。アンモニア：貯蔵・制御系2系統（各タンク49ポンド）と共通ボイラ1基、環境制御・生命維持（ECLSS）） */ }
        part def <'PHY-ECLSS-07'> PHY_ECLSS_07 { doc /* フレオンループの熱交換器・弁（燃料電池熱交換器・カーゴ熱交換器・ペイロード熱交換器・O2 リストリクタ・流量配分弁モジュール）（数量：熱交換器 3・O2 リストリクタ 3・流量配分弁モジュール 1、環境制御・生命維持（ECLSS）） */ }
        part def <'PHY-ECLSS-08'> PHY_ECLSS_08 { doc /* コールドプレート網（中胴の左右、後部アビオニクスベイ4・5・6、レートジャイロ）（数量：1式、環境制御・生命維持（ECLSS）） */ }
        part def <'PHY-ECLSS-09'> PHY_ECLSS_09 { doc /* 油圧熱交換器（フレオン／作動油、油圧系統1〜3）（数量：3（各油圧系統に1）、環境制御・生命維持（ECLSS）） */ }
        part def <'PHY-ECLSS-10'> PHY_ECLSS_10 { doc /* GSE 熱交換器（地上冷却）（数量：1、環境制御・生命維持（ECLSS）） */ }
        part def <'PHY-ECLSS-11'> PHY_ECLSS_11 { doc /* キャビン空気の分配（還気ダクト・キャビンファンフィルタ・ファン出口ダクトと LiOH 分流オリフィス・給気ダクトと吹出口）（数量：1式（フィルタ 1）、環境制御・生命維持（ECLSS）） */ }
        part def <'PHY-ECLSS-12'> PHY_ECLSS_12 { doc /* キャビン温湿度制御の機器（キャビン温度制御弁・キャビン温度コントローラ・湿分分離器）（数量：温度制御弁 1・コントローラ 2・湿分分離器 2（A・B）、環境制御・生命維持（ECLSS）） */ }
        part def <'PHY-ECLSS-13'> PHY_ECLSS_13 { doc /* CO2 除去の付帯機器（常温触媒酸化器 ATCO・CO2 分圧トランスデューサ）と再生式 CO2 除去装置（RCRS）（数量：ATCO 1・PPCO2 トランスデューサ 1・RCRS 1（OV-105 の EDO 構成）、環境制御・生命維持（ECLSS）） */ }
        part def <'PHY-ECLSS-14'> PHY_ECLSS_14 { doc /* アビオニクスベイの空冷と熱交換器（ベイファン・空気／水熱交換器、ベイ1・2・3A）（数量：ベイファン 6（各ベイ2）・熱交換器 3（各ベイ1）、環境制御・生命維持（ECLSS）） */ }
        part def <'PHY-ECLSS-15'> PHY_ECLSS_15 { doc /* IMU の空冷（IMU 吸込みフィルタ・通風ダクト・IMU ファン・IMU 熱交換器）（数量：ファン 3（A・B・C）・熱交換器 1・フィルタ・ダクト 1式、環境制御・生命維持（ECLSS）） */ }
        part def <'PHY-ECLSS-16'> PHY_ECLSS_16 { doc /* 水冷コールドプレート（アビオニクスベイ1・2・3A・3B、操縦室の MDM コールドプレートと並列オリフィス）（数量：1式（25・30・32・5 ft2 と MDM 1）、環境制御・生命維持（ECLSS）） */ }
        part def <'PHY-ECLSS-17'> PHY_ECLSS_17 { doc /* 水冷却ループの制御・付帯機器（水バイパス弁と制御器、窓シールの熱調整配管、飲料水チラー、液冷服熱交換器）（数量：バイパス弁・制御器 各2・チラー 1・LCVG 熱交換器 1・窓シール配管 1式、環境制御・生命維持（ECLSS）） */ }
        part def <'PHY-ECLSS-18'> PHY_ECLSS_18 { doc /* PCS の酸素の弁・調圧器（O2 供給弁・逆止弁・クロスオーバ弁とマニホールド・O2 レギュレータ・LEH レギュレータと O2 弁・直接 O2 弁・O2 ブリードオリフィス）（数量：供給弁 2・逆止弁 2・クロスオーバ弁 2・O2 レギュレータ 2・LEH レギュレータ 2・LEH O2 弁 8・直接 O2 弁 1・OBOA 1、環境制御・生命維持（ECLSS）） */ }
        part def <'PHY-ECLSS-19'> PHY_ECLSS_19 { doc /* PCS の窒素の弁・調圧器（N2 供給弁・N2 レギュレータ入口弁・200 psig N2 レギュレータ・逆止弁・クロスオーバ弁・水タンク N2 レギュレータ）（数量：供給弁・入口弁・N2 レギュレータ 各2・逆止弁 2・クロスオーバ弁 1・水タンク N2 レギュレータ 2、環境制御・生命維持（ECLSS）） */ }
        part def <'PHY-ECLSS-20'> PHY_ECLSS_20 { doc /* 乗員室の与圧の制御機器（O2/N2 制御弁・O2/N2 コントローラ・O2/N2 マニホールド・14.7 psia キャビンレギュレータ・8 psia 非常用レギュレータ）（数量：制御弁 2・コントローラ 2・マニホールド 2・キャビンレギュレータ 2・非常用レギュレータ 2、環境制御・生命維持（ECLSS）） */ }
        part def <'PHY-ECLSS-21'> PHY_ECLSS_21 { doc /* 逃し弁とベント弁（正圧逃し弁・逃し隔離弁・負圧逃し弁・キャビンベント隔離弁・キャビンベント弁）（数量：正圧逃し弁 2・隔離弁 2・負圧逃し弁 2・ベント隔離弁 1・ベント弁 1、環境制御・生命維持（ECLSS）） */ }
        part def <'PHY-ECLSS-22'> PHY_ECLSS_22 { doc /* PCS の計測センサ（乗員室圧・PPO2 A/B/C・dP/dT・O2/N2 流量）（数量：乗員室圧 1・PPO2 3・dP/dT 1・流量 4、環境制御・生命維持（ECLSS）） */ }
        part def <'PHY-ECLSS-23'> PHY_ECLSS_23 { doc /* 燃料電池の生成水の処理（水素分離器・微生物フィルタ）（数量：水素分離器 2・微生物フィルタ 1、環境制御・生命維持（ECLSS）） */ }
        part def <'PHY-ECLSS-24'> PHY_ECLSS_24 { doc /* 給水の分配の弁（給水出口マニホールド・クロスオーバ弁・B 給水隔離弁・ギャレー給水弁）（数量：マニホールド 1式・クロスオーバ弁 1・隔離弁 1・ギャレー給水弁 1、環境制御・生命維持（ECLSS）） */ }
        part def <'PHY-ECLSS-25'> PHY_ECLSS_25 { doc /* 給水・廃水のダンプ系（ダンプ隔離弁・ダンプ弁・配管ヒータ A/B・ダンプノズルとノズルヒータ）（数量：給水・廃水 各1式、環境制御・生命維持（ECLSS）） */ }
        part def <'PHY-ECLSS-26'> PHY_ECLSS_26 { doc /* 非常用の水の器具と水タンクの加圧の弁（非常用クロスタイの QD と移送ホース・CWC・H2O タンク N2 マニホールドの弁）（数量：クロスタイ 1式・CWC（飛行ごと）・N2 マニホールド 1式、環境制御・生命維持（ECLSS）） */ }
        part def <'PHY-ECLSS-27'> PHY_ECLSS_27 { doc /* 廃棄物収集系（小便器・便器・ファンセパレータ・臭気・細菌フィルタ）（数量：小便器 1・便器 1・ファンセパレータ 2・フィルタ 1（予備1）、環境制御・生命維持（ECLSS）） */ }
        part def <'PHY-ECLSS-28'> PHY_ECLSS_28 { doc /* WCS の真空ベント系（WCS 真空弁・真空ベント QD・真空ベント隔離弁・ベント管とノズル）（数量：1式、環境制御・生命維持（ECLSS）） */ }
        part def <'PHY-ECLSS-29'> PHY_ECLSS_29 { doc /* ARS の計装の信号調整器（IMU FAN・HUM SEP・CABIN AIR・AV BAY 1/2/3・H2O BYP LOOP 1/2 SNSR）（数量：IMU FAN 1・HUM SEP 1・CABIN AIR 1・AV BAY 3（各ベイ1）・H2O BYP LOOP SNSR 2（ループごと1）、環境制御・生命維持（ECLSS）） */ }
        part def <'PHY-ECLSS-30'> PHY_ECLSS_30 { doc /* ARS の計装のセンサ（IMU ファンの回転数・湿分分離器の速度・アビオニクスベイの温度とファン差圧・キャビン熱交換器出口温度・水ループのインターチェンジャ流量/出口温度とポンプパッケージの計装）（数量：IMU ファン回転数 3・湿分分離器速度 2・ベイ温度 3・ベイ差圧 3・熱交換器出口温度 1・インターチェンジャ（流量・出口温度）2 組・ポンプパッケージ計装 2 組（ループごと）、環境制御・生命維持（ECLSS）） */ }
        part def <'PHY-ECLSS-31'> PHY_ECLSS_31 { doc /* 消火設備（固定の Halon 消火ボトルと PIC・AGENT DISCH 押しボタン・携帯消火器）（数量：固定ボトル 3（ベイ1・2・3A に各1）・PIC 3・AGENT DISCH 押しボタン 1（ガード付き）・携帯消火器 3（中甲板2・操縦室1）、環境制御・生命維持（ECLSS）） */ }
        part def <'PHY-ECLSS-32'> PHY_ECLSS_32 { doc /* WCS のコントローラと真空ベント管ヒータ（WCS コントローラ・真空ベント管ヒータ A/B・ノズルヒータ）（数量：コントローラ 1・管ヒータ 2（A・B）・ノズルヒータ 1 式、環境制御・生命維持（ECLSS）） */ }
        part def <'PHY-ECLSS-33'> PHY_ECLSS_33 { doc /* 給水・廃水系の電動弁（タンク入口・出口・ダンプ隔離・B 給水隔離などの弁）（数量：1式（個数は資料に無い）、環境制御・生命維持（ECLSS）） */ }
        part def <'PHY-ECLSS-34'> PHY_ECLSS_34 { doc /* 空気経路の付帯機器（アビオニクスベイの空気経路と 300 ミクロンフィルタ・キャビンファン・プレナム出口）（数量：ベイの空気経路 3（ベイ1・2・3A）・プレナム 1、環境制御・生命維持（ECLSS）） */ }
        part def <'PHY-ECLSS-35'> PHY_ECLSS_35 { doc /* エアロックの均圧・減圧の弁（ハッチ均圧弁・エアロック減圧弁と減圧ライン・ベスティビュール減圧弁/隔離弁）（数量：ハッチ均圧弁 6（3ハッチに各2）・エアロック減圧弁 1・ベスティビュール減圧弁/隔離弁 2、環境制御・生命維持（ECLSS）） */ }
        part def <'PHY-ECLSS-36'> PHY_ECLSS_36 { doc /* エアロックのヒータと温度センサ（水配管ヒータ・構造ヒータ・ベスティビュールヒータ・構造パッチヒータ・水配管の温度トランスデューサ・構造温度センサ）（数量：水配管ヒータ（6本×3系統）・構造ヒータ（区域1〜3）・ベスティビュールヒータ（区域1〜3）・構造パッチヒータ 3 区域・温度トランスデューサ 4・構造温度センサ 1 式、環境制御・生命維持（ECLSS）） */ }
        part def <'PHY-ECLSS-37'> PHY_ECLSS_37 { doc /* エアロックの通風機器（ブースタファン A/B・エアロックのダクトとハローダクト）（数量：ブースタファン 2（A・B。1台ずつ使用）・ダクト 1式、環境制御・生命維持（ECLSS）） */ }
        part def <'PHY-ECLSS-38'> PHY_ECLSS_38 { doc /* EMU 支援の配管（LCG 供給・戻り配管・EMU 用 O2 配管と隔離弁・EMU 給水・廃水の配管）（数量：LCG 配管 4（EMU 2着×供給・戻り）・O2 配管と隔離弁 1式・給水・廃水配管 1式、環境制御・生命維持（ECLSS）） */ }
        part def <'PHY-ECLSS-39'> PHY_ECLSS_39 { doc /* エアロックの圧力計測（圧力・差圧トランスデューサ・ハッチ差圧計・LCG 供給圧トランスデューサ）（数量：圧力トランスデューサ 2・ハッチ差圧計 6（3ハッチ×両側）・LCG 供給圧トランスデューサ 2、環境制御・生命維持（ECLSS）） */ }
        part def <'PHY-APU-01'> PHY_APU_01 { doc /* APU（補助動力装置、改良型IAPU）（数量：3、補助動力・油圧（APU/HYD）） */ }
        part def <'PHY-APU-02'> PHY_APU_02 { doc /* APU燃料タンク（ヒドラジンタンク）（数量：3（各APUに1）、補助動力・油圧（APU/HYD）） */ }
        part def <'PHY-APU-03'> PHY_APU_03 { doc /* WSB（水噴霧ボイラ）（数量：3（APU・油圧系統ごとに1）、補助動力・油圧（APU/HYD）） */ }
        part def <'PHY-APU-04'> PHY_APU_04 { doc /* 主油圧ポンプ（可変容量形）（数量：3（各油圧系統に1）、補助動力・油圧（APU/HYD）） */ }
        part def <'PHY-APU-05'> PHY_APU_05 { doc /* 油圧リザーバ・ブートストラップアキュムレータ・循環ポンプ（各油圧系統の制御部）（数量：各3（各油圧系統に1組）、補助動力・油圧（APU/HYD）） */ }
        part def <'PHY-APU-06'> PHY_APU_06 { doc /* 噴射器冷却水タンクと水制御弁（3台共用）（数量：1、補助動力・油圧（APU/HYD）） */ }
        part def <'PHY-APU-07'> PHY_APU_07 { doc /* 油圧の分配弁・フィルタ（フィルタモジュール・プライオリティ弁、MPS/TVC 隔離弁、ブレーキ隔離弁、脚伸展弁）（数量：フィルタモジュール 3・隔離弁 6・脚伸展弁群 1、補助動力・油圧（APU/HYD）） */ }
        part def <'PHY-OMS-01'> PHY_OMS_01 { doc /* OMSエンジン（軌道制御エンジン）（数量：2（左右各1）、軌道制御系（OMS）） */ }
        part def <'PHY-OMS-02'> PHY_OMS_02 { doc /* OMS推進薬タンク（燃料MMH・酸化剤N2O4）（数量：4（各ポッドに燃料1・酸化剤1）、軌道制御系（OMS）） */ }
        part def <'PHY-OMS-03'> PHY_OMS_03 { doc /* OMSヘリウムタンク（推進薬加圧用高圧Heタンク）（数量：2（各ポッドに1）、軌道制御系（OMS）） */ }
        part def <'PHY-OMS-04'> PHY_OMS_04 { doc /* OMS TVCジンバルアクチュエータ（電気機械式、アクティブ／スタンバイ制御器付き）（数量：4（各エンジンにピッチ用1・ヨー用1）、軌道制御系（OMS）） */ }
        part def <'PHY-OMS-05'> PHY_OMS_05 { doc /* OMSクロスフィード配管・クロスフィード弁（数量：1式（左右ポッド間の燃料・酸化剤クロスフィード配管）、軌道制御系（OMS）） */ }
        part def <'PHY-MPS-01'> PHY_MPS_01 { doc /* SSME（スペースシャトル主エンジン）（数量：3、主推進系（MPS）） */ }
        part def <'PHY-MPS-02'> PHY_MPS_02 { doc /* SSMEコントローラ（主エンジン制御器）（数量：3（各SSMEに1台）、主推進系（MPS）） */ }
        part def <'PHY-MPS-03'> PHY_MPS_03 { doc /* SSME TVCサーボアクチュエータ（ジンバルアクチュエータ）（数量：6（各SSMEにピッチ用1・ヨー用1）、主推進系（MPS）） */ }
        part def <'PHY-MPS-04'> PHY_MPS_04 { doc /* ATVC（上昇推力方向制御装置）（数量：4、主推進系（MPS）） */ }
        part def <'PHY-MPS-05'> PHY_MPS_05 { doc /* MPSヘリウムタンク（He供給タンク）（数量：10（4.7 ft³×7、17.3 ft³×3）、主推進系（MPS）） */ }
        part def <'PHY-MPS-06'> PHY_MPS_06 { doc /* 推進薬マニホールド・SSME供給管（PMS：17インチLO2・LH2マニホールド、12インチ供給管、プリバルブ）（数量：マニホールド2（LO2・LH2）、SSME供給管は各推進薬3本（各エンジン1本、プリバルブ付き）、主推進系（MPS）） */ }
        part def <'PHY-MPS-07'> PHY_MPS_07 { doc /* GO2・GH2 加圧ラインと ET 加圧マニホールド（数量：GO2 加圧ライン 3・GH2 加圧ライン 3・マニホールド 2、主推進系（MPS）） */ }
        part def <'PHY-MPS-08'> PHY_MPS_08 { doc /* 充填排出弁・ダンプ弁・マニホールド再加圧弁（数量：LO2・LH2 充填排出弁 各2・バックアップ LH2 ダンプ弁 2・再加圧弁・調圧器 4、主推進系（MPS）） */ }
        part def <'PHY-TPS-01'> PHY_TPS_01 { doc /* 強化炭素－炭素（RCC）ノーズキャップ・チャインパネル・前部オービタ／ET結合部周辺（数量：ノーズキャップ1、チャインパネル、前部オービタ／ET結合部周辺（枚数は出典に記載なし）、熱防護系（TPS）） */ }
        part def <'PHY-TPS-02'> PHY_TPS_02 { doc /* 強化炭素－炭素（RCC）主翼前縁（数量：左右主翼の前縁（パネル枚数は出典に記載なし）、熱防護系（TPS）） */ }
        part def <'PHY-TPS-03'> PHY_TPS_03 { doc /* 高温再使用表面断熱材（HRSI）黒タイル（一部はFRCIタイル）（数量：—（枚数は出典に記載なし）、熱防護系（TPS）） */ }
        part def <'PHY-TPS-04'> PHY_TPS_04 { doc /* 低温再使用表面断熱材（LRSI）白タイルと改良型柔軟再使用表面断熱材（AFRSI）ブランケット（数量：—（枚数・面積は出典に記載なし）、熱防護系（TPS）） */ }
        part def <'PHY-TPS-05'> PHY_TPS_05 { doc /* フェルト再使用表面断熱材（FRSI）白ブランケット（数量：—（面積は出典に記載なし）、熱防護系（TPS）） */ }
        part def <'PHY-STR-01'> PHY_STR_01 { doc /* 前部胴体（上部・下部胴体、ノーズ部、前脚格納部）（数量：1式（上部と下部の2部分）、構造（STR）） */ }
        part def <'PHY-STR-02'> PHY_STR_02 { doc /* 乗員室（3層の与圧容器）（数量：1式（フライトデッキ・ミッドデッキ・下部機器ベイの3層）、構造（STR）） */ }
        part def <'PHY-STR-03'> PHY_STR_03 { doc /* 中部胴体（ペイロードベイ構造）（数量：1式（長さ60フィート、幅17フィート、高さ13フィート、約13,502ポンド）、主フレーム組立12、構造（STR）） */ }
        part def <'PHY-STR-04'> PHY_STR_04 { doc /* 主翼（左右、エレボン付き）（数量：左右2枚（最大厚さ5フィート）、エレボンは各翼2セグメント（各3ヒンジ）、構造（STR）） */ }
        part def <'PHY-STR-05'> PHY_STR_05 { doc /* 後部胴体（外殻・推力構造・二次構造）とボディフラップ（数量：後部胴体1式（長さ約18フィート、幅22フィート、高さ20フィート）、推力構造（主に拡散接合チタン製トラス部材28本）、ボディフラップ1（回転アクチュエータ4基）、構造（STR）） */ }
        part def <'PHY-STR-06'> PHY_STR_06 { doc /* 垂直尾翼（フィン・ラダー／スピードブレーキ）（数量：1式（フィン、2つに割れるラダー／スピードブレーキ）、構造（STR）） */ }
        part def <'PHY-MECH-01'> PHY_MECH_01 { doc /* ペイロードベイドア（PLBD）と扉駆動・ラッチ用電気機械式アクチュエータ（PDU）（数量：扉2枚（左舷・右舷、各5セグメント）、扉駆動PDU各1基、ラッチ計32個（センターライン16個を4ガング、前後の隔壁ラッチ各8個）、ヒンジ各13個、機械系（MECH）） */ }
        part def <'PHY-MECH-02'> PHY_MECH_02 { doc /* 外部タンク（ET）アンビリカル扉とラッチ（数量：扉2枚（左：液体水素側、右：液体酸素側）、センターラインラッチ、各開口内のアップロックラッチ3個、機械系（MECH）） */ }
        part def <'PHY-MECH-03'> PHY_MECH_03 { doc /* アクティブベント系（AVS）のベント扉とアクチュエータ（数量：ベントポート14か所（各舷7か所）。当初は18か所、機械系（MECH）） */ }
        part def <'PHY-MECH-04'> PHY_MECH_04 { doc /* 前脚（NLG）・前脚扉・前輪操舵アクチュエータ（数量：前脚1基（緩衝支柱1本、車輪・タイヤ2組）、前脚扉2枚、機械系（MECH）） */ }
        part def <'PHY-MECH-05'> PHY_MECH_05 { doc /* 主脚（MLG）と電気油圧式ディスクブレーキ・アンチスキッド（数量：主脚2基（左右、各車輪・タイヤ2組）、主脚扉各1枚、ブレーキ4組（主脚車輪ごと）、機械系（MECH）） */ }
        part def <'PHY-MECH-06'> PHY_MECH_06 { doc /* ドラッグシュート（数量：1式（パイロットシュート9フィート、メインシュート40フィート）、機械系（MECH）） */ }
        part def <'PHY-CW-01'> PHY_CW_01 { doc /* C/W電子ユニット（注意警報電子ユニット）（数量：1（内部に電源装置A・B）、警報系（C/W）） */ }
        part def <'PHY-CW-02'> PHY_CW_02 { doc /* 注意警報表示マトリクス（パネルF7）（数量：1（40灯）、警報系（C/W）） */ }
        part def <'PHY-CW-03'> PHY_CW_03 { doc /* MASTER ALARM押しボタン表示灯（数量：4、警報系（C/W）） */ }
        part def <'PHY-CW-04'> PHY_CW_04 { doc /* C/W限界値設定・パラメータ状態パネル（パネルR13U）（数量：1（パラメータ状態灯120）、警報系（C/W）） */ }
        part def <'PHY-CW-05'> PHY_CW_05 { doc /* 煙検知器（クラス1警報）（数量：9（A群5・B群4。SCOMの配置記述からの計数）、警報系（C/W）） */ }
        part def <'PHY-CREW-01'> PHY_CREW_01 { doc /* 乗員座席（CDR席S1・PLT席S2・MS席）（数量：フライトデッキ4席、ミッドデッキ3席（MS席と同型の座席を3〜4席装着できる）、乗員系・脱出系（CREW）） */ }
        part def <'PHY-CREW-02'> PHY_CREW_02 { doc /* 睡眠設備（寝袋・4段式固定睡眠ステーション）（数量：寝袋は乗員ごとに1つ。24時間運用ミッションでは4段式固定睡眠ステーションを搭載、乗員系・脱出系（CREW）） */ }
        part def <'PHY-CREW-03'> PHY_CREW_03 { doc /* サイドハッチと投棄・キャビンベント火工品系（数量：サイドハッチ1（直径40インチ）、Tハンドル2本（キャビンベント用・ハッチ投棄用）、乗員系・脱出系（CREW）） */ }
        part def <'PHY-CREW-04'> PHY_CREW_04 { doc /* 脱出ポールと緊急脱出スライド（数量：脱出ポール1本（ランヤード8本のマガジン付き）、緊急脱出スライド1式（膨張式スライド・アルゴンボトルなど）、乗員系・脱出系（CREW）） */ }
        part def <'PHY-CREW-05'> PHY_CREW_05 { doc /* 頭上脱出窓（W8）と緊急降下器（Sky Genie）（数量：頭上窓W8 1（3枚重ね、開口20×20インチ）、緊急降下器7個（乗員1人に1個）、乗員系・脱出系（CREW）） */ }
        part def <'PHY-PLS-01'> PHY_PLS_01 { doc /* 遠隔マニピュレータシステム（RMS）アーム（数量：1基（6関節＋エンドエフェクタ、長さ50フィート3インチ、直径15インチ）、ペイロード支援（PDRS・ODS）） */ }
        part def <'PHY-PLS-02'> PHY_PLS_02 { doc /* マニピュレータ位置決め機構（MPM）とマニピュレータ保持ラッチ（MRL）（数量：左舷：支持組立4（肩部取付点1＋MRL付きペデスタル3）、右舷（OBSS用）：MRL付きペデスタル3、ペイロード支援（PDRS・ODS）） */ }
        part def <'PHY-PLS-03'> PHY_PLS_03 { doc /* マニピュレータ制御インタフェースユニット（MCIU）とRMS専用表示・操作器（数量：MCIU 1台（RMSフライトでは通常予備1台を搭載）、ペイロード支援（PDRS・ODS）） */ }
        part def <'PHY-PLS-04'> PHY_PLS_04 { doc /* オービタドッキングシステム（ODS）：トラス組立とAPDSドッキング機構（数量：1式（外部エアロック・トラス組立・APDSの3主要構成品）。APDSは構造フック12対とペタル3枚の伸展式ガイドリングを持つ、ペイロード支援（PDRS・ODS）） */ }
        part def <'PHY-PLS-05'> PHY_PLS_05 { doc /* APDSアビオニクス（PSU・DSCU・DMCU・PACU・LACU・DCU・PFCU）と操作パネル（A6L・A7L）（数量：アビオニクスボックス9台、操作パネル2面、ペイロード支援（PDRS・ODS）） */ }
        part def <'PHY-EVA-01'> PHY_EVA_01 { doc /* 船外活動ユニット（EMU）（数量：ベースラインのミッションで2着、船外活動（EVA/EMU）） */ }
        part def <'PHY-EVA-02'> PHY_EVA_02 { doc /* 外部エアロック（ハッチ3基・EMU支援機器付き）（数量：1基（直径63インチ、長さ83インチ強、D形40インチ開口のハッチ3基：内側ハッチ・EVハッチ・ドッキングハッチ）、船外活動（EVA/EMU）） */ }
        part def <'PHY-EVA-03'> PHY_EVA_03 { doc /* ペイロードベイのEVA支援機器（スライドワイヤ・EVAウインチ・ハンドレール）（数量：スライドワイヤ2本（各舷1本、長さ約46フィート）、EVAウインチ（前後の隔壁）、船外活動（EVA/EMU）） */ }
        part def <'PHY-EVA-04'> PHY_EVA_04 { doc /* ミニワークステーション（MWS）とBRT（数量：MWS 2・BRT 2（EMU 2着分。ベースプレートは EMU、T バー・スイングアーム・BRT はミッドデッキに収める）、船外活動（EVA/EMU）） */ }
        part def <'PHY-EVA-05'> PHY_EVA_05 { doc /* 左舷の軽量工具収納組立（TSA）（数量：1（前後のトレイ）、船外活動（EVA/EMU）） */ }
        part def <'PHY-EVA-06'> PHY_EVA_06 { doc /* EVA 機器の電池と充電器（EHIP ライト電池充電器・REBA 充電器・Y ケーブル・アダプタケーブル・延長ケーブルと、PGT 電池・ヘルメットライト電池）（数量：EHIP 充電器 1・REBA 充電器 1・PGT 電池 2・ヘルメットライト電池 4・アダプタケーブル 2・25 ft 延長ケーブル（必要なとき）、船外活動（EVA/EMU）） */ }
        part def <'PHY-EVA-07'> PHY_EVA_07 { doc /* 簡易着用マスク（マスク前呼吸用）と 14 ft の通信・O2 アンビリカル（数量：EV1・EV2 の各1式（アンビリカル 2）、船外活動（EVA/EMU）） */ }
        part def <'PHY-EVA-08'> PHY_EVA_08 { doc /* 非常時 EVA の工具一式（中心線ラッチ工具・3点ラッチ工具・RMS ロープリール・調整式テザー・大型カッタ・PRD）（数量：中心線ラッチ工具 2・3点ラッチ工具 2・RMS ロープリール 1・調整式テザー 2・大型カッタ 1・PRD 2、船外活動（EVA/EMU）） */ }
        part def <'PHY-EVA-09'> PHY_EVA_09 { doc /* PGT とヘルメットライトの電池（数量：PGT の電池 2・ヘルメットライトの電池 4、船外活動（EVA/EMU）） */ }
        part def OrbiterLayout {
            doc /* オービタの物理配置：区画と、区画に置いた機器 */
            part <'FD'> fd : Compartment {
                doc /* フライトデッキ */
                part phy_ct_12 : PHY_CT_12[1];
                part phy_dps_04 : PHY_DPS_04[4];
                part phy_gnc_01 : PHY_GNC_01[3];
                part phy_eclss_15 : PHY_ECLSS_15;
                part phy_cw_02 : PHY_CW_02[1];
                part phy_cw_04 : PHY_CW_04[1];
                part phy_crew_05 : PHY_CREW_05;
                part phy_pls_03 : PHY_PLS_03;
            }
            part <'MD'> md : Compartment {
                doc /* ミッドデッキ */
                part phy_eclss_20 : PHY_ECLSS_20;
                part phy_eclss_21 : PHY_ECLSS_21;
                part phy_eclss_26 : PHY_ECLSS_26;
                part phy_eclss_27 : PHY_ECLSS_27;
                part phy_crew_02 : PHY_CREW_02;
                part phy_crew_03 : PHY_CREW_03;
                part phy_crew_04 : PHY_CREW_04;
                part phy_eva_06 : PHY_EVA_06;
                part phy_eva_09 : PHY_EVA_09;
            }
            part <'LEB'> leb : Compartment {
                doc /* 下部機器ベイ */
                part phy_eclss_01 : PHY_ECLSS_01;
                part phy_eclss_02 : PHY_ECLSS_02;
                part phy_eclss_12 : PHY_ECLSS_12;
                part phy_eclss_13 : PHY_ECLSS_13;
                part phy_eclss_23 : PHY_ECLSS_23;
                part phy_eclss_24 : PHY_ECLSS_24;
            }
            part <'AVB1'> avb1 : Compartment {
                doc /* 前方アビオニクスベイ1 */
                part phy_ct_06 : PHY_CT_06;
            }
            part <'AVB2'> avb2 : Compartment { doc /* 前方アビオニクスベイ2（配分表の機器なし） */ }
            part <'AVB3A'> avb3a : Compartment {
                doc /* 前方アビオニクスベイ3A */
                part phy_ct_01 : PHY_CT_01[2];
                part phy_ct_04 : PHY_CT_04[2];
                part phy_ct_05 : PHY_CT_05[1];
                part phy_ct_07 : PHY_CT_07;
                part phy_cw_01 : PHY_CW_01[1];
            }
            part <'AVB3B'> avb3b : Compartment {
                doc /* 前方アビオニクスベイ3B */
                part phy_ct_09 : PHY_CT_09[1];
                part phy_dps_05 : PHY_DPS_05[1];
            }
            part <'AVBF'> avbf : Compartment {
                doc /* 前方アビオニクスベイ（複数） */
                part phy_ct_10 : PHY_CT_10[2];
                part phy_dps_01 : PHY_DPS_01[5];
                part phy_dps_02 : PHY_DPS_02[2];
                part phy_gnc_03 : PHY_GNC_03;
                part phy_gnc_05 : PHY_GNC_05[3];
                part phy_rcs_05 : PHY_RCS_05[2];
                part phy_eps_03 : PHY_EPS_03[9];
                part phy_eclss_14 : PHY_ECLSS_14;
                part phy_eclss_16 : PHY_ECLSS_16;
            }
            part <'AIRLOCK'> airlock : Compartment {
                doc /* エアロック */
                part phy_ct_11 : PHY_CT_11;
                part phy_eclss_35 : PHY_ECLSS_35;
                part phy_eclss_36 : PHY_ECLSS_36;
                part phy_eclss_37 : PHY_ECLSS_37;
                part phy_eclss_38 : PHY_ECLSS_38;
                part phy_eclss_39 : PHY_ECLSS_39;
                part phy_pls_05 : PHY_PLS_05;
                part phy_eva_01 : PHY_EVA_01;
                part phy_eva_02 : PHY_EVA_02;
            }
            part <'FWD'> fwd : Compartment {
                doc /* 前部胴体（乗員室の外） */
                part phy_ct_02 : PHY_CT_02[4];
                part phy_ct_08 : PHY_CT_08;
                part phy_gnc_02 : PHY_GNC_02[2];
                part phy_tps_01 : PHY_TPS_01;
                part phy_str_01 : PHY_STR_01;
                part phy_mech_04 : PHY_MECH_04;
            }
            part <'FRCS'> frcs : Compartment {
                doc /* 前部 RCS モジュール */
                part phy_rcs_01 : PHY_RCS_01[16];
                part phy_rcs_03 : PHY_RCS_03;
            }
            part <'PLB'> plb : Compartment {
                doc /* ペイロードベイ */
                part phy_ct_03 : PHY_CT_03[1];
                part phy_eclss_03 : PHY_ECLSS_03;
                part phy_eclss_05 : PHY_ECLSS_05;
                part phy_mech_01 : PHY_MECH_01;
                part phy_pls_01 : PHY_PLS_01;
                part phy_pls_02 : PHY_PLS_02;
                part phy_pls_04 : PHY_PLS_04;
                part phy_eva_03 : PHY_EVA_03;
                part phy_eva_05 : PHY_EVA_05[1];
                part phy_eva_08 : PHY_EVA_08;
            }
            part <'MID'> mid : Compartment {
                doc /* 中部胴体（床下・側面） */
                part phy_eps_01 : PHY_EPS_01[3];
                part phy_eps_02 : PHY_EPS_02;
                part phy_eclss_04 : PHY_ECLSS_04;
                part phy_eclss_07 : PHY_ECLSS_07;
                part phy_str_03 : PHY_STR_03;
            }
            part <'AFT'> aft : Compartment {
                doc /* 後部胴体 */
                part phy_eclss_06 : PHY_ECLSS_06;
                part phy_eclss_09 : PHY_ECLSS_09[3];
                part phy_eclss_10 : PHY_ECLSS_10[1];
                part phy_apu_01 : PHY_APU_01[3];
                part phy_apu_02 : PHY_APU_02[3];
                part phy_apu_03 : PHY_APU_03[3];
                part phy_apu_04 : PHY_APU_04[3];
                part phy_apu_05 : PHY_APU_05;
                part phy_apu_06 : PHY_APU_06[1];
                part phy_oms_05 : PHY_OMS_05;
                part phy_mps_01 : PHY_MPS_01[3];
                part phy_mps_02 : PHY_MPS_02[3];
                part phy_mps_03 : PHY_MPS_03[6];
                part phy_mps_06 : PHY_MPS_06;
                part phy_mps_07 : PHY_MPS_07;
                part phy_mps_08 : PHY_MPS_08;
                part phy_str_05 : PHY_STR_05;
                part phy_mech_02 : PHY_MECH_02;
            }
            part <'AVBA'> avba : Compartment {
                doc /* 後部アビオニクスベイ4〜6 */
                part phy_dps_07 : PHY_DPS_07;
                part phy_gnc_06 : PHY_GNC_06[4];
                part phy_rcs_07 : PHY_RCS_07[2];
                part phy_mps_04 : PHY_MPS_04[4];
            }
            part <'POD'> pod : Compartment {
                doc /* OMS/RCS ポッド */
                part phy_rcs_02 : PHY_RCS_02[28];
                part phy_rcs_04 : PHY_RCS_04;
                part phy_rcs_06 : PHY_RCS_06;
                part phy_oms_01 : PHY_OMS_01[2];
                part phy_oms_02 : PHY_OMS_02[4];
                part phy_oms_03 : PHY_OMS_03[2];
                part phy_oms_04 : PHY_OMS_04[4];
            }
            part <'WING'> wing : Compartment {
                doc /* 主翼 */
                part phy_tps_02 : PHY_TPS_02;
                part phy_str_04 : PHY_STR_04;
                part phy_mech_05 : PHY_MECH_05;
            }
            part <'VT'> vt : Compartment {
                doc /* 垂直尾翼 */
                part phy_str_06 : PHY_STR_06;
                part phy_mech_06 : PHY_MECH_06;
            }
            part <'MULTI'> multi : Compartment {
                doc /* 複数区画に分散 */
                part phy_dps_03 : PHY_DPS_03;
                part phy_dps_06 : PHY_DPS_06;
                part phy_gnc_04 : PHY_GNC_04;
                part phy_rcs_08 : PHY_RCS_08;
                part phy_eps_04 : PHY_EPS_04;
                part phy_eps_05 : PHY_EPS_05[10];
                part phy_eclss_08 : PHY_ECLSS_08;
                part phy_eclss_11 : PHY_ECLSS_11;
                part phy_eclss_17 : PHY_ECLSS_17;
                part phy_eclss_18 : PHY_ECLSS_18;
                part phy_eclss_19 : PHY_ECLSS_19;
                part phy_eclss_22 : PHY_ECLSS_22;
                part phy_eclss_25 : PHY_ECLSS_25;
                part phy_eclss_28 : PHY_ECLSS_28;
                part phy_eclss_29 : PHY_ECLSS_29;
                part phy_eclss_30 : PHY_ECLSS_30;
                part phy_eclss_31 : PHY_ECLSS_31;
                part phy_eclss_32 : PHY_ECLSS_32;
                part phy_eclss_33 : PHY_ECLSS_33;
                part phy_eclss_34 : PHY_ECLSS_34;
                part phy_apu_07 : PHY_APU_07;
                part phy_mps_05 : PHY_MPS_05[10];
                part phy_tps_03 : PHY_TPS_03;
                part phy_tps_04 : PHY_TPS_04;
                part phy_tps_05 : PHY_TPS_05;
                part phy_str_02 : PHY_STR_02;
                part phy_mech_03 : PHY_MECH_03;
                part phy_cw_03 : PHY_CW_03[4];
                part phy_cw_05 : PHY_CW_05[9];
                part phy_crew_01 : PHY_CREW_01;
                part phy_eva_04 : PHY_EVA_04;
                part phy_eva_07 : PHY_EVA_07;
            }
        }
        part orbiterLayout : OrbiterLayout;
    }
    // ---- 論理の割付：機能 → 機能行を持つ機能説明書の部品
    package LogicalAllocation {
        allocate Functions::FN_EXT::F_NET_01 to context.ext;
        allocate Functions::FN_EXT::F_NET_02 to context.ext;
        allocate Functions::FN_EXT::F_NET_03 to context.ext;
        allocate Functions::FN_EXT::F_NET_04 to context.ext;
        allocate Functions::FN_EXT::F_MCC_01 to context.ext;
        allocate Functions::FN_EXT::F_MCC_02 to context.ext;
        allocate Functions::FN_EXT::F_MCC_03 to context.ext;
        allocate Functions::FN_EXT::F_LPS_01 to context.ext;
        allocate Functions::FN_EXT::F_LPS_02 to context.ext;
        allocate Functions::FN_ET::F_ET_01 to context.sts.et;
        allocate Functions::FN_ET::F_ET_02 to context.sts.et;
        allocate Functions::FN_ET::F_ET_03 to context.sts.et;
        allocate Functions::FN_ET::F_ET_04 to context.sts.et;
        allocate Functions::FN_ET_ITK::F_ET_ITK_01 to context.sts.et.itk;
        allocate Functions::FN_ET_ITK::F_ET_ITK_02 to context.sts.et.itk;
        allocate Functions::FN_ET_ITK::F_ET_ITK_03 to context.sts.et.itk;
        allocate Functions::FN_ET_ITK::F_ET_ITK_04 to context.sts.et.itk;
        allocate Functions::FN_ET_ITK::F_ET_ITK_05 to context.sts.et.itk;
        allocate Functions::FN_ET_ITK::F_ET_ITK_06 to context.sts.et.itk;
        allocate Functions::FN_ET_LH2::F_ET_LH2_01 to context.sts.et.lh2;
        allocate Functions::FN_ET_LH2::F_ET_LH2_02 to context.sts.et.lh2;
        allocate Functions::FN_ET_LH2::F_ET_LH2_03 to context.sts.et.lh2;
        allocate Functions::FN_ET_LH2::F_ET_LH2_04 to context.sts.et.lh2;
        allocate Functions::FN_ET_LH2::F_ET_LH2_05 to context.sts.et.lh2;
        allocate Functions::FN_ET_LH2::F_ET_LH2_06 to context.sts.et.lh2;
        allocate Functions::FN_ET_LOX::F_ET_LOX_01 to context.sts.et.lox;
        allocate Functions::FN_ET_LOX::F_ET_LOX_02 to context.sts.et.lox;
        allocate Functions::FN_ET_LOX::F_ET_LOX_03 to context.sts.et.lox;
        allocate Functions::FN_ET_LOX::F_ET_LOX_04 to context.sts.et.lox;
        allocate Functions::FN_ET_LOX::F_ET_LOX_05 to context.sts.et.lox;
        allocate Functions::FN_ET_LOX::F_ET_LOX_06 to context.sts.et.lox;
        allocate Functions::FN_ET_LOX::F_ET_LOX_07 to context.sts.et.lox;
        allocate Functions::FN_ET_SEP::F_ET_SEP_01 to context.sts.et.sep;
        allocate Functions::FN_ET_SEP::F_ET_SEP_02 to context.sts.et.sep;
        allocate Functions::FN_ET_SEP::F_ET_SEP_03 to context.sts.et.sep;
        allocate Functions::FN_ET_SEP::F_ET_SEP_04 to context.sts.et.sep;
        allocate Functions::FN_ET_SEP::F_ET_SEP_05 to context.sts.et.sep;
        allocate Functions::FN_ET_SEP::F_ET_SEP_06 to context.sts.et.sep;
        allocate Functions::FN_ET_SEP::F_ET_SEP_07 to context.sts.et.sep;
        allocate Functions::FN_ET_TPS::F_ET_TPS_01 to context.sts.et.tps;
        allocate Functions::FN_ET_TPS::F_ET_TPS_02 to context.sts.et.tps;
        allocate Functions::FN_ET_TPS::F_ET_TPS_03 to context.sts.et.tps;
        allocate Functions::FN_ET_TPS::F_ET_TPS_04 to context.sts.et.tps;
        allocate Functions::FN_ET_TPS::F_ET_TPS_05 to context.sts.et.tps;
        allocate Functions::FN_ET_TPS::F_ET_TPS_06 to context.sts.et.tps;
        allocate Functions::FN_ET_UMB::F_ET_UMB_01 to context.sts.et.umb;
        allocate Functions::FN_ET_UMB::F_ET_UMB_02 to context.sts.et.umb;
        allocate Functions::FN_ET_UMB::F_ET_UMB_03 to context.sts.et.umb;
        allocate Functions::FN_ET_UMB::F_ET_UMB_04 to context.sts.et.umb;
        allocate Functions::FN_ET_UMB::F_ET_UMB_05 to context.sts.et.umb;
        allocate Functions::FN_ET_UMB::F_ET_UMB_06 to context.sts.et.umb;
        allocate Functions::FN_ET_UMB::F_ET_UMB_07 to context.sts.et.umb;
        allocate Functions::FN_ORB::F_ORB_01 to context.sts.orb;
        allocate Functions::FN_ORB::F_ORB_02 to context.sts.orb;
        allocate Functions::FN_ORB::F_ORB_03 to context.sts.orb;
        allocate Functions::FN_APU::F_APU_01 to context.sts.orb.apu;
        allocate Functions::FN_APU::F_APU_02 to context.sts.orb.apu;
        allocate Functions::FN_APU::F_APU_03 to context.sts.orb.apu;
        allocate Functions::FN_APU::F_APU_04 to context.sts.orb.apu;
        allocate Functions::FN_APU::F_APU_05 to context.sts.orb.apu;
        allocate Functions::FN_APU_CIR::F_APU_CIR_01 to context.sts.orb.apu.cir;
        allocate Functions::FN_APU_CIR::F_APU_CIR_02 to context.sts.orb.apu.cir;
        allocate Functions::FN_APU_CIR::F_APU_CIR_03 to context.sts.orb.apu.cir;
        allocate Functions::FN_APU_CIR::F_APU_CIR_04 to context.sts.orb.apu.cir;
        allocate Functions::FN_APU_CIR::F_APU_CIR_05 to context.sts.orb.apu.cir;
        allocate Functions::FN_APU_CIR::F_APU_CIR_06 to context.sts.orb.apu.cir;
        allocate Functions::FN_APU_CIR::F_APU_CIR_07 to context.sts.orb.apu.cir;
        allocate Functions::FN_APU_CIR::F_APU_CIR_08 to context.sts.orb.apu.cir;
        allocate Functions::FN_APU_CIR::F_APU_CIR_09 to context.sts.orb.apu.cir;
        allocate Functions::FN_APU_CIR::F_APU_CIR_10 to context.sts.orb.apu.cir;
        allocate Functions::FN_APU_CIR::F_APU_CIR_11 to context.sts.orb.apu.cir;
        allocate Functions::FN_APU_CIR::F_APU_CIR_12 to context.sts.orb.apu.cir;
        allocate Functions::FN_APU_CTL::F_APU_CTL_01 to context.sts.orb.apu.ctl;
        allocate Functions::FN_APU_CTL::F_APU_CTL_02 to context.sts.orb.apu.ctl;
        allocate Functions::FN_APU_CTL::F_APU_CTL_03 to context.sts.orb.apu.ctl;
        allocate Functions::FN_APU_CTL::F_APU_CTL_04 to context.sts.orb.apu.ctl;
        allocate Functions::FN_APU_CTL::F_APU_CTL_05 to context.sts.orb.apu.ctl;
        allocate Functions::FN_APU_CTL::F_APU_CTL_06 to context.sts.orb.apu.ctl;
        allocate Functions::FN_APU_CTL::F_APU_CTL_07 to context.sts.orb.apu.ctl;
        allocate Functions::FN_APU_CTL::F_APU_CTL_08 to context.sts.orb.apu.ctl;
        allocate Functions::FN_APU_CTL::F_APU_CTL_09 to context.sts.orb.apu.ctl;
        allocate Functions::FN_APU_CTL::F_APU_CTL_10 to context.sts.orb.apu.ctl;
        allocate Functions::FN_APU_CTL::F_APU_CTL_11 to context.sts.orb.apu.ctl;
        allocate Functions::FN_APU_CTL::F_APU_CTL_12 to context.sts.orb.apu.ctl;
        allocate Functions::FN_APU_FUL::F_APU_FUL_01 to context.sts.orb.apu.ful;
        allocate Functions::FN_APU_FUL::F_APU_FUL_02 to context.sts.orb.apu.ful;
        allocate Functions::FN_APU_FUL::F_APU_FUL_03 to context.sts.orb.apu.ful;
        allocate Functions::FN_APU_FUL::F_APU_FUL_04 to context.sts.orb.apu.ful;
        allocate Functions::FN_APU_FUL::F_APU_FUL_05 to context.sts.orb.apu.ful;
        allocate Functions::FN_APU_FUL::F_APU_FUL_06 to context.sts.orb.apu.ful;
        allocate Functions::FN_APU_FUL::F_APU_FUL_07 to context.sts.orb.apu.ful;
        allocate Functions::FN_APU_FUL::F_APU_FUL_08 to context.sts.orb.apu.ful;
        allocate Functions::FN_APU_FUL::F_APU_FUL_09 to context.sts.orb.apu.ful;
        allocate Functions::FN_APU_FUL::F_APU_FUL_10 to context.sts.orb.apu.ful;
        allocate Functions::FN_APU_FUL::F_APU_FUL_11 to context.sts.orb.apu.ful;
        allocate Functions::FN_APU_FUL::F_APU_FUL_12 to context.sts.orb.apu.ful;
        allocate Functions::FN_APU_HYD::F_APU_HYD_01 to context.sts.orb.apu.hyd;
        allocate Functions::FN_APU_HYD::F_APU_HYD_02 to context.sts.orb.apu.hyd;
        allocate Functions::FN_APU_HYD::F_APU_HYD_03 to context.sts.orb.apu.hyd;
        allocate Functions::FN_APU_HYD::F_APU_HYD_04 to context.sts.orb.apu.hyd;
        allocate Functions::FN_APU_HYD::F_APU_HYD_05 to context.sts.orb.apu.hyd;
        allocate Functions::FN_APU_HYD::F_APU_HYD_06 to context.sts.orb.apu.hyd;
        allocate Functions::FN_APU_HYD::F_APU_HYD_07 to context.sts.orb.apu.hyd;
        allocate Functions::FN_APU_HYD::F_APU_HYD_08 to context.sts.orb.apu.hyd;
        allocate Functions::FN_APU_HYD::F_APU_HYD_09 to context.sts.orb.apu.hyd;
        allocate Functions::FN_APU_HYD::F_APU_HYD_10 to context.sts.orb.apu.hyd;
        allocate Functions::FN_APU_HYD::F_APU_HYD_11 to context.sts.orb.apu.hyd;
        allocate Functions::FN_APU_HYD::F_APU_HYD_12 to context.sts.orb.apu.hyd;
        allocate Functions::FN_APU_HYD::F_APU_HYD_13 to context.sts.orb.apu.hyd;
        allocate Functions::FN_APU_OPS::F_APU_OPS_01 to context.sts.orb.apu.ops;
        allocate Functions::FN_APU_OPS::F_APU_OPS_02 to context.sts.orb.apu.ops;
        allocate Functions::FN_APU_OPS::F_APU_OPS_03 to context.sts.orb.apu.ops;
        allocate Functions::FN_APU_OPS::F_APU_OPS_04 to context.sts.orb.apu.ops;
        allocate Functions::FN_APU_OPS::F_APU_OPS_05 to context.sts.orb.apu.ops;
        allocate Functions::FN_APU_OPS::F_APU_OPS_06 to context.sts.orb.apu.ops;
        allocate Functions::FN_APU_OPS::F_APU_OPS_07 to context.sts.orb.apu.ops;
        allocate Functions::FN_APU_OPS::F_APU_OPS_08 to context.sts.orb.apu.ops;
        allocate Functions::FN_APU_OPS::F_APU_OPS_09 to context.sts.orb.apu.ops;
        allocate Functions::FN_APU_OPS::F_APU_OPS_10 to context.sts.orb.apu.ops;
        allocate Functions::FN_APU_OPS::F_APU_OPS_11 to context.sts.orb.apu.ops;
        allocate Functions::FN_APU_OPS::F_APU_OPS_12 to context.sts.orb.apu.ops;
        allocate Functions::FN_APU_TRB::F_APU_TRB_01 to context.sts.orb.apu.trb;
        allocate Functions::FN_APU_TRB::F_APU_TRB_02 to context.sts.orb.apu.trb;
        allocate Functions::FN_APU_TRB::F_APU_TRB_03 to context.sts.orb.apu.trb;
        allocate Functions::FN_APU_TRB::F_APU_TRB_04 to context.sts.orb.apu.trb;
        allocate Functions::FN_APU_TRB::F_APU_TRB_05 to context.sts.orb.apu.trb;
        allocate Functions::FN_APU_TRB::F_APU_TRB_06 to context.sts.orb.apu.trb;
        allocate Functions::FN_APU_TRB::F_APU_TRB_07 to context.sts.orb.apu.trb;
        allocate Functions::FN_APU_TRB::F_APU_TRB_08 to context.sts.orb.apu.trb;
        allocate Functions::FN_APU_TRB::F_APU_TRB_09 to context.sts.orb.apu.trb;
        allocate Functions::FN_APU_TRB::F_APU_TRB_10 to context.sts.orb.apu.trb;
        allocate Functions::FN_APU_TRB::F_APU_TRB_11 to context.sts.orb.apu.trb;
        allocate Functions::FN_APU_TRB::F_APU_TRB_12 to context.sts.orb.apu.trb;
        allocate Functions::FN_APU_TRB::F_APU_TRB_13 to context.sts.orb.apu.trb;
        allocate Functions::FN_APU_WSB::F_APU_WSB_01 to context.sts.orb.apu.wsb;
        allocate Functions::FN_APU_WSB::F_APU_WSB_02 to context.sts.orb.apu.wsb;
        allocate Functions::FN_APU_WSB::F_APU_WSB_03 to context.sts.orb.apu.wsb;
        allocate Functions::FN_APU_WSB::F_APU_WSB_04 to context.sts.orb.apu.wsb;
        allocate Functions::FN_APU_WSB::F_APU_WSB_05 to context.sts.orb.apu.wsb;
        allocate Functions::FN_APU_WSB::F_APU_WSB_06 to context.sts.orb.apu.wsb;
        allocate Functions::FN_APU_WSB::F_APU_WSB_07 to context.sts.orb.apu.wsb;
        allocate Functions::FN_APU_WSB::F_APU_WSB_08 to context.sts.orb.apu.wsb;
        allocate Functions::FN_APU_WSB::F_APU_WSB_09 to context.sts.orb.apu.wsb;
        allocate Functions::FN_APU_WSB::F_APU_WSB_10 to context.sts.orb.apu.wsb;
        allocate Functions::FN_APU_WSB::F_APU_WSB_11 to context.sts.orb.apu.wsb;
        allocate Functions::FN_APU_WSB::F_APU_WSB_12 to context.sts.orb.apu.wsb;
        allocate Functions::FN_APU_WSB::F_APU_WSB_13 to context.sts.orb.apu.wsb;
        allocate Functions::FN_CREW::F_CREW_01 to context.sts.orb.crew;
        allocate Functions::FN_CREW::F_CREW_02 to context.sts.orb.crew;
        allocate Functions::FN_CREW::F_CREW_03 to context.sts.orb.crew;
        allocate Functions::FN_CREW::F_CREW_04 to context.sts.orb.crew;
        allocate Functions::FN_CREW::F_CREW_05 to context.sts.orb.crew;
        allocate Functions::FN_CREW::F_CREW_06 to context.sts.orb.crew;
        allocate Functions::FN_CREW_ESC::F_CREW_ESC_01 to context.sts.orb.crew.esc;
        allocate Functions::FN_CREW_ESC::F_CREW_ESC_02 to context.sts.orb.crew.esc;
        allocate Functions::FN_CREW_ESC::F_CREW_ESC_03 to context.sts.orb.crew.esc;
        allocate Functions::FN_CREW_ESC::F_CREW_ESC_04 to context.sts.orb.crew.esc;
        allocate Functions::FN_CREW_ESC::F_CREW_ESC_05 to context.sts.orb.crew.esc;
        allocate Functions::FN_CREW_ESC::F_CREW_ESC_06 to context.sts.orb.crew.esc;
        allocate Functions::FN_CREW_ESC::F_CREW_ESC_07 to context.sts.orb.crew.esc;
        allocate Functions::FN_CREW_ESC::F_CREW_ESC_08 to context.sts.orb.crew.esc;
        allocate Functions::FN_CREW_ESC::F_CREW_ESC_09 to context.sts.orb.crew.esc;
        allocate Functions::FN_CREW_HAB::F_CREW_HAB_01 to context.sts.orb.crew.hab;
        allocate Functions::FN_CREW_HAB::F_CREW_HAB_02 to context.sts.orb.crew.hab;
        allocate Functions::FN_CREW_HAB::F_CREW_HAB_03 to context.sts.orb.crew.hab;
        allocate Functions::FN_CREW_HAB::F_CREW_HAB_04 to context.sts.orb.crew.hab;
        allocate Functions::FN_CREW_HAB::F_CREW_HAB_05 to context.sts.orb.crew.hab;
        allocate Functions::FN_CREW_HAB::F_CREW_HAB_06 to context.sts.orb.crew.hab;
        allocate Functions::FN_CREW_HAB::F_CREW_HAB_07 to context.sts.orb.crew.hab;
        allocate Functions::FN_CREW_HAB::F_CREW_HAB_08 to context.sts.orb.crew.hab;
        allocate Functions::FN_CREW_LTG::F_CREW_LTG_01 to context.sts.orb.crew.ltg;
        allocate Functions::FN_CREW_LTG::F_CREW_LTG_02 to context.sts.orb.crew.ltg;
        allocate Functions::FN_CREW_LTG::F_CREW_LTG_03 to context.sts.orb.crew.ltg;
        allocate Functions::FN_CREW_LTG::F_CREW_LTG_04 to context.sts.orb.crew.ltg;
        allocate Functions::FN_CREW_LTG::F_CREW_LTG_05 to context.sts.orb.crew.ltg;
        allocate Functions::FN_CREW_LTG::F_CREW_LTG_06 to context.sts.orb.crew.ltg;
        allocate Functions::FN_CREW_LTG::F_CREW_LTG_07 to context.sts.orb.crew.ltg;
        allocate Functions::FN_CREW_MED::F_CREW_MED_01 to context.sts.orb.crew.med;
        allocate Functions::FN_CREW_MED::F_CREW_MED_02 to context.sts.orb.crew.med;
        allocate Functions::FN_CREW_MED::F_CREW_MED_03 to context.sts.orb.crew.med;
        allocate Functions::FN_CREW_MED::F_CREW_MED_04 to context.sts.orb.crew.med;
        allocate Functions::FN_CREW_MED::F_CREW_MED_05 to context.sts.orb.crew.med;
        allocate Functions::FN_CREW_MED::F_CREW_MED_06 to context.sts.orb.crew.med;
        allocate Functions::FN_CREW_MED::F_CREW_MED_07 to context.sts.orb.crew.med;
        allocate Functions::FN_CREW_OPS::F_CREW_OPS_01 to context.sts.orb.crew.ops;
        allocate Functions::FN_CREW_OPS::F_CREW_OPS_02 to context.sts.orb.crew.ops;
        allocate Functions::FN_CREW_OPS::F_CREW_OPS_03 to context.sts.orb.crew.ops;
        allocate Functions::FN_CREW_OPS::F_CREW_OPS_04 to context.sts.orb.crew.ops;
        allocate Functions::FN_CREW_OPS::F_CREW_OPS_05 to context.sts.orb.crew.ops;
        allocate Functions::FN_CREW_OPS::F_CREW_OPS_06 to context.sts.orb.crew.ops;
        allocate Functions::FN_CREW_OPS::F_CREW_OPS_07 to context.sts.orb.crew.ops;
        allocate Functions::FN_CREW_OPS::F_CREW_OPS_08 to context.sts.orb.crew.ops;
        allocate Functions::FN_CREW_STW::F_CREW_STW_01 to context.sts.orb.crew.stw;
        allocate Functions::FN_CREW_STW::F_CREW_STW_02 to context.sts.orb.crew.stw;
        allocate Functions::FN_CREW_STW::F_CREW_STW_03 to context.sts.orb.crew.stw;
        allocate Functions::FN_CREW_STW::F_CREW_STW_04 to context.sts.orb.crew.stw;
        allocate Functions::FN_CREW_STW::F_CREW_STW_05 to context.sts.orb.crew.stw;
        allocate Functions::FN_CREW_STW::F_CREW_STW_06 to context.sts.orb.crew.stw;
        allocate Functions::FN_CREW_STW::F_CREW_STW_07 to context.sts.orb.crew.stw;
        allocate Functions::FN_CT::F_CT_01 to context.sts.orb.ct;
        allocate Functions::FN_CT::F_CT_02 to context.sts.orb.ct;
        allocate Functions::FN_CT::F_CT_03 to context.sts.orb.ct;
        allocate Functions::FN_CT::F_CT_04 to context.sts.orb.ct;
        allocate Functions::FN_CT_AUD::F_CT_AUD_01 to context.sts.orb.ct.aud;
        allocate Functions::FN_CT_AUD::F_CT_AUD_02 to context.sts.orb.ct.aud;
        allocate Functions::FN_CT_AUD::F_CT_AUD_03 to context.sts.orb.ct.aud;
        allocate Functions::FN_CT_AUD::F_CT_AUD_04 to context.sts.orb.ct.aud;
        allocate Functions::FN_CT_AUD::F_CT_AUD_05 to context.sts.orb.ct.aud;
        allocate Functions::FN_CT_AUD::F_CT_AUD_06 to context.sts.orb.ct.aud;
        allocate Functions::FN_CT_AUD::F_CT_AUD_07 to context.sts.orb.ct.aud;
        allocate Functions::FN_CT_AUD::F_CT_AUD_08 to context.sts.orb.ct.aud;
        allocate Functions::FN_CT_AUD::F_CT_AUD_09 to context.sts.orb.ct.aud;
        allocate Functions::FN_CT_AUD::F_CT_AUD_10 to context.sts.orb.ct.aud;
        allocate Functions::FN_CT_AUD::F_CT_AUD_11 to context.sts.orb.ct.aud;
        allocate Functions::FN_CT_AUD::F_CT_AUD_12 to context.sts.orb.ct.aud;
        allocate Functions::FN_CT_CCTV::F_CT_CCTV_01 to context.sts.orb.ct.cctv;
        allocate Functions::FN_CT_CCTV::F_CT_CCTV_02 to context.sts.orb.ct.cctv;
        allocate Functions::FN_CT_CCTV::F_CT_CCTV_03 to context.sts.orb.ct.cctv;
        allocate Functions::FN_CT_CCTV::F_CT_CCTV_04 to context.sts.orb.ct.cctv;
        allocate Functions::FN_CT_CCTV::F_CT_CCTV_05 to context.sts.orb.ct.cctv;
        allocate Functions::FN_CT_CCTV::F_CT_CCTV_06 to context.sts.orb.ct.cctv;
        allocate Functions::FN_CT_CCTV::F_CT_CCTV_07 to context.sts.orb.ct.cctv;
        allocate Functions::FN_CT_CCTV::F_CT_CCTV_08 to context.sts.orb.ct.cctv;
        allocate Functions::FN_CT_CCTV::F_CT_CCTV_09 to context.sts.orb.ct.cctv;
        allocate Functions::FN_CT_CCTV::F_CT_CCTV_10 to context.sts.orb.ct.cctv;
        allocate Functions::FN_CT_CCTV::F_CT_CCTV_11 to context.sts.orb.ct.cctv;
        allocate Functions::FN_CT_CCTV::F_CT_CCTV_12 to context.sts.orb.ct.cctv;
        allocate Functions::FN_CT_INST::F_CT_INST_01 to context.sts.orb.ct.inst;
        allocate Functions::FN_CT_INST::F_CT_INST_02 to context.sts.orb.ct.inst;
        allocate Functions::FN_CT_INST::F_CT_INST_03 to context.sts.orb.ct.inst;
        allocate Functions::FN_CT_INST::F_CT_INST_04 to context.sts.orb.ct.inst;
        allocate Functions::FN_CT_INST::F_CT_INST_05 to context.sts.orb.ct.inst;
        allocate Functions::FN_CT_INST::F_CT_INST_06 to context.sts.orb.ct.inst;
        allocate Functions::FN_CT_INST::F_CT_INST_07 to context.sts.orb.ct.inst;
        allocate Functions::FN_CT_INST::F_CT_INST_08 to context.sts.orb.ct.inst;
        allocate Functions::FN_CT_INST::F_CT_INST_09 to context.sts.orb.ct.inst;
        allocate Functions::FN_CT_INST::F_CT_INST_10 to context.sts.orb.ct.inst;
        allocate Functions::FN_CT_INST::F_CT_INST_11 to context.sts.orb.ct.inst;
        allocate Functions::FN_CT_INST::F_CT_INST_12 to context.sts.orb.ct.inst;
        allocate Functions::FN_CT_KU::F_CT_KU_01 to context.sts.orb.ct.ku;
        allocate Functions::FN_CT_KU::F_CT_KU_02 to context.sts.orb.ct.ku;
        allocate Functions::FN_CT_KU::F_CT_KU_03 to context.sts.orb.ct.ku;
        allocate Functions::FN_CT_KU::F_CT_KU_04 to context.sts.orb.ct.ku;
        allocate Functions::FN_CT_KU::F_CT_KU_05 to context.sts.orb.ct.ku;
        allocate Functions::FN_CT_KU::F_CT_KU_06 to context.sts.orb.ct.ku;
        allocate Functions::FN_CT_KU::F_CT_KU_07 to context.sts.orb.ct.ku;
        allocate Functions::FN_CT_KU::F_CT_KU_08 to context.sts.orb.ct.ku;
        allocate Functions::FN_CT_KU::F_CT_KU_09 to context.sts.orb.ct.ku;
        allocate Functions::FN_CT_KU::F_CT_KU_10 to context.sts.orb.ct.ku;
        allocate Functions::FN_CT_KU::F_CT_KU_11 to context.sts.orb.ct.ku;
        allocate Functions::FN_CT_KU::F_CT_KU_12 to context.sts.orb.ct.ku;
        allocate Functions::FN_CT_OPS::F_CT_OPS_01 to context.sts.orb.ct.ops;
        allocate Functions::FN_CT_OPS::F_CT_OPS_02 to context.sts.orb.ct.ops;
        allocate Functions::FN_CT_OPS::F_CT_OPS_03 to context.sts.orb.ct.ops;
        allocate Functions::FN_CT_OPS::F_CT_OPS_04 to context.sts.orb.ct.ops;
        allocate Functions::FN_CT_OPS::F_CT_OPS_05 to context.sts.orb.ct.ops;
        allocate Functions::FN_CT_OPS::F_CT_OPS_06 to context.sts.orb.ct.ops;
        allocate Functions::FN_CT_OPS::F_CT_OPS_07 to context.sts.orb.ct.ops;
        allocate Functions::FN_CT_OPS::F_CT_OPS_08 to context.sts.orb.ct.ops;
        allocate Functions::FN_CT_OPS::F_CT_OPS_09 to context.sts.orb.ct.ops;
        allocate Functions::FN_CT_OPS::F_CT_OPS_10 to context.sts.orb.ct.ops;
        allocate Functions::FN_CT_OPS::F_CT_OPS_11 to context.sts.orb.ct.ops;
        allocate Functions::FN_CT_OPS::F_CT_OPS_12 to context.sts.orb.ct.ops;
        allocate Functions::FN_CT_SBD::F_CT_SBD_01 to context.sts.orb.ct.sbd;
        allocate Functions::FN_CT_SBD::F_CT_SBD_02 to context.sts.orb.ct.sbd;
        allocate Functions::FN_CT_SBD::F_CT_SBD_03 to context.sts.orb.ct.sbd;
        allocate Functions::FN_CT_SBD::F_CT_SBD_04 to context.sts.orb.ct.sbd;
        allocate Functions::FN_CT_SBD::F_CT_SBD_05 to context.sts.orb.ct.sbd;
        allocate Functions::FN_CT_SBD::F_CT_SBD_06 to context.sts.orb.ct.sbd;
        allocate Functions::FN_CT_SBD::F_CT_SBD_07 to context.sts.orb.ct.sbd;
        allocate Functions::FN_CT_SBD::F_CT_SBD_08 to context.sts.orb.ct.sbd;
        allocate Functions::FN_CT_SBD::F_CT_SBD_09 to context.sts.orb.ct.sbd;
        allocate Functions::FN_CT_SBD::F_CT_SBD_10 to context.sts.orb.ct.sbd;
        allocate Functions::FN_CT_SBD::F_CT_SBD_11 to context.sts.orb.ct.sbd;
        allocate Functions::FN_CT_SBD::F_CT_SBD_12 to context.sts.orb.ct.sbd;
        allocate Functions::FN_CT_UHF::F_CT_UHF_01 to context.sts.orb.ct.uhf;
        allocate Functions::FN_CT_UHF::F_CT_UHF_02 to context.sts.orb.ct.uhf;
        allocate Functions::FN_CT_UHF::F_CT_UHF_03 to context.sts.orb.ct.uhf;
        allocate Functions::FN_CT_UHF::F_CT_UHF_04 to context.sts.orb.ct.uhf;
        allocate Functions::FN_CT_UHF::F_CT_UHF_05 to context.sts.orb.ct.uhf;
        allocate Functions::FN_CT_UHF::F_CT_UHF_06 to context.sts.orb.ct.uhf;
        allocate Functions::FN_CT_UHF::F_CT_UHF_07 to context.sts.orb.ct.uhf;
        allocate Functions::FN_CT_UHF::F_CT_UHF_08 to context.sts.orb.ct.uhf;
        allocate Functions::FN_CT_UHF::F_CT_UHF_09 to context.sts.orb.ct.uhf;
        allocate Functions::FN_CT_UHF::F_CT_UHF_10 to context.sts.orb.ct.uhf;
        allocate Functions::FN_CT_UHF::F_CT_UHF_11 to context.sts.orb.ct.uhf;
        allocate Functions::FN_CT_UHF::F_CT_UHF_12 to context.sts.orb.ct.uhf;
        allocate Functions::FN_CW::F_CW_01 to context.sts.orb.cw;
        allocate Functions::FN_CW::F_CW_02 to context.sts.orb.cw;
        allocate Functions::FN_CW::F_CW_03 to context.sts.orb.cw;
        allocate Functions::FN_CW::F_CW_04 to context.sts.orb.cw;
        allocate Functions::FN_CW::F_CW_05 to context.sts.orb.cw;
        allocate Functions::FN_CW::F_CW_06 to context.sts.orb.cw;
        allocate Functions::FN_CW::F_CW_07 to context.sts.orb.cw;
        allocate Functions::FN_CW_ALT::F_CW_ALT_01 to context.sts.orb.cw.alt;
        allocate Functions::FN_CW_ALT::F_CW_ALT_02 to context.sts.orb.cw.alt;
        allocate Functions::FN_CW_ALT::F_CW_ALT_03 to context.sts.orb.cw.alt;
        allocate Functions::FN_CW_ALT::F_CW_ALT_04 to context.sts.orb.cw.alt;
        allocate Functions::FN_CW_ALT::F_CW_ALT_05 to context.sts.orb.cw.alt;
        allocate Functions::FN_CW_ALT::F_CW_ALT_06 to context.sts.orb.cw.alt;
        allocate Functions::FN_CW_ALT::F_CW_ALT_07 to context.sts.orb.cw.alt;
        allocate Functions::FN_CW_ANN::F_CW_ANN_01 to context.sts.orb.cw.ann;
        allocate Functions::FN_CW_ANN::F_CW_ANN_02 to context.sts.orb.cw.ann;
        allocate Functions::FN_CW_ANN::F_CW_ANN_03 to context.sts.orb.cw.ann;
        allocate Functions::FN_CW_ANN::F_CW_ANN_04 to context.sts.orb.cw.ann;
        allocate Functions::FN_CW_ANN::F_CW_ANN_05 to context.sts.orb.cw.ann;
        allocate Functions::FN_CW_ANN::F_CW_ANN_06 to context.sts.orb.cw.ann;
        allocate Functions::FN_CW_ANN::F_CW_ANN_07 to context.sts.orb.cw.ann;
        allocate Functions::FN_CW_ANN::F_CW_ANN_08 to context.sts.orb.cw.ann;
        allocate Functions::FN_CW_BKP::F_CW_BKP_01 to context.sts.orb.cw.bkp;
        allocate Functions::FN_CW_BKP::F_CW_BKP_02 to context.sts.orb.cw.bkp;
        allocate Functions::FN_CW_BKP::F_CW_BKP_03 to context.sts.orb.cw.bkp;
        allocate Functions::FN_CW_BKP::F_CW_BKP_04 to context.sts.orb.cw.bkp;
        allocate Functions::FN_CW_BKP::F_CW_BKP_05 to context.sts.orb.cw.bkp;
        allocate Functions::FN_CW_BKP::F_CW_BKP_06 to context.sts.orb.cw.bkp;
        allocate Functions::FN_CW_BKP::F_CW_BKP_07 to context.sts.orb.cw.bkp;
        allocate Functions::FN_CW_OPS::F_CW_OPS_01 to context.sts.orb.cw.ops;
        allocate Functions::FN_CW_OPS::F_CW_OPS_02 to context.sts.orb.cw.ops;
        allocate Functions::FN_CW_OPS::F_CW_OPS_03 to context.sts.orb.cw.ops;
        allocate Functions::FN_CW_OPS::F_CW_OPS_04 to context.sts.orb.cw.ops;
        allocate Functions::FN_CW_OPS::F_CW_OPS_05 to context.sts.orb.cw.ops;
        allocate Functions::FN_CW_OPS::F_CW_OPS_06 to context.sts.orb.cw.ops;
        allocate Functions::FN_CW_OPS::F_CW_OPS_07 to context.sts.orb.cw.ops;
        allocate Functions::FN_CW_OPS::F_CW_OPS_08 to context.sts.orb.cw.ops;
        allocate Functions::FN_CW_OPS::F_CW_OPS_09 to context.sts.orb.cw.ops;
        allocate Functions::FN_CW_PRI::F_CW_PRI_01 to context.sts.orb.cw.pri;
        allocate Functions::FN_CW_PRI::F_CW_PRI_02 to context.sts.orb.cw.pri;
        allocate Functions::FN_CW_PRI::F_CW_PRI_03 to context.sts.orb.cw.pri;
        allocate Functions::FN_CW_PRI::F_CW_PRI_04 to context.sts.orb.cw.pri;
        allocate Functions::FN_CW_PRI::F_CW_PRI_05 to context.sts.orb.cw.pri;
        allocate Functions::FN_CW_PRI::F_CW_PRI_06 to context.sts.orb.cw.pri;
        allocate Functions::FN_CW_PRI::F_CW_PRI_07 to context.sts.orb.cw.pri;
        allocate Functions::FN_CW_PRI::F_CW_PRI_08 to context.sts.orb.cw.pri;
        allocate Functions::FN_DPS::F_DPS_01 to context.sts.orb.dps;
        allocate Functions::FN_DPS::F_DPS_02 to context.sts.orb.dps;
        allocate Functions::FN_DPS::F_DPS_03 to context.sts.orb.dps;
        allocate Functions::FN_DPS::F_DPS_04 to context.sts.orb.dps;
        allocate Functions::FN_DPS::F_DPS_05 to context.sts.orb.dps;
        allocate Functions::FN_DPS_ASC::F_DPS_ASC_01 to context.sts.orb.dps.asc;
        allocate Functions::FN_DPS_ASC::F_DPS_ASC_02 to context.sts.orb.dps.asc;
        allocate Functions::FN_DPS_ASC::F_DPS_ASC_03 to context.sts.orb.dps.asc;
        allocate Functions::FN_DPS_ASC::F_DPS_ASC_04 to context.sts.orb.dps.asc;
        allocate Functions::FN_DPS_ASC::F_DPS_ASC_05 to context.sts.orb.dps.asc;
        allocate Functions::FN_DPS_ASC::F_DPS_ASC_06 to context.sts.orb.dps.asc;
        allocate Functions::FN_DPS_ASC::F_DPS_ASC_07 to context.sts.orb.dps.asc;
        allocate Functions::FN_DPS_ASC::F_DPS_ASC_08 to context.sts.orb.dps.asc;
        allocate Functions::FN_DPS_ASC::F_DPS_ASC_09 to context.sts.orb.dps.asc;
        allocate Functions::FN_DPS_ASC::F_DPS_ASC_10 to context.sts.orb.dps.asc;
        allocate Functions::FN_DPS_ASC::F_DPS_ASC_11 to context.sts.orb.dps.asc;
        allocate Functions::FN_DPS_ASC::F_DPS_ASC_12 to context.sts.orb.dps.asc;
        allocate Functions::FN_DPS_BUS::F_DPS_BUS_01 to context.sts.orb.dps.bus;
        allocate Functions::FN_DPS_BUS::F_DPS_BUS_02 to context.sts.orb.dps.bus;
        allocate Functions::FN_DPS_BUS::F_DPS_BUS_03 to context.sts.orb.dps.bus;
        allocate Functions::FN_DPS_BUS::F_DPS_BUS_04 to context.sts.orb.dps.bus;
        allocate Functions::FN_DPS_BUS::F_DPS_BUS_05 to context.sts.orb.dps.bus;
        allocate Functions::FN_DPS_BUS::F_DPS_BUS_06 to context.sts.orb.dps.bus;
        allocate Functions::FN_DPS_BUS::F_DPS_BUS_07 to context.sts.orb.dps.bus;
        allocate Functions::FN_DPS_BUS::F_DPS_BUS_08 to context.sts.orb.dps.bus;
        allocate Functions::FN_DPS_BUS::F_DPS_BUS_09 to context.sts.orb.dps.bus;
        allocate Functions::FN_DPS_BUS::F_DPS_BUS_10 to context.sts.orb.dps.bus;
        allocate Functions::FN_DPS_BUS::F_DPS_BUS_11 to context.sts.orb.dps.bus;
        allocate Functions::FN_DPS_BUS::F_DPS_BUS_12 to context.sts.orb.dps.bus;
        allocate Functions::FN_DPS_FSW::F_DPS_FSW_01 to context.sts.orb.dps.fsw;
        allocate Functions::FN_DPS_FSW::F_DPS_FSW_02 to context.sts.orb.dps.fsw;
        allocate Functions::FN_DPS_FSW::F_DPS_FSW_03 to context.sts.orb.dps.fsw;
        allocate Functions::FN_DPS_FSW::F_DPS_FSW_04 to context.sts.orb.dps.fsw;
        allocate Functions::FN_DPS_FSW::F_DPS_FSW_05 to context.sts.orb.dps.fsw;
        allocate Functions::FN_DPS_FSW::F_DPS_FSW_06 to context.sts.orb.dps.fsw;
        allocate Functions::FN_DPS_FSW::F_DPS_FSW_07 to context.sts.orb.dps.fsw;
        allocate Functions::FN_DPS_FSW::F_DPS_FSW_08 to context.sts.orb.dps.fsw;
        allocate Functions::FN_DPS_FSW::F_DPS_FSW_09 to context.sts.orb.dps.fsw;
        allocate Functions::FN_DPS_FSW::F_DPS_FSW_10 to context.sts.orb.dps.fsw;
        allocate Functions::FN_DPS_FSW::F_DPS_FSW_11 to context.sts.orb.dps.fsw;
        allocate Functions::FN_DPS_FSW::F_DPS_FSW_12 to context.sts.orb.dps.fsw;
        allocate Functions::FN_DPS_FSW::F_DPS_FSW_13 to context.sts.orb.dps.fsw;
        allocate Functions::FN_DPS_GPC::F_DPS_GPC_01 to context.sts.orb.dps.gpc;
        allocate Functions::FN_DPS_GPC::F_DPS_GPC_02 to context.sts.orb.dps.gpc;
        allocate Functions::FN_DPS_GPC::F_DPS_GPC_03 to context.sts.orb.dps.gpc;
        allocate Functions::FN_DPS_GPC::F_DPS_GPC_04 to context.sts.orb.dps.gpc;
        allocate Functions::FN_DPS_GPC::F_DPS_GPC_05 to context.sts.orb.dps.gpc;
        allocate Functions::FN_DPS_GPC::F_DPS_GPC_06 to context.sts.orb.dps.gpc;
        allocate Functions::FN_DPS_GPC::F_DPS_GPC_07 to context.sts.orb.dps.gpc;
        allocate Functions::FN_DPS_GPC::F_DPS_GPC_08 to context.sts.orb.dps.gpc;
        allocate Functions::FN_DPS_GPC::F_DPS_GPC_09 to context.sts.orb.dps.gpc;
        allocate Functions::FN_DPS_GPC::F_DPS_GPC_10 to context.sts.orb.dps.gpc;
        allocate Functions::FN_DPS_GPC::F_DPS_GPC_11 to context.sts.orb.dps.gpc;
        allocate Functions::FN_DPS_GPC::F_DPS_GPC_12 to context.sts.orb.dps.gpc;
        allocate Functions::FN_DPS_MEDS::F_DPS_MEDS_01 to context.sts.orb.dps.meds;
        allocate Functions::FN_DPS_MEDS::F_DPS_MEDS_02 to context.sts.orb.dps.meds;
        allocate Functions::FN_DPS_MEDS::F_DPS_MEDS_03 to context.sts.orb.dps.meds;
        allocate Functions::FN_DPS_MEDS::F_DPS_MEDS_04 to context.sts.orb.dps.meds;
        allocate Functions::FN_DPS_MEDS::F_DPS_MEDS_05 to context.sts.orb.dps.meds;
        allocate Functions::FN_DPS_MEDS::F_DPS_MEDS_06 to context.sts.orb.dps.meds;
        allocate Functions::FN_DPS_MEDS::F_DPS_MEDS_07 to context.sts.orb.dps.meds;
        allocate Functions::FN_DPS_MEDS::F_DPS_MEDS_08 to context.sts.orb.dps.meds;
        allocate Functions::FN_DPS_MEDS::F_DPS_MEDS_09 to context.sts.orb.dps.meds;
        allocate Functions::FN_DPS_MEDS::F_DPS_MEDS_10 to context.sts.orb.dps.meds;
        allocate Functions::FN_DPS_MEDS::F_DPS_MEDS_11 to context.sts.orb.dps.meds;
        allocate Functions::FN_DPS_MEDS::F_DPS_MEDS_12 to context.sts.orb.dps.meds;
        allocate Functions::FN_DPS_MTU::F_DPS_MTU_01 to context.sts.orb.dps.mtu;
        allocate Functions::FN_DPS_MTU::F_DPS_MTU_02 to context.sts.orb.dps.mtu;
        allocate Functions::FN_DPS_MTU::F_DPS_MTU_03 to context.sts.orb.dps.mtu;
        allocate Functions::FN_DPS_MTU::F_DPS_MTU_04 to context.sts.orb.dps.mtu;
        allocate Functions::FN_DPS_MTU::F_DPS_MTU_05 to context.sts.orb.dps.mtu;
        allocate Functions::FN_DPS_MTU::F_DPS_MTU_06 to context.sts.orb.dps.mtu;
        allocate Functions::FN_DPS_MTU::F_DPS_MTU_07 to context.sts.orb.dps.mtu;
        allocate Functions::FN_DPS_MTU::F_DPS_MTU_08 to context.sts.orb.dps.mtu;
        allocate Functions::FN_DPS_MTU::F_DPS_MTU_09 to context.sts.orb.dps.mtu;
        allocate Functions::FN_DPS_MTU::F_DPS_MTU_10 to context.sts.orb.dps.mtu;
        allocate Functions::FN_DPS_MTU::F_DPS_MTU_11 to context.sts.orb.dps.mtu;
        allocate Functions::FN_DPS_MTU::F_DPS_MTU_12 to context.sts.orb.dps.mtu;
        allocate Functions::FN_DPS_OPS::F_DPS_OPS_01 to context.sts.orb.dps.ops;
        allocate Functions::FN_DPS_OPS::F_DPS_OPS_02 to context.sts.orb.dps.ops;
        allocate Functions::FN_DPS_OPS::F_DPS_OPS_03 to context.sts.orb.dps.ops;
        allocate Functions::FN_DPS_OPS::F_DPS_OPS_04 to context.sts.orb.dps.ops;
        allocate Functions::FN_DPS_OPS::F_DPS_OPS_05 to context.sts.orb.dps.ops;
        allocate Functions::FN_DPS_OPS::F_DPS_OPS_06 to context.sts.orb.dps.ops;
        allocate Functions::FN_DPS_OPS::F_DPS_OPS_07 to context.sts.orb.dps.ops;
        allocate Functions::FN_DPS_OPS::F_DPS_OPS_08 to context.sts.orb.dps.ops;
        allocate Functions::FN_DPS_OPS::F_DPS_OPS_09 to context.sts.orb.dps.ops;
        allocate Functions::FN_DPS_OPS::F_DPS_OPS_10 to context.sts.orb.dps.ops;
        allocate Functions::FN_DPS_OPS::F_DPS_OPS_11 to context.sts.orb.dps.ops;
        allocate Functions::FN_DPS_OPS::F_DPS_OPS_12 to context.sts.orb.dps.ops;
        allocate Functions::FN_DPS_OPS::F_DPS_OPS_13 to context.sts.orb.dps.ops;
        allocate Functions::FN_ECLSS::F_ECLSS_01 to context.sts.orb.eclss;
        allocate Functions::FN_ECLSS::F_ECLSS_02 to context.sts.orb.eclss;
        allocate Functions::FN_ECLSS::F_ECLSS_03 to context.sts.orb.eclss;
        allocate Functions::FN_ECLSS::F_ECLSS_04 to context.sts.orb.eclss;
        allocate Functions::FN_ECLSS::F_ECLSS_05 to context.sts.orb.eclss;
        allocate Functions::FN_ECLSS::F_ECLSS_06 to context.sts.orb.eclss;
        allocate Functions::FN_ECL_ALS::F_ECL_ALS_01 to context.sts.orb.eclss.als;
        allocate Functions::FN_ECL_ALS::F_ECL_ALS_02 to context.sts.orb.eclss.als;
        allocate Functions::FN_ECL_ALS::F_ECL_ALS_03 to context.sts.orb.eclss.als;
        allocate Functions::FN_ECL_ALS::F_ECL_ALS_04 to context.sts.orb.eclss.als;
        allocate Functions::FN_ECL_ALS::F_ECL_ALS_05 to context.sts.orb.eclss.als;
        allocate Functions::FN_ECL_ALS::F_ECL_ALS_06 to context.sts.orb.eclss.als;
        allocate Functions::FN_ECL_ALS::F_ECL_ALS_07 to context.sts.orb.eclss.als;
        allocate Functions::FN_ECL_ALS::F_ECL_ALS_08 to context.sts.orb.eclss.als;
        allocate Functions::FN_ECL_ALS::F_ECL_ALS_09 to context.sts.orb.eclss.als;
        allocate Functions::FN_ECL_ALS::F_ECL_ALS_10 to context.sts.orb.eclss.als;
        allocate Functions::FN_ECL_ALS::F_ECL_ALS_11 to context.sts.orb.eclss.als;
        allocate Functions::FN_ECL_ALS_DEP::F_ECL_ALS_DEP_01 to context.sts.orb.eclss.als.dep;
        allocate Functions::FN_ECL_ALS_DEP::F_ECL_ALS_DEP_02 to context.sts.orb.eclss.als.dep;
        allocate Functions::FN_ECL_ALS_DEP::F_ECL_ALS_DEP_03 to context.sts.orb.eclss.als.dep;
        allocate Functions::FN_ECL_ALS_DEP::F_ECL_ALS_DEP_04 to context.sts.orb.eclss.als.dep;
        allocate Functions::FN_ECL_ALS_DEP::F_ECL_ALS_DEP_05 to context.sts.orb.eclss.als.dep;
        allocate Functions::FN_ECL_ALS_DEP::F_ECL_ALS_DEP_06 to context.sts.orb.eclss.als.dep;
        allocate Functions::FN_ECL_ALS_DEP::F_ECL_ALS_DEP_07 to context.sts.orb.eclss.als.dep;
        allocate Functions::FN_ECL_ALS_DEP::F_ECL_ALS_DEP_08 to context.sts.orb.eclss.als.dep;
        allocate Functions::FN_ECL_ALS_DEP::F_ECL_ALS_DEP_09 to context.sts.orb.eclss.als.dep;
        allocate Functions::FN_ECL_ALS_DEP::F_ECL_ALS_DEP_10 to context.sts.orb.eclss.als.dep;
        allocate Functions::FN_ECL_ALS_DEP::F_ECL_ALS_DEP_11 to context.sts.orb.eclss.als.dep;
        allocate Functions::FN_ECL_ALS_DEP::F_ECL_ALS_DEP_12 to context.sts.orb.eclss.als.dep;
        allocate Functions::FN_ECL_ALS_HTR::F_ECL_ALS_HTR_01 to context.sts.orb.eclss.als.htr;
        allocate Functions::FN_ECL_ALS_HTR::F_ECL_ALS_HTR_02 to context.sts.orb.eclss.als.htr;
        allocate Functions::FN_ECL_ALS_HTR::F_ECL_ALS_HTR_03 to context.sts.orb.eclss.als.htr;
        allocate Functions::FN_ECL_ALS_HTR::F_ECL_ALS_HTR_04 to context.sts.orb.eclss.als.htr;
        allocate Functions::FN_ECL_ALS_HTR::F_ECL_ALS_HTR_05 to context.sts.orb.eclss.als.htr;
        allocate Functions::FN_ECL_ALS_HTR::F_ECL_ALS_HTR_06 to context.sts.orb.eclss.als.htr;
        allocate Functions::FN_ECL_ALS_HTR::F_ECL_ALS_HTR_07 to context.sts.orb.eclss.als.htr;
        allocate Functions::FN_ECL_ALS_HTR::F_ECL_ALS_HTR_08 to context.sts.orb.eclss.als.htr;
        allocate Functions::FN_ECL_ALS_HTR::F_ECL_ALS_HTR_09 to context.sts.orb.eclss.als.htr;
        allocate Functions::FN_ECL_ALS_HTR::F_ECL_ALS_HTR_10 to context.sts.orb.eclss.als.htr;
        allocate Functions::FN_ECL_ALS_HTR::F_ECL_ALS_HTR_11 to context.sts.orb.eclss.als.htr;
        allocate Functions::FN_ECL_ALS_HTR::F_ECL_ALS_HTR_12 to context.sts.orb.eclss.als.htr;
        allocate Functions::FN_ECL_ALS_LCG::F_ECL_ALS_LCG_01 to context.sts.orb.eclss.als.lcg;
        allocate Functions::FN_ECL_ALS_LCG::F_ECL_ALS_LCG_02 to context.sts.orb.eclss.als.lcg;
        allocate Functions::FN_ECL_ALS_LCG::F_ECL_ALS_LCG_03 to context.sts.orb.eclss.als.lcg;
        allocate Functions::FN_ECL_ALS_LCG::F_ECL_ALS_LCG_04 to context.sts.orb.eclss.als.lcg;
        allocate Functions::FN_ECL_ALS_LCG::F_ECL_ALS_LCG_05 to context.sts.orb.eclss.als.lcg;
        allocate Functions::FN_ECL_ALS_LCG::F_ECL_ALS_LCG_06 to context.sts.orb.eclss.als.lcg;
        allocate Functions::FN_ECL_ALS_LCG::F_ECL_ALS_LCG_07 to context.sts.orb.eclss.als.lcg;
        allocate Functions::FN_ECL_ALS_LCG::F_ECL_ALS_LCG_08 to context.sts.orb.eclss.als.lcg;
        allocate Functions::FN_ECL_ALS_LCG::F_ECL_ALS_LCG_09 to context.sts.orb.eclss.als.lcg;
        allocate Functions::FN_ECL_ALS_LCG::F_ECL_ALS_LCG_10 to context.sts.orb.eclss.als.lcg;
        allocate Functions::FN_ECL_ALS_LCG::F_ECL_ALS_LCG_11 to context.sts.orb.eclss.als.lcg;
        allocate Functions::FN_ECL_ALS_MON::F_ECL_ALS_MON_01 to context.sts.orb.eclss.als.mon;
        allocate Functions::FN_ECL_ALS_MON::F_ECL_ALS_MON_02 to context.sts.orb.eclss.als.mon;
        allocate Functions::FN_ECL_ALS_MON::F_ECL_ALS_MON_03 to context.sts.orb.eclss.als.mon;
        allocate Functions::FN_ECL_ALS_MON::F_ECL_ALS_MON_04 to context.sts.orb.eclss.als.mon;
        allocate Functions::FN_ECL_ALS_MON::F_ECL_ALS_MON_05 to context.sts.orb.eclss.als.mon;
        allocate Functions::FN_ECL_ALS_MON::F_ECL_ALS_MON_06 to context.sts.orb.eclss.als.mon;
        allocate Functions::FN_ECL_ALS_MON::F_ECL_ALS_MON_07 to context.sts.orb.eclss.als.mon;
        allocate Functions::FN_ECL_ALS_MON::F_ECL_ALS_MON_08 to context.sts.orb.eclss.als.mon;
        allocate Functions::FN_ECL_ALS_MON::F_ECL_ALS_MON_09 to context.sts.orb.eclss.als.mon;
        allocate Functions::FN_ECL_ALS_MON::F_ECL_ALS_MON_10 to context.sts.orb.eclss.als.mon;
        allocate Functions::FN_ECL_ALS_MON::F_ECL_ALS_MON_11 to context.sts.orb.eclss.als.mon;
        allocate Functions::FN_ECL_ALS_MON::F_ECL_ALS_MON_12 to context.sts.orb.eclss.als.mon;
        allocate Functions::FN_ECL_ALS_SCU::F_ECL_ALS_SCU_01 to context.sts.orb.eclss.als.scu;
        allocate Functions::FN_ECL_ALS_SCU::F_ECL_ALS_SCU_02 to context.sts.orb.eclss.als.scu;
        allocate Functions::FN_ECL_ALS_SCU::F_ECL_ALS_SCU_03 to context.sts.orb.eclss.als.scu;
        allocate Functions::FN_ECL_ALS_SCU::F_ECL_ALS_SCU_04 to context.sts.orb.eclss.als.scu;
        allocate Functions::FN_ECL_ALS_SCU::F_ECL_ALS_SCU_05 to context.sts.orb.eclss.als.scu;
        allocate Functions::FN_ECL_ALS_SCU::F_ECL_ALS_SCU_06 to context.sts.orb.eclss.als.scu;
        allocate Functions::FN_ECL_ALS_SCU::F_ECL_ALS_SCU_07 to context.sts.orb.eclss.als.scu;
        allocate Functions::FN_ECL_ALS_SCU::F_ECL_ALS_SCU_08 to context.sts.orb.eclss.als.scu;
        allocate Functions::FN_ECL_ALS_SCU::F_ECL_ALS_SCU_09 to context.sts.orb.eclss.als.scu;
        allocate Functions::FN_ECL_ALS_SCU::F_ECL_ALS_SCU_10 to context.sts.orb.eclss.als.scu;
        allocate Functions::FN_ECL_ALS_SCU::F_ECL_ALS_SCU_11 to context.sts.orb.eclss.als.scu;
        allocate Functions::FN_ECL_ALS_SCU::F_ECL_ALS_SCU_12 to context.sts.orb.eclss.als.scu;
        allocate Functions::FN_ECL_ALS_VNT::F_ECL_ALS_VNT_01 to context.sts.orb.eclss.als.vnt;
        allocate Functions::FN_ECL_ALS_VNT::F_ECL_ALS_VNT_02 to context.sts.orb.eclss.als.vnt;
        allocate Functions::FN_ECL_ALS_VNT::F_ECL_ALS_VNT_03 to context.sts.orb.eclss.als.vnt;
        allocate Functions::FN_ECL_ALS_VNT::F_ECL_ALS_VNT_04 to context.sts.orb.eclss.als.vnt;
        allocate Functions::FN_ECL_ALS_VNT::F_ECL_ALS_VNT_05 to context.sts.orb.eclss.als.vnt;
        allocate Functions::FN_ECL_ALS_VNT::F_ECL_ALS_VNT_06 to context.sts.orb.eclss.als.vnt;
        allocate Functions::FN_ECL_ALS_VNT::F_ECL_ALS_VNT_07 to context.sts.orb.eclss.als.vnt;
        allocate Functions::FN_ECL_ALS_VNT::F_ECL_ALS_VNT_08 to context.sts.orb.eclss.als.vnt;
        allocate Functions::FN_ECL_ALS_VNT::F_ECL_ALS_VNT_09 to context.sts.orb.eclss.als.vnt;
        allocate Functions::FN_ECL_ALS_VNT::F_ECL_ALS_VNT_10 to context.sts.orb.eclss.als.vnt;
        allocate Functions::FN_ECL_ALS_VNT::F_ECL_ALS_VNT_11 to context.sts.orb.eclss.als.vnt;
        allocate Functions::FN_ECL_ALS_VNT::F_ECL_ALS_VNT_12 to context.sts.orb.eclss.als.vnt;
        allocate Functions::FN_ECL_ARS::F_ECL_ARS_01 to context.sts.orb.eclss.ars;
        allocate Functions::FN_ECL_ARS::F_ECL_ARS_02 to context.sts.orb.eclss.ars;
        allocate Functions::FN_ECL_ARS::F_ECL_ARS_03 to context.sts.orb.eclss.ars;
        allocate Functions::FN_ECL_ARS::F_ECL_ARS_04 to context.sts.orb.eclss.ars;
        allocate Functions::FN_ECL_ARS::F_ECL_ARS_05 to context.sts.orb.eclss.ars;
        allocate Functions::FN_ECL_ARS::F_ECL_ARS_06 to context.sts.orb.eclss.ars;
        allocate Functions::FN_ECL_ARS::F_ECL_ARS_07 to context.sts.orb.eclss.ars;
        allocate Functions::FN_ECL_ARS::F_ECL_ARS_08 to context.sts.orb.eclss.ars;
        allocate Functions::FN_ECL_ARS::F_ECL_ARS_09 to context.sts.orb.eclss.ars;
        allocate Functions::FN_ARS_AVB::F_ARS_AVB_01 to context.sts.orb.eclss.ars.avb;
        allocate Functions::FN_ARS_AVB::F_ARS_AVB_02 to context.sts.orb.eclss.ars.avb;
        allocate Functions::FN_ARS_AVB::F_ARS_AVB_03 to context.sts.orb.eclss.ars.avb;
        allocate Functions::FN_ARS_AVB::F_ARS_AVB_04 to context.sts.orb.eclss.ars.avb;
        allocate Functions::FN_ARS_AVB::F_ARS_AVB_05 to context.sts.orb.eclss.ars.avb;
        allocate Functions::FN_ARS_AVB::F_ARS_AVB_06 to context.sts.orb.eclss.ars.avb;
        allocate Functions::FN_ARS_AVB::F_ARS_AVB_07 to context.sts.orb.eclss.ars.avb;
        allocate Functions::FN_ARS_AVB::F_ARS_AVB_08 to context.sts.orb.eclss.ars.avb;
        allocate Functions::FN_ARS_AVB::F_ARS_AVB_09 to context.sts.orb.eclss.ars.avb;
        allocate Functions::FN_ARS_AVB::F_ARS_AVB_10 to context.sts.orb.eclss.ars.avb;
        allocate Functions::FN_ARS_AVB::F_ARS_AVB_11 to context.sts.orb.eclss.ars.avb;
        allocate Functions::FN_ARS_AVB::F_ARS_AVB_12 to context.sts.orb.eclss.ars.avb;
        allocate Functions::FN_ARS_AVB_CIR::F_ARS_AVB_CIR_01 to context.sts.orb.eclss.ars.avb.cir;
        allocate Functions::FN_ARS_AVB_CIR::F_ARS_AVB_CIR_02 to context.sts.orb.eclss.ars.avb.cir;
        allocate Functions::FN_ARS_AVB_CIR::F_ARS_AVB_CIR_03 to context.sts.orb.eclss.ars.avb.cir;
        allocate Functions::FN_ARS_AVB_CIR::F_ARS_AVB_CIR_04 to context.sts.orb.eclss.ars.avb.cir;
        allocate Functions::FN_ARS_AVB_CIR::F_ARS_AVB_CIR_05 to context.sts.orb.eclss.ars.avb.cir;
        allocate Functions::FN_ARS_AVB_CIR::F_ARS_AVB_CIR_06 to context.sts.orb.eclss.ars.avb.cir;
        allocate Functions::FN_ARS_AVB_CIR::F_ARS_AVB_CIR_07 to context.sts.orb.eclss.ars.avb.cir;
        allocate Functions::FN_ARS_AVB_CIR::F_ARS_AVB_CIR_08 to context.sts.orb.eclss.ars.avb.cir;
        allocate Functions::FN_ARS_AVB_CIR::F_ARS_AVB_CIR_09 to context.sts.orb.eclss.ars.avb.cir;
        allocate Functions::FN_ARS_AVB_CIR::F_ARS_AVB_CIR_10 to context.sts.orb.eclss.ars.avb.cir;
        allocate Functions::FN_ARS_AVB_CIR::F_ARS_AVB_CIR_11 to context.sts.orb.eclss.ars.avb.cir;
        allocate Functions::FN_ARS_AVB_FAN::F_ARS_AVB_FAN_01 to context.sts.orb.eclss.ars.avb.fan;
        allocate Functions::FN_ARS_AVB_FAN::F_ARS_AVB_FAN_02 to context.sts.orb.eclss.ars.avb.fan;
        allocate Functions::FN_ARS_AVB_FAN::F_ARS_AVB_FAN_03 to context.sts.orb.eclss.ars.avb.fan;
        allocate Functions::FN_ARS_AVB_FAN::F_ARS_AVB_FAN_04 to context.sts.orb.eclss.ars.avb.fan;
        allocate Functions::FN_ARS_AVB_FAN::F_ARS_AVB_FAN_05 to context.sts.orb.eclss.ars.avb.fan;
        allocate Functions::FN_ARS_AVB_FAN::F_ARS_AVB_FAN_06 to context.sts.orb.eclss.ars.avb.fan;
        allocate Functions::FN_ARS_AVB_FAN::F_ARS_AVB_FAN_07 to context.sts.orb.eclss.ars.avb.fan;
        allocate Functions::FN_ARS_AVB_FAN::F_ARS_AVB_FAN_08 to context.sts.orb.eclss.ars.avb.fan;
        allocate Functions::FN_ARS_AVB_FAN::F_ARS_AVB_FAN_09 to context.sts.orb.eclss.ars.avb.fan;
        allocate Functions::FN_ARS_AVB_FAN::F_ARS_AVB_FAN_10 to context.sts.orb.eclss.ars.avb.fan;
        allocate Functions::FN_ARS_AVB_FAN::F_ARS_AVB_FAN_11 to context.sts.orb.eclss.ars.avb.fan;
        allocate Functions::FN_ARS_AVB_FAN::F_ARS_AVB_FAN_12 to context.sts.orb.eclss.ars.avb.fan;
        allocate Functions::FN_ARS_AVB_HX::F_ARS_AVB_HX_01 to context.sts.orb.eclss.ars.avb.hx;
        allocate Functions::FN_ARS_AVB_HX::F_ARS_AVB_HX_02 to context.sts.orb.eclss.ars.avb.hx;
        allocate Functions::FN_ARS_AVB_HX::F_ARS_AVB_HX_03 to context.sts.orb.eclss.ars.avb.hx;
        allocate Functions::FN_ARS_AVB_HX::F_ARS_AVB_HX_04 to context.sts.orb.eclss.ars.avb.hx;
        allocate Functions::FN_ARS_AVB_HX::F_ARS_AVB_HX_05 to context.sts.orb.eclss.ars.avb.hx;
        allocate Functions::FN_ARS_AVB_HX::F_ARS_AVB_HX_06 to context.sts.orb.eclss.ars.avb.hx;
        allocate Functions::FN_ARS_AVB_HX::F_ARS_AVB_HX_07 to context.sts.orb.eclss.ars.avb.hx;
        allocate Functions::FN_ARS_AVB_HX::F_ARS_AVB_HX_08 to context.sts.orb.eclss.ars.avb.hx;
        allocate Functions::FN_ARS_AVB_HX::F_ARS_AVB_HX_09 to context.sts.orb.eclss.ars.avb.hx;
        allocate Functions::FN_ARS_AVB_HX::F_ARS_AVB_HX_10 to context.sts.orb.eclss.ars.avb.hx;
        allocate Functions::FN_ARS_AVB_MON::F_ARS_AVB_MON_01 to context.sts.orb.eclss.ars.avb.mon;
        allocate Functions::FN_ARS_AVB_MON::F_ARS_AVB_MON_02 to context.sts.orb.eclss.ars.avb.mon;
        allocate Functions::FN_ARS_AVB_MON::F_ARS_AVB_MON_03 to context.sts.orb.eclss.ars.avb.mon;
        allocate Functions::FN_ARS_AVB_MON::F_ARS_AVB_MON_04 to context.sts.orb.eclss.ars.avb.mon;
        allocate Functions::FN_ARS_AVB_MON::F_ARS_AVB_MON_05 to context.sts.orb.eclss.ars.avb.mon;
        allocate Functions::FN_ARS_AVB_MON::F_ARS_AVB_MON_06 to context.sts.orb.eclss.ars.avb.mon;
        allocate Functions::FN_ARS_AVB_MON::F_ARS_AVB_MON_07 to context.sts.orb.eclss.ars.avb.mon;
        allocate Functions::FN_ARS_AVB_MON::F_ARS_AVB_MON_08 to context.sts.orb.eclss.ars.avb.mon;
        allocate Functions::FN_ARS_AVB_MON::F_ARS_AVB_MON_09 to context.sts.orb.eclss.ars.avb.mon;
        allocate Functions::FN_ARS_AVB_MON::F_ARS_AVB_MON_10 to context.sts.orb.eclss.ars.avb.mon;
        allocate Functions::FN_ARS_AVB_MON::F_ARS_AVB_MON_11 to context.sts.orb.eclss.ars.avb.mon;
        allocate Functions::FN_ARS_AVB_MON::F_ARS_AVB_MON_12 to context.sts.orb.eclss.ars.avb.mon;
        allocate Functions::FN_ARS_AVB_OPS::F_ARS_AVB_OPS_01 to context.sts.orb.eclss.ars.avb.ops;
        allocate Functions::FN_ARS_AVB_OPS::F_ARS_AVB_OPS_02 to context.sts.orb.eclss.ars.avb.ops;
        allocate Functions::FN_ARS_AVB_OPS::F_ARS_AVB_OPS_03 to context.sts.orb.eclss.ars.avb.ops;
        allocate Functions::FN_ARS_AVB_OPS::F_ARS_AVB_OPS_04 to context.sts.orb.eclss.ars.avb.ops;
        allocate Functions::FN_ARS_AVB_OPS::F_ARS_AVB_OPS_05 to context.sts.orb.eclss.ars.avb.ops;
        allocate Functions::FN_ARS_AVB_OPS::F_ARS_AVB_OPS_06 to context.sts.orb.eclss.ars.avb.ops;
        allocate Functions::FN_ARS_AVB_OPS::F_ARS_AVB_OPS_07 to context.sts.orb.eclss.ars.avb.ops;
        allocate Functions::FN_ARS_AVB_OPS::F_ARS_AVB_OPS_08 to context.sts.orb.eclss.ars.avb.ops;
        allocate Functions::FN_ARS_AVB_OPS::F_ARS_AVB_OPS_09 to context.sts.orb.eclss.ars.avb.ops;
        allocate Functions::FN_ARS_AVB_OPS::F_ARS_AVB_OPS_10 to context.sts.orb.eclss.ars.avb.ops;
        allocate Functions::FN_ARS_AVB_OPS::F_ARS_AVB_OPS_11 to context.sts.orb.eclss.ars.avb.ops;
        allocate Functions::FN_ARS_AVB_OPS::F_ARS_AVB_OPS_12 to context.sts.orb.eclss.ars.avb.ops;
        allocate Functions::FN_ARS_CAC::F_ARS_CAC_01 to context.sts.orb.eclss.ars.cac;
        allocate Functions::FN_ARS_CAC::F_ARS_CAC_02 to context.sts.orb.eclss.ars.cac;
        allocate Functions::FN_ARS_CAC::F_ARS_CAC_03 to context.sts.orb.eclss.ars.cac;
        allocate Functions::FN_ARS_CAC::F_ARS_CAC_04 to context.sts.orb.eclss.ars.cac;
        allocate Functions::FN_ARS_CAC::F_ARS_CAC_05 to context.sts.orb.eclss.ars.cac;
        allocate Functions::FN_ARS_CAC::F_ARS_CAC_06 to context.sts.orb.eclss.ars.cac;
        allocate Functions::FN_ARS_CAC::F_ARS_CAC_07 to context.sts.orb.eclss.ars.cac;
        allocate Functions::FN_ARS_CAC::F_ARS_CAC_08 to context.sts.orb.eclss.ars.cac;
        allocate Functions::FN_ARS_CAC::F_ARS_CAC_09 to context.sts.orb.eclss.ars.cac;
        allocate Functions::FN_ARS_CAC::F_ARS_CAC_10 to context.sts.orb.eclss.ars.cac;
        allocate Functions::FN_ARS_CAC::F_ARS_CAC_11 to context.sts.orb.eclss.ars.cac;
        allocate Functions::FN_CAC_DCT::F_CAC_DCT_01 to context.sts.orb.eclss.ars.cac.dct;
        allocate Functions::FN_CAC_DCT::F_CAC_DCT_02 to context.sts.orb.eclss.ars.cac.dct;
        allocate Functions::FN_CAC_DCT::F_CAC_DCT_03 to context.sts.orb.eclss.ars.cac.dct;
        allocate Functions::FN_CAC_DCT::F_CAC_DCT_04 to context.sts.orb.eclss.ars.cac.dct;
        allocate Functions::FN_CAC_DCT::F_CAC_DCT_05 to context.sts.orb.eclss.ars.cac.dct;
        allocate Functions::FN_CAC_DCT::F_CAC_DCT_06 to context.sts.orb.eclss.ars.cac.dct;
        allocate Functions::FN_CAC_DCT::F_CAC_DCT_07 to context.sts.orb.eclss.ars.cac.dct;
        allocate Functions::FN_CAC_DCT::F_CAC_DCT_08 to context.sts.orb.eclss.ars.cac.dct;
        allocate Functions::FN_CAC_DCT::F_CAC_DCT_09 to context.sts.orb.eclss.ars.cac.dct;
        allocate Functions::FN_CAC_DCT::F_CAC_DCT_10 to context.sts.orb.eclss.ars.cac.dct;
        allocate Functions::FN_CAC_DCT::F_CAC_DCT_11 to context.sts.orb.eclss.ars.cac.dct;
        allocate Functions::FN_CAC_FAN::F_CAC_FAN_01 to context.sts.orb.eclss.ars.cac.fan;
        allocate Functions::FN_CAC_FAN::F_CAC_FAN_02 to context.sts.orb.eclss.ars.cac.fan;
        allocate Functions::FN_CAC_FAN::F_CAC_FAN_03 to context.sts.orb.eclss.ars.cac.fan;
        allocate Functions::FN_CAC_FAN::F_CAC_FAN_04 to context.sts.orb.eclss.ars.cac.fan;
        allocate Functions::FN_CAC_FAN::F_CAC_FAN_05 to context.sts.orb.eclss.ars.cac.fan;
        allocate Functions::FN_CAC_FAN::F_CAC_FAN_06 to context.sts.orb.eclss.ars.cac.fan;
        allocate Functions::FN_CAC_FAN::F_CAC_FAN_07 to context.sts.orb.eclss.ars.cac.fan;
        allocate Functions::FN_CAC_FAN::F_CAC_FAN_08 to context.sts.orb.eclss.ars.cac.fan;
        allocate Functions::FN_CAC_FAN::F_CAC_FAN_09 to context.sts.orb.eclss.ars.cac.fan;
        allocate Functions::FN_CAC_FAN::F_CAC_FAN_10 to context.sts.orb.eclss.ars.cac.fan;
        allocate Functions::FN_CAC_MON::F_CAC_MON_01 to context.sts.orb.eclss.ars.cac.mon;
        allocate Functions::FN_CAC_MON::F_CAC_MON_02 to context.sts.orb.eclss.ars.cac.mon;
        allocate Functions::FN_CAC_MON::F_CAC_MON_03 to context.sts.orb.eclss.ars.cac.mon;
        allocate Functions::FN_CAC_MON::F_CAC_MON_04 to context.sts.orb.eclss.ars.cac.mon;
        allocate Functions::FN_CAC_MON::F_CAC_MON_05 to context.sts.orb.eclss.ars.cac.mon;
        allocate Functions::FN_CAC_MON::F_CAC_MON_06 to context.sts.orb.eclss.ars.cac.mon;
        allocate Functions::FN_CAC_MON::F_CAC_MON_07 to context.sts.orb.eclss.ars.cac.mon;
        allocate Functions::FN_CAC_MON::F_CAC_MON_08 to context.sts.orb.eclss.ars.cac.mon;
        allocate Functions::FN_CAC_MON::F_CAC_MON_09 to context.sts.orb.eclss.ars.cac.mon;
        allocate Functions::FN_CAC_MON::F_CAC_MON_10 to context.sts.orb.eclss.ars.cac.mon;
        allocate Functions::FN_CAC_MON::F_CAC_MON_11 to context.sts.orb.eclss.ars.cac.mon;
        allocate Functions::FN_CAC_MON::F_CAC_MON_12 to context.sts.orb.eclss.ars.cac.mon;
        allocate Functions::FN_CAC_OPS::F_CAC_OPS_01 to context.sts.orb.eclss.ars.cac.ops;
        allocate Functions::FN_CAC_OPS::F_CAC_OPS_02 to context.sts.orb.eclss.ars.cac.ops;
        allocate Functions::FN_CAC_OPS::F_CAC_OPS_03 to context.sts.orb.eclss.ars.cac.ops;
        allocate Functions::FN_CAC_OPS::F_CAC_OPS_04 to context.sts.orb.eclss.ars.cac.ops;
        allocate Functions::FN_CAC_OPS::F_CAC_OPS_05 to context.sts.orb.eclss.ars.cac.ops;
        allocate Functions::FN_CAC_OPS::F_CAC_OPS_06 to context.sts.orb.eclss.ars.cac.ops;
        allocate Functions::FN_CAC_OPS::F_CAC_OPS_07 to context.sts.orb.eclss.ars.cac.ops;
        allocate Functions::FN_CAC_OPS::F_CAC_OPS_08 to context.sts.orb.eclss.ars.cac.ops;
        allocate Functions::FN_CAC_OPS::F_CAC_OPS_09 to context.sts.orb.eclss.ars.cac.ops;
        allocate Functions::FN_CAC_OPS::F_CAC_OPS_10 to context.sts.orb.eclss.ars.cac.ops;
        allocate Functions::FN_CAC_OPS::F_CAC_OPS_11 to context.sts.orb.eclss.ars.cac.ops;
        allocate Functions::FN_CAC_OPS::F_CAC_OPS_12 to context.sts.orb.eclss.ars.cac.ops;
        allocate Functions::FN_CAC_RTN::F_CAC_RTN_01 to context.sts.orb.eclss.ars.cac.rtn;
        allocate Functions::FN_CAC_RTN::F_CAC_RTN_02 to context.sts.orb.eclss.ars.cac.rtn;
        allocate Functions::FN_CAC_RTN::F_CAC_RTN_03 to context.sts.orb.eclss.ars.cac.rtn;
        allocate Functions::FN_CAC_RTN::F_CAC_RTN_04 to context.sts.orb.eclss.ars.cac.rtn;
        allocate Functions::FN_CAC_RTN::F_CAC_RTN_05 to context.sts.orb.eclss.ars.cac.rtn;
        allocate Functions::FN_CAC_RTN::F_CAC_RTN_06 to context.sts.orb.eclss.ars.cac.rtn;
        allocate Functions::FN_CAC_RTN::F_CAC_RTN_07 to context.sts.orb.eclss.ars.cac.rtn;
        allocate Functions::FN_CAC_RTN::F_CAC_RTN_08 to context.sts.orb.eclss.ars.cac.rtn;
        allocate Functions::FN_CAC_RTN::F_CAC_RTN_09 to context.sts.orb.eclss.ars.cac.rtn;
        allocate Functions::FN_CAC_RTN::F_CAC_RTN_10 to context.sts.orb.eclss.ars.cac.rtn;
        allocate Functions::FN_CAC_RTN::F_CAC_RTN_11 to context.sts.orb.eclss.ars.cac.rtn;
        allocate Functions::FN_CAC_RTN::F_CAC_RTN_12 to context.sts.orb.eclss.ars.cac.rtn;
        allocate Functions::FN_ARS_CO2::F_ARS_CO2_01 to context.sts.orb.eclss.ars.co2;
        allocate Functions::FN_ARS_CO2::F_ARS_CO2_02 to context.sts.orb.eclss.ars.co2;
        allocate Functions::FN_ARS_CO2::F_ARS_CO2_03 to context.sts.orb.eclss.ars.co2;
        allocate Functions::FN_ARS_CO2::F_ARS_CO2_04 to context.sts.orb.eclss.ars.co2;
        allocate Functions::FN_ARS_CO2::F_ARS_CO2_05 to context.sts.orb.eclss.ars.co2;
        allocate Functions::FN_ARS_CO2::F_ARS_CO2_06 to context.sts.orb.eclss.ars.co2;
        allocate Functions::FN_ARS_CO2::F_ARS_CO2_07 to context.sts.orb.eclss.ars.co2;
        allocate Functions::FN_ARS_CO2::F_ARS_CO2_08 to context.sts.orb.eclss.ars.co2;
        allocate Functions::FN_ARS_CO2::F_ARS_CO2_09 to context.sts.orb.eclss.ars.co2;
        allocate Functions::FN_ARS_CO2::F_ARS_CO2_10 to context.sts.orb.eclss.ars.co2;
        allocate Functions::FN_ARS_CO2::F_ARS_CO2_11 to context.sts.orb.eclss.ars.co2;
        allocate Functions::FN_CO2_ABS::F_CO2_ABS_01 to context.sts.orb.eclss.ars.co2.abs;
        allocate Functions::FN_CO2_ABS::F_CO2_ABS_02 to context.sts.orb.eclss.ars.co2.abs;
        allocate Functions::FN_CO2_ABS::F_CO2_ABS_03 to context.sts.orb.eclss.ars.co2.abs;
        allocate Functions::FN_CO2_ABS::F_CO2_ABS_04 to context.sts.orb.eclss.ars.co2.abs;
        allocate Functions::FN_CO2_ABS::F_CO2_ABS_05 to context.sts.orb.eclss.ars.co2.abs;
        allocate Functions::FN_CO2_ABS::F_CO2_ABS_06 to context.sts.orb.eclss.ars.co2.abs;
        allocate Functions::FN_CO2_ABS::F_CO2_ABS_07 to context.sts.orb.eclss.ars.co2.abs;
        allocate Functions::FN_CO2_ABS::F_CO2_ABS_08 to context.sts.orb.eclss.ars.co2.abs;
        allocate Functions::FN_CO2_ATCO::F_CO2_ATCO_01 to context.sts.orb.eclss.ars.co2.atco;
        allocate Functions::FN_CO2_ATCO::F_CO2_ATCO_02 to context.sts.orb.eclss.ars.co2.atco;
        allocate Functions::FN_CO2_ATCO::F_CO2_ATCO_03 to context.sts.orb.eclss.ars.co2.atco;
        allocate Functions::FN_CO2_ATCO::F_CO2_ATCO_04 to context.sts.orb.eclss.ars.co2.atco;
        allocate Functions::FN_CO2_ATCO::F_CO2_ATCO_05 to context.sts.orb.eclss.ars.co2.atco;
        allocate Functions::FN_CO2_ATCO::F_CO2_ATCO_06 to context.sts.orb.eclss.ars.co2.atco;
        allocate Functions::FN_CO2_ATCO::F_CO2_ATCO_07 to context.sts.orb.eclss.ars.co2.atco;
        allocate Functions::FN_CO2_ATCO::F_CO2_ATCO_08 to context.sts.orb.eclss.ars.co2.atco;
        allocate Functions::FN_CO2_ATCO::F_CO2_ATCO_09 to context.sts.orb.eclss.ars.co2.atco;
        allocate Functions::FN_CO2_ATCO::F_CO2_ATCO_10 to context.sts.orb.eclss.ars.co2.atco;
        allocate Functions::FN_CO2_CAN::F_CO2_CAN_01 to context.sts.orb.eclss.ars.co2.can;
        allocate Functions::FN_CO2_CAN::F_CO2_CAN_02 to context.sts.orb.eclss.ars.co2.can;
        allocate Functions::FN_CO2_CAN::F_CO2_CAN_03 to context.sts.orb.eclss.ars.co2.can;
        allocate Functions::FN_CO2_CAN::F_CO2_CAN_04 to context.sts.orb.eclss.ars.co2.can;
        allocate Functions::FN_CO2_CAN::F_CO2_CAN_05 to context.sts.orb.eclss.ars.co2.can;
        allocate Functions::FN_CO2_CAN::F_CO2_CAN_06 to context.sts.orb.eclss.ars.co2.can;
        allocate Functions::FN_CO2_CAN::F_CO2_CAN_07 to context.sts.orb.eclss.ars.co2.can;
        allocate Functions::FN_CO2_CAN::F_CO2_CAN_08 to context.sts.orb.eclss.ars.co2.can;
        allocate Functions::FN_CO2_CAN::F_CO2_CAN_09 to context.sts.orb.eclss.ars.co2.can;
        allocate Functions::FN_CO2_CAN::F_CO2_CAN_10 to context.sts.orb.eclss.ars.co2.can;
        allocate Functions::FN_CO2_CAN::F_CO2_CAN_11 to context.sts.orb.eclss.ars.co2.can;
        allocate Functions::FN_CO2_CAN::F_CO2_CAN_12 to context.sts.orb.eclss.ars.co2.can;
        allocate Functions::FN_CO2_MON::F_CO2_MON_01 to context.sts.orb.eclss.ars.co2.mon;
        allocate Functions::FN_CO2_MON::F_CO2_MON_02 to context.sts.orb.eclss.ars.co2.mon;
        allocate Functions::FN_CO2_MON::F_CO2_MON_03 to context.sts.orb.eclss.ars.co2.mon;
        allocate Functions::FN_CO2_MON::F_CO2_MON_04 to context.sts.orb.eclss.ars.co2.mon;
        allocate Functions::FN_CO2_MON::F_CO2_MON_05 to context.sts.orb.eclss.ars.co2.mon;
        allocate Functions::FN_CO2_MON::F_CO2_MON_06 to context.sts.orb.eclss.ars.co2.mon;
        allocate Functions::FN_CO2_MON::F_CO2_MON_07 to context.sts.orb.eclss.ars.co2.mon;
        allocate Functions::FN_CO2_MON::F_CO2_MON_08 to context.sts.orb.eclss.ars.co2.mon;
        allocate Functions::FN_CO2_MON::F_CO2_MON_09 to context.sts.orb.eclss.ars.co2.mon;
        allocate Functions::FN_CO2_MON::F_CO2_MON_10 to context.sts.orb.eclss.ars.co2.mon;
        allocate Functions::FN_CO2_MON::F_CO2_MON_11 to context.sts.orb.eclss.ars.co2.mon;
        allocate Functions::FN_CO2_MON::F_CO2_MON_12 to context.sts.orb.eclss.ars.co2.mon;
        allocate Functions::FN_CO2_STW::F_CO2_STW_01 to context.sts.orb.eclss.ars.co2.stw;
        allocate Functions::FN_CO2_STW::F_CO2_STW_02 to context.sts.orb.eclss.ars.co2.stw;
        allocate Functions::FN_CO2_STW::F_CO2_STW_03 to context.sts.orb.eclss.ars.co2.stw;
        allocate Functions::FN_CO2_STW::F_CO2_STW_04 to context.sts.orb.eclss.ars.co2.stw;
        allocate Functions::FN_CO2_STW::F_CO2_STW_05 to context.sts.orb.eclss.ars.co2.stw;
        allocate Functions::FN_CO2_STW::F_CO2_STW_06 to context.sts.orb.eclss.ars.co2.stw;
        allocate Functions::FN_CO2_STW::F_CO2_STW_07 to context.sts.orb.eclss.ars.co2.stw;
        allocate Functions::FN_CO2_STW::F_CO2_STW_08 to context.sts.orb.eclss.ars.co2.stw;
        allocate Functions::FN_CO2_STW::F_CO2_STW_09 to context.sts.orb.eclss.ars.co2.stw;
        allocate Functions::FN_CO2_STW::F_CO2_STW_10 to context.sts.orb.eclss.ars.co2.stw;
        allocate Functions::FN_CO2_STW::F_CO2_STW_11 to context.sts.orb.eclss.ars.co2.stw;
        allocate Functions::FN_CO2_STW::F_CO2_STW_12 to context.sts.orb.eclss.ars.co2.stw;
        allocate Functions::FN_ARS_IMU::F_ARS_IMU_01 to context.sts.orb.eclss.ars.imu;
        allocate Functions::FN_ARS_IMU::F_ARS_IMU_02 to context.sts.orb.eclss.ars.imu;
        allocate Functions::FN_ARS_IMU::F_ARS_IMU_03 to context.sts.orb.eclss.ars.imu;
        allocate Functions::FN_ARS_IMU::F_ARS_IMU_04 to context.sts.orb.eclss.ars.imu;
        allocate Functions::FN_ARS_IMU::F_ARS_IMU_05 to context.sts.orb.eclss.ars.imu;
        allocate Functions::FN_ARS_IMU::F_ARS_IMU_06 to context.sts.orb.eclss.ars.imu;
        allocate Functions::FN_ARS_IMU::F_ARS_IMU_07 to context.sts.orb.eclss.ars.imu;
        allocate Functions::FN_ARS_IMU::F_ARS_IMU_08 to context.sts.orb.eclss.ars.imu;
        allocate Functions::FN_ARS_IMU::F_ARS_IMU_09 to context.sts.orb.eclss.ars.imu;
        allocate Functions::FN_ARS_IMU::F_ARS_IMU_10 to context.sts.orb.eclss.ars.imu;
        allocate Functions::FN_ARS_IMU::F_ARS_IMU_11 to context.sts.orb.eclss.ars.imu;
        allocate Functions::FN_ARS_IMU_FAN::F_ARS_IMU_FAN_01 to context.sts.orb.eclss.ars.imu.fan;
        allocate Functions::FN_ARS_IMU_FAN::F_ARS_IMU_FAN_02 to context.sts.orb.eclss.ars.imu.fan;
        allocate Functions::FN_ARS_IMU_FAN::F_ARS_IMU_FAN_03 to context.sts.orb.eclss.ars.imu.fan;
        allocate Functions::FN_ARS_IMU_FAN::F_ARS_IMU_FAN_04 to context.sts.orb.eclss.ars.imu.fan;
        allocate Functions::FN_ARS_IMU_FAN::F_ARS_IMU_FAN_05 to context.sts.orb.eclss.ars.imu.fan;
        allocate Functions::FN_ARS_IMU_FAN::F_ARS_IMU_FAN_06 to context.sts.orb.eclss.ars.imu.fan;
        allocate Functions::FN_ARS_IMU_FAN::F_ARS_IMU_FAN_07 to context.sts.orb.eclss.ars.imu.fan;
        allocate Functions::FN_ARS_IMU_FAN::F_ARS_IMU_FAN_08 to context.sts.orb.eclss.ars.imu.fan;
        allocate Functions::FN_ARS_IMU_FAN::F_ARS_IMU_FAN_09 to context.sts.orb.eclss.ars.imu.fan;
        allocate Functions::FN_ARS_IMU_FAN::F_ARS_IMU_FAN_10 to context.sts.orb.eclss.ars.imu.fan;
        allocate Functions::FN_ARS_IMU_FAN::F_ARS_IMU_FAN_11 to context.sts.orb.eclss.ars.imu.fan;
        allocate Functions::FN_ARS_IMU_FAN::F_ARS_IMU_FAN_12 to context.sts.orb.eclss.ars.imu.fan;
        allocate Functions::FN_ARS_IMU_HEX::F_ARS_IMU_HEX_01 to context.sts.orb.eclss.ars.imu.hex;
        allocate Functions::FN_ARS_IMU_HEX::F_ARS_IMU_HEX_02 to context.sts.orb.eclss.ars.imu.hex;
        allocate Functions::FN_ARS_IMU_HEX::F_ARS_IMU_HEX_03 to context.sts.orb.eclss.ars.imu.hex;
        allocate Functions::FN_ARS_IMU_HEX::F_ARS_IMU_HEX_04 to context.sts.orb.eclss.ars.imu.hex;
        allocate Functions::FN_ARS_IMU_HEX::F_ARS_IMU_HEX_05 to context.sts.orb.eclss.ars.imu.hex;
        allocate Functions::FN_ARS_IMU_HEX::F_ARS_IMU_HEX_06 to context.sts.orb.eclss.ars.imu.hex;
        allocate Functions::FN_ARS_IMU_HEX::F_ARS_IMU_HEX_07 to context.sts.orb.eclss.ars.imu.hex;
        allocate Functions::FN_ARS_IMU_HEX::F_ARS_IMU_HEX_08 to context.sts.orb.eclss.ars.imu.hex;
        allocate Functions::FN_ARS_IMU_HEX::F_ARS_IMU_HEX_09 to context.sts.orb.eclss.ars.imu.hex;
        allocate Functions::FN_ARS_IMU_HEX::F_ARS_IMU_HEX_10 to context.sts.orb.eclss.ars.imu.hex;
        allocate Functions::FN_ARS_IMU_HEX::F_ARS_IMU_HEX_11 to context.sts.orb.eclss.ars.imu.hex;
        allocate Functions::FN_ARS_IMU_HEX::F_ARS_IMU_HEX_12 to context.sts.orb.eclss.ars.imu.hex;
        allocate Functions::FN_ARS_IMU_INL::F_ARS_IMU_INL_01 to context.sts.orb.eclss.ars.imu.inl;
        allocate Functions::FN_ARS_IMU_INL::F_ARS_IMU_INL_02 to context.sts.orb.eclss.ars.imu.inl;
        allocate Functions::FN_ARS_IMU_INL::F_ARS_IMU_INL_03 to context.sts.orb.eclss.ars.imu.inl;
        allocate Functions::FN_ARS_IMU_INL::F_ARS_IMU_INL_04 to context.sts.orb.eclss.ars.imu.inl;
        allocate Functions::FN_ARS_IMU_INL::F_ARS_IMU_INL_05 to context.sts.orb.eclss.ars.imu.inl;
        allocate Functions::FN_ARS_IMU_INL::F_ARS_IMU_INL_06 to context.sts.orb.eclss.ars.imu.inl;
        allocate Functions::FN_ARS_IMU_INL::F_ARS_IMU_INL_07 to context.sts.orb.eclss.ars.imu.inl;
        allocate Functions::FN_ARS_IMU_INL::F_ARS_IMU_INL_08 to context.sts.orb.eclss.ars.imu.inl;
        allocate Functions::FN_ARS_IMU_INL::F_ARS_IMU_INL_09 to context.sts.orb.eclss.ars.imu.inl;
        allocate Functions::FN_ARS_IMU_INL::F_ARS_IMU_INL_10 to context.sts.orb.eclss.ars.imu.inl;
        allocate Functions::FN_ARS_IMU_INL::F_ARS_IMU_INL_11 to context.sts.orb.eclss.ars.imu.inl;
        allocate Functions::FN_ARS_IMU_INL::F_ARS_IMU_INL_12 to context.sts.orb.eclss.ars.imu.inl;
        allocate Functions::FN_ARS_IMU_MON::F_ARS_IMU_MON_01 to context.sts.orb.eclss.ars.imu.mon;
        allocate Functions::FN_ARS_IMU_MON::F_ARS_IMU_MON_02 to context.sts.orb.eclss.ars.imu.mon;
        allocate Functions::FN_ARS_IMU_MON::F_ARS_IMU_MON_03 to context.sts.orb.eclss.ars.imu.mon;
        allocate Functions::FN_ARS_IMU_MON::F_ARS_IMU_MON_04 to context.sts.orb.eclss.ars.imu.mon;
        allocate Functions::FN_ARS_IMU_MON::F_ARS_IMU_MON_05 to context.sts.orb.eclss.ars.imu.mon;
        allocate Functions::FN_ARS_IMU_MON::F_ARS_IMU_MON_06 to context.sts.orb.eclss.ars.imu.mon;
        allocate Functions::FN_ARS_IMU_MON::F_ARS_IMU_MON_07 to context.sts.orb.eclss.ars.imu.mon;
        allocate Functions::FN_ARS_IMU_MON::F_ARS_IMU_MON_08 to context.sts.orb.eclss.ars.imu.mon;
        allocate Functions::FN_ARS_IMU_MON::F_ARS_IMU_MON_09 to context.sts.orb.eclss.ars.imu.mon;
        allocate Functions::FN_ARS_IMU_MON::F_ARS_IMU_MON_10 to context.sts.orb.eclss.ars.imu.mon;
        allocate Functions::FN_ARS_IMU_MON::F_ARS_IMU_MON_11 to context.sts.orb.eclss.ars.imu.mon;
        allocate Functions::FN_ARS_IMU_MON::F_ARS_IMU_MON_12 to context.sts.orb.eclss.ars.imu.mon;
        allocate Functions::FN_ARS_IMU_OPS::F_ARS_IMU_OPS_01 to context.sts.orb.eclss.ars.imu.ops;
        allocate Functions::FN_ARS_IMU_OPS::F_ARS_IMU_OPS_02 to context.sts.orb.eclss.ars.imu.ops;
        allocate Functions::FN_ARS_IMU_OPS::F_ARS_IMU_OPS_03 to context.sts.orb.eclss.ars.imu.ops;
        allocate Functions::FN_ARS_IMU_OPS::F_ARS_IMU_OPS_04 to context.sts.orb.eclss.ars.imu.ops;
        allocate Functions::FN_ARS_IMU_OPS::F_ARS_IMU_OPS_05 to context.sts.orb.eclss.ars.imu.ops;
        allocate Functions::FN_ARS_IMU_OPS::F_ARS_IMU_OPS_06 to context.sts.orb.eclss.ars.imu.ops;
        allocate Functions::FN_ARS_IMU_OPS::F_ARS_IMU_OPS_07 to context.sts.orb.eclss.ars.imu.ops;
        allocate Functions::FN_ARS_IMU_OPS::F_ARS_IMU_OPS_08 to context.sts.orb.eclss.ars.imu.ops;
        allocate Functions::FN_ARS_IMU_OPS::F_ARS_IMU_OPS_09 to context.sts.orb.eclss.ars.imu.ops;
        allocate Functions::FN_ARS_IMU_OPS::F_ARS_IMU_OPS_10 to context.sts.orb.eclss.ars.imu.ops;
        allocate Functions::FN_ARS_IMU_OPS::F_ARS_IMU_OPS_11 to context.sts.orb.eclss.ars.imu.ops;
        allocate Functions::FN_ARS_IMU_OPS::F_ARS_IMU_OPS_12 to context.sts.orb.eclss.ars.imu.ops;
        allocate Functions::FN_ARS_RCRS::F_ARS_RCRS_01 to context.sts.orb.eclss.ars.rcrs;
        allocate Functions::FN_ARS_RCRS::F_ARS_RCRS_02 to context.sts.orb.eclss.ars.rcrs;
        allocate Functions::FN_ARS_RCRS::F_ARS_RCRS_03 to context.sts.orb.eclss.ars.rcrs;
        allocate Functions::FN_ARS_RCRS::F_ARS_RCRS_04 to context.sts.orb.eclss.ars.rcrs;
        allocate Functions::FN_ARS_RCRS::F_ARS_RCRS_05 to context.sts.orb.eclss.ars.rcrs;
        allocate Functions::FN_ARS_RCRS::F_ARS_RCRS_06 to context.sts.orb.eclss.ars.rcrs;
        allocate Functions::FN_ARS_RCRS::F_ARS_RCRS_07 to context.sts.orb.eclss.ars.rcrs;
        allocate Functions::FN_ARS_RCRS::F_ARS_RCRS_08 to context.sts.orb.eclss.ars.rcrs;
        allocate Functions::FN_ARS_RCRS::F_ARS_RCRS_09 to context.sts.orb.eclss.ars.rcrs;
        allocate Functions::FN_ARS_RCRS::F_ARS_RCRS_10 to context.sts.orb.eclss.ars.rcrs;
        allocate Functions::FN_ARS_RCRS::F_ARS_RCRS_11 to context.sts.orb.eclss.ars.rcrs;
        allocate Functions::FN_ARS_RCRS_BED::F_ARS_RCRS_BED_01 to context.sts.orb.eclss.ars.rcrs.bed;
        allocate Functions::FN_ARS_RCRS_BED::F_ARS_RCRS_BED_02 to context.sts.orb.eclss.ars.rcrs.bed;
        allocate Functions::FN_ARS_RCRS_BED::F_ARS_RCRS_BED_03 to context.sts.orb.eclss.ars.rcrs.bed;
        allocate Functions::FN_ARS_RCRS_BED::F_ARS_RCRS_BED_04 to context.sts.orb.eclss.ars.rcrs.bed;
        allocate Functions::FN_ARS_RCRS_BED::F_ARS_RCRS_BED_05 to context.sts.orb.eclss.ars.rcrs.bed;
        allocate Functions::FN_ARS_RCRS_BED::F_ARS_RCRS_BED_06 to context.sts.orb.eclss.ars.rcrs.bed;
        allocate Functions::FN_ARS_RCRS_BED::F_ARS_RCRS_BED_07 to context.sts.orb.eclss.ars.rcrs.bed;
        allocate Functions::FN_ARS_RCRS_BED::F_ARS_RCRS_BED_08 to context.sts.orb.eclss.ars.rcrs.bed;
        allocate Functions::FN_ARS_RCRS_BED::F_ARS_RCRS_BED_09 to context.sts.orb.eclss.ars.rcrs.bed;
        allocate Functions::FN_ARS_RCRS_BED::F_ARS_RCRS_BED_10 to context.sts.orb.eclss.ars.rcrs.bed;
        allocate Functions::FN_ARS_RCRS_BED::F_ARS_RCRS_BED_11 to context.sts.orb.eclss.ars.rcrs.bed;
        allocate Functions::FN_ARS_RCRS_CTL::F_ARS_RCRS_CTL_01 to context.sts.orb.eclss.ars.rcrs.ctl;
        allocate Functions::FN_ARS_RCRS_CTL::F_ARS_RCRS_CTL_02 to context.sts.orb.eclss.ars.rcrs.ctl;
        allocate Functions::FN_ARS_RCRS_CTL::F_ARS_RCRS_CTL_03 to context.sts.orb.eclss.ars.rcrs.ctl;
        allocate Functions::FN_ARS_RCRS_CTL::F_ARS_RCRS_CTL_04 to context.sts.orb.eclss.ars.rcrs.ctl;
        allocate Functions::FN_ARS_RCRS_CTL::F_ARS_RCRS_CTL_05 to context.sts.orb.eclss.ars.rcrs.ctl;
        allocate Functions::FN_ARS_RCRS_CTL::F_ARS_RCRS_CTL_06 to context.sts.orb.eclss.ars.rcrs.ctl;
        allocate Functions::FN_ARS_RCRS_CTL::F_ARS_RCRS_CTL_07 to context.sts.orb.eclss.ars.rcrs.ctl;
        allocate Functions::FN_ARS_RCRS_CTL::F_ARS_RCRS_CTL_08 to context.sts.orb.eclss.ars.rcrs.ctl;
        allocate Functions::FN_ARS_RCRS_CTL::F_ARS_RCRS_CTL_09 to context.sts.orb.eclss.ars.rcrs.ctl;
        allocate Functions::FN_ARS_RCRS_CTL::F_ARS_RCRS_CTL_10 to context.sts.orb.eclss.ars.rcrs.ctl;
        allocate Functions::FN_ARS_RCRS_CTL::F_ARS_RCRS_CTL_11 to context.sts.orb.eclss.ars.rcrs.ctl;
        allocate Functions::FN_ARS_RCRS_CTL::F_ARS_RCRS_CTL_12 to context.sts.orb.eclss.ars.rcrs.ctl;
        allocate Functions::FN_ARS_RCRS_FAN::F_ARS_RCRS_FAN_01 to context.sts.orb.eclss.ars.rcrs.fan;
        allocate Functions::FN_ARS_RCRS_FAN::F_ARS_RCRS_FAN_02 to context.sts.orb.eclss.ars.rcrs.fan;
        allocate Functions::FN_ARS_RCRS_FAN::F_ARS_RCRS_FAN_03 to context.sts.orb.eclss.ars.rcrs.fan;
        allocate Functions::FN_ARS_RCRS_FAN::F_ARS_RCRS_FAN_04 to context.sts.orb.eclss.ars.rcrs.fan;
        allocate Functions::FN_ARS_RCRS_FAN::F_ARS_RCRS_FAN_05 to context.sts.orb.eclss.ars.rcrs.fan;
        allocate Functions::FN_ARS_RCRS_FAN::F_ARS_RCRS_FAN_06 to context.sts.orb.eclss.ars.rcrs.fan;
        allocate Functions::FN_ARS_RCRS_FAN::F_ARS_RCRS_FAN_07 to context.sts.orb.eclss.ars.rcrs.fan;
        allocate Functions::FN_ARS_RCRS_FAN::F_ARS_RCRS_FAN_08 to context.sts.orb.eclss.ars.rcrs.fan;
        allocate Functions::FN_ARS_RCRS_FAN::F_ARS_RCRS_FAN_09 to context.sts.orb.eclss.ars.rcrs.fan;
        allocate Functions::FN_ARS_RCRS_MON::F_ARS_RCRS_MON_01 to context.sts.orb.eclss.ars.rcrs.mon;
        allocate Functions::FN_ARS_RCRS_MON::F_ARS_RCRS_MON_02 to context.sts.orb.eclss.ars.rcrs.mon;
        allocate Functions::FN_ARS_RCRS_MON::F_ARS_RCRS_MON_03 to context.sts.orb.eclss.ars.rcrs.mon;
        allocate Functions::FN_ARS_RCRS_MON::F_ARS_RCRS_MON_04 to context.sts.orb.eclss.ars.rcrs.mon;
        allocate Functions::FN_ARS_RCRS_MON::F_ARS_RCRS_MON_05 to context.sts.orb.eclss.ars.rcrs.mon;
        allocate Functions::FN_ARS_RCRS_MON::F_ARS_RCRS_MON_06 to context.sts.orb.eclss.ars.rcrs.mon;
        allocate Functions::FN_ARS_RCRS_MON::F_ARS_RCRS_MON_07 to context.sts.orb.eclss.ars.rcrs.mon;
        allocate Functions::FN_ARS_RCRS_MON::F_ARS_RCRS_MON_08 to context.sts.orb.eclss.ars.rcrs.mon;
        allocate Functions::FN_ARS_RCRS_MON::F_ARS_RCRS_MON_09 to context.sts.orb.eclss.ars.rcrs.mon;
        allocate Functions::FN_ARS_RCRS_MON::F_ARS_RCRS_MON_10 to context.sts.orb.eclss.ars.rcrs.mon;
        allocate Functions::FN_ARS_RCRS_OPS::F_ARS_RCRS_OPS_01 to context.sts.orb.eclss.ars.rcrs.ops;
        allocate Functions::FN_ARS_RCRS_OPS::F_ARS_RCRS_OPS_02 to context.sts.orb.eclss.ars.rcrs.ops;
        allocate Functions::FN_ARS_RCRS_OPS::F_ARS_RCRS_OPS_03 to context.sts.orb.eclss.ars.rcrs.ops;
        allocate Functions::FN_ARS_RCRS_OPS::F_ARS_RCRS_OPS_04 to context.sts.orb.eclss.ars.rcrs.ops;
        allocate Functions::FN_ARS_RCRS_OPS::F_ARS_RCRS_OPS_05 to context.sts.orb.eclss.ars.rcrs.ops;
        allocate Functions::FN_ARS_RCRS_OPS::F_ARS_RCRS_OPS_06 to context.sts.orb.eclss.ars.rcrs.ops;
        allocate Functions::FN_ARS_RCRS_OPS::F_ARS_RCRS_OPS_07 to context.sts.orb.eclss.ars.rcrs.ops;
        allocate Functions::FN_ARS_RCRS_OPS::F_ARS_RCRS_OPS_08 to context.sts.orb.eclss.ars.rcrs.ops;
        allocate Functions::FN_ARS_RCRS_OPS::F_ARS_RCRS_OPS_09 to context.sts.orb.eclss.ars.rcrs.ops;
        allocate Functions::FN_ARS_RCRS_OPS::F_ARS_RCRS_OPS_10 to context.sts.orb.eclss.ars.rcrs.ops;
        allocate Functions::FN_ARS_RCRS_OPS::F_ARS_RCRS_OPS_11 to context.sts.orb.eclss.ars.rcrs.ops;
        allocate Functions::FN_ARS_RCRS_OPS::F_ARS_RCRS_OPS_12 to context.sts.orb.eclss.ars.rcrs.ops;
        allocate Functions::FN_ARS_RCRS_USC::F_ARS_RCRS_USC_01 to context.sts.orb.eclss.ars.rcrs.usc;
        allocate Functions::FN_ARS_RCRS_USC::F_ARS_RCRS_USC_02 to context.sts.orb.eclss.ars.rcrs.usc;
        allocate Functions::FN_ARS_RCRS_USC::F_ARS_RCRS_USC_03 to context.sts.orb.eclss.ars.rcrs.usc;
        allocate Functions::FN_ARS_RCRS_USC::F_ARS_RCRS_USC_04 to context.sts.orb.eclss.ars.rcrs.usc;
        allocate Functions::FN_ARS_RCRS_USC::F_ARS_RCRS_USC_05 to context.sts.orb.eclss.ars.rcrs.usc;
        allocate Functions::FN_ARS_RCRS_USC::F_ARS_RCRS_USC_06 to context.sts.orb.eclss.ars.rcrs.usc;
        allocate Functions::FN_ARS_RCRS_USC::F_ARS_RCRS_USC_07 to context.sts.orb.eclss.ars.rcrs.usc;
        allocate Functions::FN_ARS_RCRS_USC::F_ARS_RCRS_USC_08 to context.sts.orb.eclss.ars.rcrs.usc;
        allocate Functions::FN_ARS_RCRS_USC::F_ARS_RCRS_USC_09 to context.sts.orb.eclss.ars.rcrs.usc;
        allocate Functions::FN_ARS_RCRS_USC::F_ARS_RCRS_USC_10 to context.sts.orb.eclss.ars.rcrs.usc;
        allocate Functions::FN_ARS_RCRS_USC::F_ARS_RCRS_USC_11 to context.sts.orb.eclss.ars.rcrs.usc;
        allocate Functions::FN_ARS_THC::F_ARS_THC_01 to context.sts.orb.eclss.ars.thc;
        allocate Functions::FN_ARS_THC::F_ARS_THC_02 to context.sts.orb.eclss.ars.thc;
        allocate Functions::FN_ARS_THC::F_ARS_THC_03 to context.sts.orb.eclss.ars.thc;
        allocate Functions::FN_ARS_THC::F_ARS_THC_04 to context.sts.orb.eclss.ars.thc;
        allocate Functions::FN_ARS_THC::F_ARS_THC_05 to context.sts.orb.eclss.ars.thc;
        allocate Functions::FN_ARS_THC::F_ARS_THC_06 to context.sts.orb.eclss.ars.thc;
        allocate Functions::FN_ARS_THC::F_ARS_THC_07 to context.sts.orb.eclss.ars.thc;
        allocate Functions::FN_ARS_THC::F_ARS_THC_08 to context.sts.orb.eclss.ars.thc;
        allocate Functions::FN_ARS_THC::F_ARS_THC_09 to context.sts.orb.eclss.ars.thc;
        allocate Functions::FN_ARS_THC::F_ARS_THC_10 to context.sts.orb.eclss.ars.thc;
        allocate Functions::FN_ARS_THC::F_ARS_THC_11 to context.sts.orb.eclss.ars.thc;
        allocate Functions::FN_ARS_THC_HX::F_ARS_THC_HX_01 to context.sts.orb.eclss.ars.thc.hx;
        allocate Functions::FN_ARS_THC_HX::F_ARS_THC_HX_02 to context.sts.orb.eclss.ars.thc.hx;
        allocate Functions::FN_ARS_THC_HX::F_ARS_THC_HX_03 to context.sts.orb.eclss.ars.thc.hx;
        allocate Functions::FN_ARS_THC_HX::F_ARS_THC_HX_04 to context.sts.orb.eclss.ars.thc.hx;
        allocate Functions::FN_ARS_THC_HX::F_ARS_THC_HX_05 to context.sts.orb.eclss.ars.thc.hx;
        allocate Functions::FN_ARS_THC_HX::F_ARS_THC_HX_06 to context.sts.orb.eclss.ars.thc.hx;
        allocate Functions::FN_ARS_THC_HX::F_ARS_THC_HX_07 to context.sts.orb.eclss.ars.thc.hx;
        allocate Functions::FN_ARS_THC_HX::F_ARS_THC_HX_08 to context.sts.orb.eclss.ars.thc.hx;
        allocate Functions::FN_ARS_THC_HX::F_ARS_THC_HX_09 to context.sts.orb.eclss.ars.thc.hx;
        allocate Functions::FN_ARS_THC_HX::F_ARS_THC_HX_10 to context.sts.orb.eclss.ars.thc.hx;
        allocate Functions::FN_ARS_THC_MON::F_ARS_THC_MON_01 to context.sts.orb.eclss.ars.thc.mon;
        allocate Functions::FN_ARS_THC_MON::F_ARS_THC_MON_02 to context.sts.orb.eclss.ars.thc.mon;
        allocate Functions::FN_ARS_THC_MON::F_ARS_THC_MON_03 to context.sts.orb.eclss.ars.thc.mon;
        allocate Functions::FN_ARS_THC_MON::F_ARS_THC_MON_04 to context.sts.orb.eclss.ars.thc.mon;
        allocate Functions::FN_ARS_THC_MON::F_ARS_THC_MON_05 to context.sts.orb.eclss.ars.thc.mon;
        allocate Functions::FN_ARS_THC_MON::F_ARS_THC_MON_06 to context.sts.orb.eclss.ars.thc.mon;
        allocate Functions::FN_ARS_THC_MON::F_ARS_THC_MON_07 to context.sts.orb.eclss.ars.thc.mon;
        allocate Functions::FN_ARS_THC_MON::F_ARS_THC_MON_08 to context.sts.orb.eclss.ars.thc.mon;
        allocate Functions::FN_ARS_THC_MON::F_ARS_THC_MON_09 to context.sts.orb.eclss.ars.thc.mon;
        allocate Functions::FN_ARS_THC_MON::F_ARS_THC_MON_10 to context.sts.orb.eclss.ars.thc.mon;
        allocate Functions::FN_ARS_THC_MON::F_ARS_THC_MON_11 to context.sts.orb.eclss.ars.thc.mon;
        allocate Functions::FN_ARS_THC_MON::F_ARS_THC_MON_12 to context.sts.orb.eclss.ars.thc.mon;
        allocate Functions::FN_ARS_THC_OPS::F_ARS_THC_OPS_01 to context.sts.orb.eclss.ars.thc.ops;
        allocate Functions::FN_ARS_THC_OPS::F_ARS_THC_OPS_02 to context.sts.orb.eclss.ars.thc.ops;
        allocate Functions::FN_ARS_THC_OPS::F_ARS_THC_OPS_03 to context.sts.orb.eclss.ars.thc.ops;
        allocate Functions::FN_ARS_THC_OPS::F_ARS_THC_OPS_04 to context.sts.orb.eclss.ars.thc.ops;
        allocate Functions::FN_ARS_THC_OPS::F_ARS_THC_OPS_05 to context.sts.orb.eclss.ars.thc.ops;
        allocate Functions::FN_ARS_THC_OPS::F_ARS_THC_OPS_06 to context.sts.orb.eclss.ars.thc.ops;
        allocate Functions::FN_ARS_THC_OPS::F_ARS_THC_OPS_07 to context.sts.orb.eclss.ars.thc.ops;
        allocate Functions::FN_ARS_THC_OPS::F_ARS_THC_OPS_08 to context.sts.orb.eclss.ars.thc.ops;
        allocate Functions::FN_ARS_THC_OPS::F_ARS_THC_OPS_09 to context.sts.orb.eclss.ars.thc.ops;
        allocate Functions::FN_ARS_THC_OPS::F_ARS_THC_OPS_10 to context.sts.orb.eclss.ars.thc.ops;
        allocate Functions::FN_ARS_THC_OPS::F_ARS_THC_OPS_11 to context.sts.orb.eclss.ars.thc.ops;
        allocate Functions::FN_ARS_THC_OPS::F_ARS_THC_OPS_12 to context.sts.orb.eclss.ars.thc.ops;
        allocate Functions::FN_ARS_THC_SEP::F_ARS_THC_SEP_01 to context.sts.orb.eclss.ars.thc.sep;
        allocate Functions::FN_ARS_THC_SEP::F_ARS_THC_SEP_02 to context.sts.orb.eclss.ars.thc.sep;
        allocate Functions::FN_ARS_THC_SEP::F_ARS_THC_SEP_03 to context.sts.orb.eclss.ars.thc.sep;
        allocate Functions::FN_ARS_THC_SEP::F_ARS_THC_SEP_04 to context.sts.orb.eclss.ars.thc.sep;
        allocate Functions::FN_ARS_THC_SEP::F_ARS_THC_SEP_05 to context.sts.orb.eclss.ars.thc.sep;
        allocate Functions::FN_ARS_THC_SEP::F_ARS_THC_SEP_06 to context.sts.orb.eclss.ars.thc.sep;
        allocate Functions::FN_ARS_THC_SEP::F_ARS_THC_SEP_07 to context.sts.orb.eclss.ars.thc.sep;
        allocate Functions::FN_ARS_THC_SEP::F_ARS_THC_SEP_08 to context.sts.orb.eclss.ars.thc.sep;
        allocate Functions::FN_ARS_THC_SEP::F_ARS_THC_SEP_09 to context.sts.orb.eclss.ars.thc.sep;
        allocate Functions::FN_ARS_THC_SEP::F_ARS_THC_SEP_10 to context.sts.orb.eclss.ars.thc.sep;
        allocate Functions::FN_ARS_THC_SEP::F_ARS_THC_SEP_11 to context.sts.orb.eclss.ars.thc.sep;
        allocate Functions::FN_ARS_THC_SEP::F_ARS_THC_SEP_12 to context.sts.orb.eclss.ars.thc.sep;
        allocate Functions::FN_ARS_THC_TCV::F_ARS_THC_TCV_01 to context.sts.orb.eclss.ars.thc.tcv;
        allocate Functions::FN_ARS_THC_TCV::F_ARS_THC_TCV_02 to context.sts.orb.eclss.ars.thc.tcv;
        allocate Functions::FN_ARS_THC_TCV::F_ARS_THC_TCV_03 to context.sts.orb.eclss.ars.thc.tcv;
        allocate Functions::FN_ARS_THC_TCV::F_ARS_THC_TCV_04 to context.sts.orb.eclss.ars.thc.tcv;
        allocate Functions::FN_ARS_THC_TCV::F_ARS_THC_TCV_05 to context.sts.orb.eclss.ars.thc.tcv;
        allocate Functions::FN_ARS_THC_TCV::F_ARS_THC_TCV_06 to context.sts.orb.eclss.ars.thc.tcv;
        allocate Functions::FN_ARS_THC_TCV::F_ARS_THC_TCV_07 to context.sts.orb.eclss.ars.thc.tcv;
        allocate Functions::FN_ARS_THC_TCV::F_ARS_THC_TCV_08 to context.sts.orb.eclss.ars.thc.tcv;
        allocate Functions::FN_ARS_THC_TCV::F_ARS_THC_TCV_09 to context.sts.orb.eclss.ars.thc.tcv;
        allocate Functions::FN_ARS_THC_TCV::F_ARS_THC_TCV_10 to context.sts.orb.eclss.ars.thc.tcv;
        allocate Functions::FN_ARS_THC_TCV::F_ARS_THC_TCV_11 to context.sts.orb.eclss.ars.thc.tcv;
        allocate Functions::FN_ARS_WCL::F_ARS_WCL_01 to context.sts.orb.eclss.ars.wcl;
        allocate Functions::FN_ARS_WCL::F_ARS_WCL_02 to context.sts.orb.eclss.ars.wcl;
        allocate Functions::FN_ARS_WCL::F_ARS_WCL_03 to context.sts.orb.eclss.ars.wcl;
        allocate Functions::FN_ARS_WCL::F_ARS_WCL_04 to context.sts.orb.eclss.ars.wcl;
        allocate Functions::FN_ARS_WCL::F_ARS_WCL_05 to context.sts.orb.eclss.ars.wcl;
        allocate Functions::FN_ARS_WCL::F_ARS_WCL_06 to context.sts.orb.eclss.ars.wcl;
        allocate Functions::FN_ARS_WCL::F_ARS_WCL_07 to context.sts.orb.eclss.ars.wcl;
        allocate Functions::FN_ARS_WCL::F_ARS_WCL_08 to context.sts.orb.eclss.ars.wcl;
        allocate Functions::FN_ARS_WCL::F_ARS_WCL_09 to context.sts.orb.eclss.ars.wcl;
        allocate Functions::FN_ARS_WCL::F_ARS_WCL_10 to context.sts.orb.eclss.ars.wcl;
        allocate Functions::FN_ARS_WCL::F_ARS_WCL_11 to context.sts.orb.eclss.ars.wcl;
        allocate Functions::FN_ARS_WCL::F_ARS_WCL_12 to context.sts.orb.eclss.ars.wcl;
        allocate Functions::FN_ARS_WCL::F_ARS_WCL_13 to context.sts.orb.eclss.ars.wcl;
        allocate Functions::FN_ARS_WCL::F_ARS_WCL_14 to context.sts.orb.eclss.ars.wcl;
        allocate Functions::FN_ARS_WCL_AVL::F_ARS_WCL_AVL_01 to context.sts.orb.eclss.ars.wcl.avl;
        allocate Functions::FN_ARS_WCL_AVL::F_ARS_WCL_AVL_02 to context.sts.orb.eclss.ars.wcl.avl;
        allocate Functions::FN_ARS_WCL_AVL::F_ARS_WCL_AVL_03 to context.sts.orb.eclss.ars.wcl.avl;
        allocate Functions::FN_ARS_WCL_AVL::F_ARS_WCL_AVL_04 to context.sts.orb.eclss.ars.wcl.avl;
        allocate Functions::FN_ARS_WCL_AVL::F_ARS_WCL_AVL_05 to context.sts.orb.eclss.ars.wcl.avl;
        allocate Functions::FN_ARS_WCL_AVL::F_ARS_WCL_AVL_06 to context.sts.orb.eclss.ars.wcl.avl;
        allocate Functions::FN_ARS_WCL_AVL::F_ARS_WCL_AVL_07 to context.sts.orb.eclss.ars.wcl.avl;
        allocate Functions::FN_ARS_WCL_AVL::F_ARS_WCL_AVL_08 to context.sts.orb.eclss.ars.wcl.avl;
        allocate Functions::FN_ARS_WCL_AVL::F_ARS_WCL_AVL_09 to context.sts.orb.eclss.ars.wcl.avl;
        allocate Functions::FN_ARS_WCL_AVL::F_ARS_WCL_AVL_10 to context.sts.orb.eclss.ars.wcl.avl;
        allocate Functions::FN_ARS_WCL_AVL::F_ARS_WCL_AVL_11 to context.sts.orb.eclss.ars.wcl.avl;
        allocate Functions::FN_ARS_WCL_CLD::F_ARS_WCL_CLD_01 to context.sts.orb.eclss.ars.wcl.cld;
        allocate Functions::FN_ARS_WCL_CLD::F_ARS_WCL_CLD_02 to context.sts.orb.eclss.ars.wcl.cld;
        allocate Functions::FN_ARS_WCL_CLD::F_ARS_WCL_CLD_03 to context.sts.orb.eclss.ars.wcl.cld;
        allocate Functions::FN_ARS_WCL_CLD::F_ARS_WCL_CLD_04 to context.sts.orb.eclss.ars.wcl.cld;
        allocate Functions::FN_ARS_WCL_CLD::F_ARS_WCL_CLD_05 to context.sts.orb.eclss.ars.wcl.cld;
        allocate Functions::FN_ARS_WCL_CLD::F_ARS_WCL_CLD_06 to context.sts.orb.eclss.ars.wcl.cld;
        allocate Functions::FN_ARS_WCL_CLD::F_ARS_WCL_CLD_07 to context.sts.orb.eclss.ars.wcl.cld;
        allocate Functions::FN_ARS_WCL_CLD::F_ARS_WCL_CLD_08 to context.sts.orb.eclss.ars.wcl.cld;
        allocate Functions::FN_ARS_WCL_CLD::F_ARS_WCL_CLD_09 to context.sts.orb.eclss.ars.wcl.cld;
        allocate Functions::FN_ARS_WCL_CLD::F_ARS_WCL_CLD_10 to context.sts.orb.eclss.ars.wcl.cld;
        allocate Functions::FN_ARS_WCL_CLD::F_ARS_WCL_CLD_11 to context.sts.orb.eclss.ars.wcl.cld;
        allocate Functions::FN_ARS_WCL_ICH::F_ARS_WCL_ICH_01 to context.sts.orb.eclss.ars.wcl.ich;
        allocate Functions::FN_ARS_WCL_ICH::F_ARS_WCL_ICH_02 to context.sts.orb.eclss.ars.wcl.ich;
        allocate Functions::FN_ARS_WCL_ICH::F_ARS_WCL_ICH_03 to context.sts.orb.eclss.ars.wcl.ich;
        allocate Functions::FN_ARS_WCL_ICH::F_ARS_WCL_ICH_04 to context.sts.orb.eclss.ars.wcl.ich;
        allocate Functions::FN_ARS_WCL_ICH::F_ARS_WCL_ICH_05 to context.sts.orb.eclss.ars.wcl.ich;
        allocate Functions::FN_ARS_WCL_ICH::F_ARS_WCL_ICH_06 to context.sts.orb.eclss.ars.wcl.ich;
        allocate Functions::FN_ARS_WCL_ICH::F_ARS_WCL_ICH_07 to context.sts.orb.eclss.ars.wcl.ich;
        allocate Functions::FN_ARS_WCL_ICH::F_ARS_WCL_ICH_08 to context.sts.orb.eclss.ars.wcl.ich;
        allocate Functions::FN_ARS_WCL_ICH::F_ARS_WCL_ICH_09 to context.sts.orb.eclss.ars.wcl.ich;
        allocate Functions::FN_ARS_WCL_ICH::F_ARS_WCL_ICH_10 to context.sts.orb.eclss.ars.wcl.ich;
        allocate Functions::FN_ARS_WCL_ICH::F_ARS_WCL_ICH_11 to context.sts.orb.eclss.ars.wcl.ich;
        allocate Functions::FN_ARS_WCL_ICH::F_ARS_WCL_ICH_12 to context.sts.orb.eclss.ars.wcl.ich;
        allocate Functions::FN_ARS_WCL_MON::F_ARS_WCL_MON_01 to context.sts.orb.eclss.ars.wcl.mon;
        allocate Functions::FN_ARS_WCL_MON::F_ARS_WCL_MON_02 to context.sts.orb.eclss.ars.wcl.mon;
        allocate Functions::FN_ARS_WCL_MON::F_ARS_WCL_MON_03 to context.sts.orb.eclss.ars.wcl.mon;
        allocate Functions::FN_ARS_WCL_MON::F_ARS_WCL_MON_04 to context.sts.orb.eclss.ars.wcl.mon;
        allocate Functions::FN_ARS_WCL_MON::F_ARS_WCL_MON_05 to context.sts.orb.eclss.ars.wcl.mon;
        allocate Functions::FN_ARS_WCL_MON::F_ARS_WCL_MON_06 to context.sts.orb.eclss.ars.wcl.mon;
        allocate Functions::FN_ARS_WCL_MON::F_ARS_WCL_MON_07 to context.sts.orb.eclss.ars.wcl.mon;
        allocate Functions::FN_ARS_WCL_MON::F_ARS_WCL_MON_08 to context.sts.orb.eclss.ars.wcl.mon;
        allocate Functions::FN_ARS_WCL_MON::F_ARS_WCL_MON_09 to context.sts.orb.eclss.ars.wcl.mon;
        allocate Functions::FN_ARS_WCL_MON::F_ARS_WCL_MON_10 to context.sts.orb.eclss.ars.wcl.mon;
        allocate Functions::FN_ARS_WCL_MON::F_ARS_WCL_MON_11 to context.sts.orb.eclss.ars.wcl.mon;
        allocate Functions::FN_ARS_WCL_MON::F_ARS_WCL_MON_12 to context.sts.orb.eclss.ars.wcl.mon;
        allocate Functions::FN_ARS_WCL_OPS::F_ARS_WCL_OPS_01 to context.sts.orb.eclss.ars.wcl.ops;
        allocate Functions::FN_ARS_WCL_OPS::F_ARS_WCL_OPS_02 to context.sts.orb.eclss.ars.wcl.ops;
        allocate Functions::FN_ARS_WCL_OPS::F_ARS_WCL_OPS_03 to context.sts.orb.eclss.ars.wcl.ops;
        allocate Functions::FN_ARS_WCL_OPS::F_ARS_WCL_OPS_04 to context.sts.orb.eclss.ars.wcl.ops;
        allocate Functions::FN_ARS_WCL_OPS::F_ARS_WCL_OPS_05 to context.sts.orb.eclss.ars.wcl.ops;
        allocate Functions::FN_ARS_WCL_OPS::F_ARS_WCL_OPS_06 to context.sts.orb.eclss.ars.wcl.ops;
        allocate Functions::FN_ARS_WCL_OPS::F_ARS_WCL_OPS_07 to context.sts.orb.eclss.ars.wcl.ops;
        allocate Functions::FN_ARS_WCL_OPS::F_ARS_WCL_OPS_08 to context.sts.orb.eclss.ars.wcl.ops;
        allocate Functions::FN_ARS_WCL_OPS::F_ARS_WCL_OPS_09 to context.sts.orb.eclss.ars.wcl.ops;
        allocate Functions::FN_ARS_WCL_OPS::F_ARS_WCL_OPS_10 to context.sts.orb.eclss.ars.wcl.ops;
        allocate Functions::FN_ARS_WCL_OPS::F_ARS_WCL_OPS_11 to context.sts.orb.eclss.ars.wcl.ops;
        allocate Functions::FN_ARS_WCL_OPS::F_ARS_WCL_OPS_12 to context.sts.orb.eclss.ars.wcl.ops;
        allocate Functions::FN_ARS_WCL_PMP::F_ARS_WCL_PMP_01 to context.sts.orb.eclss.ars.wcl.pmp;
        allocate Functions::FN_ARS_WCL_PMP::F_ARS_WCL_PMP_02 to context.sts.orb.eclss.ars.wcl.pmp;
        allocate Functions::FN_ARS_WCL_PMP::F_ARS_WCL_PMP_03 to context.sts.orb.eclss.ars.wcl.pmp;
        allocate Functions::FN_ARS_WCL_PMP::F_ARS_WCL_PMP_04 to context.sts.orb.eclss.ars.wcl.pmp;
        allocate Functions::FN_ARS_WCL_PMP::F_ARS_WCL_PMP_05 to context.sts.orb.eclss.ars.wcl.pmp;
        allocate Functions::FN_ARS_WCL_PMP::F_ARS_WCL_PMP_06 to context.sts.orb.eclss.ars.wcl.pmp;
        allocate Functions::FN_ARS_WCL_PMP::F_ARS_WCL_PMP_07 to context.sts.orb.eclss.ars.wcl.pmp;
        allocate Functions::FN_ARS_WCL_PMP::F_ARS_WCL_PMP_08 to context.sts.orb.eclss.ars.wcl.pmp;
        allocate Functions::FN_ARS_WCL_PMP::F_ARS_WCL_PMP_09 to context.sts.orb.eclss.ars.wcl.pmp;
        allocate Functions::FN_ARS_WCL_PMP::F_ARS_WCL_PMP_10 to context.sts.orb.eclss.ars.wcl.pmp;
        allocate Functions::FN_ARS_WCL_PMP::F_ARS_WCL_PMP_11 to context.sts.orb.eclss.ars.wcl.pmp;
        allocate Functions::FN_ARS_WCL_PMP::F_ARS_WCL_PMP_12 to context.sts.orb.eclss.ars.wcl.pmp;
        allocate Functions::FN_ECL_ATCS::F_ECL_ATCS_01 to context.sts.orb.eclss.atcs;
        allocate Functions::FN_ECL_ATCS::F_ECL_ATCS_02 to context.sts.orb.eclss.atcs;
        allocate Functions::FN_ECL_ATCS::F_ECL_ATCS_03 to context.sts.orb.eclss.atcs;
        allocate Functions::FN_ECL_ATCS::F_ECL_ATCS_04 to context.sts.orb.eclss.atcs;
        allocate Functions::FN_ECL_ATCS::F_ECL_ATCS_05 to context.sts.orb.eclss.atcs;
        allocate Functions::FN_ECL_ATCS::F_ECL_ATCS_06 to context.sts.orb.eclss.atcs;
        allocate Functions::FN_ECL_ATCS::F_ECL_ATCS_07 to context.sts.orb.eclss.atcs;
        allocate Functions::FN_TCS_FCL::F_TCS_FCL_01 to context.sts.orb.eclss.atcs.fcl;
        allocate Functions::FN_TCS_FCL::F_TCS_FCL_02 to context.sts.orb.eclss.atcs.fcl;
        allocate Functions::FN_TCS_FCL::F_TCS_FCL_03 to context.sts.orb.eclss.atcs.fcl;
        allocate Functions::FN_TCS_FCL::F_TCS_FCL_04 to context.sts.orb.eclss.atcs.fcl;
        allocate Functions::FN_TCS_FCL::F_TCS_FCL_05 to context.sts.orb.eclss.atcs.fcl;
        allocate Functions::FN_TCS_FCL::F_TCS_FCL_06 to context.sts.orb.eclss.atcs.fcl;
        allocate Functions::FN_TCS_FES::F_TCS_FES_01 to context.sts.orb.eclss.atcs.fes;
        allocate Functions::FN_TCS_FES::F_TCS_FES_02 to context.sts.orb.eclss.atcs.fes;
        allocate Functions::FN_TCS_FES::F_TCS_FES_03 to context.sts.orb.eclss.atcs.fes;
        allocate Functions::FN_TCS_FES::F_TCS_FES_04 to context.sts.orb.eclss.atcs.fes;
        allocate Functions::FN_TCS_FES::F_TCS_FES_05 to context.sts.orb.eclss.atcs.fes;
        allocate Functions::FN_TCS_FES::F_TCS_FES_06 to context.sts.orb.eclss.atcs.fes;
        allocate Functions::FN_TCS_GSE::F_TCS_GSE_01 to context.sts.orb.eclss.atcs.gse;
        allocate Functions::FN_TCS_GSE::F_TCS_GSE_02 to context.sts.orb.eclss.atcs.gse;
        allocate Functions::FN_TCS_GSE::F_TCS_GSE_03 to context.sts.orb.eclss.atcs.gse;
        allocate Functions::FN_TCS_GSE::F_TCS_GSE_04 to context.sts.orb.eclss.atcs.gse;
        allocate Functions::FN_TCS_GSE::F_TCS_GSE_05 to context.sts.orb.eclss.atcs.gse;
        allocate Functions::FN_TCS_HX::F_TCS_HX_01 to context.sts.orb.eclss.atcs.hx;
        allocate Functions::FN_TCS_HX::F_TCS_HX_02 to context.sts.orb.eclss.atcs.hx;
        allocate Functions::FN_TCS_HX::F_TCS_HX_03 to context.sts.orb.eclss.atcs.hx;
        allocate Functions::FN_TCS_HX::F_TCS_HX_04 to context.sts.orb.eclss.atcs.hx;
        allocate Functions::FN_TCS_HX::F_TCS_HX_05 to context.sts.orb.eclss.atcs.hx;
        allocate Functions::FN_TCS_NH3::F_TCS_NH3_01 to context.sts.orb.eclss.atcs.nh3;
        allocate Functions::FN_TCS_NH3::F_TCS_NH3_02 to context.sts.orb.eclss.atcs.nh3;
        allocate Functions::FN_TCS_NH3::F_TCS_NH3_03 to context.sts.orb.eclss.atcs.nh3;
        allocate Functions::FN_TCS_NH3::F_TCS_NH3_04 to context.sts.orb.eclss.atcs.nh3;
        allocate Functions::FN_TCS_NH3::F_TCS_NH3_05 to context.sts.orb.eclss.atcs.nh3;
        allocate Functions::FN_TCS_NH3::F_TCS_NH3_06 to context.sts.orb.eclss.atcs.nh3;
        allocate Functions::FN_TCS_RAD::F_TCS_RAD_01 to context.sts.orb.eclss.atcs.rad;
        allocate Functions::FN_TCS_RAD::F_TCS_RAD_02 to context.sts.orb.eclss.atcs.rad;
        allocate Functions::FN_TCS_RAD::F_TCS_RAD_03 to context.sts.orb.eclss.atcs.rad;
        allocate Functions::FN_TCS_RAD::F_TCS_RAD_04 to context.sts.orb.eclss.atcs.rad;
        allocate Functions::FN_TCS_RAD::F_TCS_RAD_05 to context.sts.orb.eclss.atcs.rad;
        allocate Functions::FN_ECL_CAB::F_ECL_CAB_01 to context.sts.orb.eclss.cab;
        allocate Functions::FN_ECL_CAB::F_ECL_CAB_02 to context.sts.orb.eclss.cab;
        allocate Functions::FN_ECL_CAB::F_ECL_CAB_03 to context.sts.orb.eclss.cab;
        allocate Functions::FN_ECL_CAB::F_ECL_CAB_04 to context.sts.orb.eclss.cab;
        allocate Functions::FN_ECL_CAB::F_ECL_CAB_05 to context.sts.orb.eclss.cab;
        allocate Functions::FN_ECL_FDS::F_ECL_FDS_01 to context.sts.orb.eclss.fds;
        allocate Functions::FN_ECL_FDS::F_ECL_FDS_02 to context.sts.orb.eclss.fds;
        allocate Functions::FN_ECL_FDS::F_ECL_FDS_03 to context.sts.orb.eclss.fds;
        allocate Functions::FN_ECL_FDS::F_ECL_FDS_04 to context.sts.orb.eclss.fds;
        allocate Functions::FN_ECL_FDS::F_ECL_FDS_05 to context.sts.orb.eclss.fds;
        allocate Functions::FN_ECL_FDS::F_ECL_FDS_06 to context.sts.orb.eclss.fds;
        allocate Functions::FN_ECL_FDS::F_ECL_FDS_07 to context.sts.orb.eclss.fds;
        allocate Functions::FN_ECL_FDS::F_ECL_FDS_08 to context.sts.orb.eclss.fds;
        allocate Functions::FN_ECL_FDS::F_ECL_FDS_09 to context.sts.orb.eclss.fds;
        allocate Functions::FN_ECL_FDS::F_ECL_FDS_10 to context.sts.orb.eclss.fds;
        allocate Functions::FN_ECL_FDS::F_ECL_FDS_11 to context.sts.orb.eclss.fds;
        allocate Functions::FN_ECL_FDS::F_ECL_FDS_12 to context.sts.orb.eclss.fds;
        allocate Functions::FN_ECL_FDS_ALM::F_ECL_FDS_ALM_01 to context.sts.orb.eclss.fds.alm;
        allocate Functions::FN_ECL_FDS_ALM::F_ECL_FDS_ALM_02 to context.sts.orb.eclss.fds.alm;
        allocate Functions::FN_ECL_FDS_ALM::F_ECL_FDS_ALM_03 to context.sts.orb.eclss.fds.alm;
        allocate Functions::FN_ECL_FDS_ALM::F_ECL_FDS_ALM_04 to context.sts.orb.eclss.fds.alm;
        allocate Functions::FN_ECL_FDS_ALM::F_ECL_FDS_ALM_05 to context.sts.orb.eclss.fds.alm;
        allocate Functions::FN_ECL_FDS_ALM::F_ECL_FDS_ALM_06 to context.sts.orb.eclss.fds.alm;
        allocate Functions::FN_ECL_FDS_ALM::F_ECL_FDS_ALM_07 to context.sts.orb.eclss.fds.alm;
        allocate Functions::FN_ECL_FDS_ALM::F_ECL_FDS_ALM_08 to context.sts.orb.eclss.fds.alm;
        allocate Functions::FN_ECL_FDS_ALM::F_ECL_FDS_ALM_09 to context.sts.orb.eclss.fds.alm;
        allocate Functions::FN_ECL_FDS_ALM::F_ECL_FDS_ALM_10 to context.sts.orb.eclss.fds.alm;
        allocate Functions::FN_ECL_FDS_ALM::F_ECL_FDS_ALM_11 to context.sts.orb.eclss.fds.alm;
        allocate Functions::FN_ECL_FDS_ALM::F_ECL_FDS_ALM_12 to context.sts.orb.eclss.fds.alm;
        allocate Functions::FN_ECL_FDS_DET::F_ECL_FDS_DET_01 to context.sts.orb.eclss.fds.det;
        allocate Functions::FN_ECL_FDS_DET::F_ECL_FDS_DET_02 to context.sts.orb.eclss.fds.det;
        allocate Functions::FN_ECL_FDS_DET::F_ECL_FDS_DET_03 to context.sts.orb.eclss.fds.det;
        allocate Functions::FN_ECL_FDS_DET::F_ECL_FDS_DET_04 to context.sts.orb.eclss.fds.det;
        allocate Functions::FN_ECL_FDS_DET::F_ECL_FDS_DET_05 to context.sts.orb.eclss.fds.det;
        allocate Functions::FN_ECL_FDS_DET::F_ECL_FDS_DET_06 to context.sts.orb.eclss.fds.det;
        allocate Functions::FN_ECL_FDS_DET::F_ECL_FDS_DET_07 to context.sts.orb.eclss.fds.det;
        allocate Functions::FN_ECL_FDS_DET::F_ECL_FDS_DET_08 to context.sts.orb.eclss.fds.det;
        allocate Functions::FN_ECL_FDS_DET::F_ECL_FDS_DET_09 to context.sts.orb.eclss.fds.det;
        allocate Functions::FN_ECL_FDS_DET::F_ECL_FDS_DET_10 to context.sts.orb.eclss.fds.det;
        allocate Functions::FN_ECL_FDS_DET::F_ECL_FDS_DET_11 to context.sts.orb.eclss.fds.det;
        allocate Functions::FN_ECL_FDS_DET::F_ECL_FDS_DET_12 to context.sts.orb.eclss.fds.det;
        allocate Functions::FN_ECL_FDS_FIX::F_ECL_FDS_FIX_01 to context.sts.orb.eclss.fds.fix;
        allocate Functions::FN_ECL_FDS_FIX::F_ECL_FDS_FIX_02 to context.sts.orb.eclss.fds.fix;
        allocate Functions::FN_ECL_FDS_FIX::F_ECL_FDS_FIX_03 to context.sts.orb.eclss.fds.fix;
        allocate Functions::FN_ECL_FDS_FIX::F_ECL_FDS_FIX_04 to context.sts.orb.eclss.fds.fix;
        allocate Functions::FN_ECL_FDS_FIX::F_ECL_FDS_FIX_05 to context.sts.orb.eclss.fds.fix;
        allocate Functions::FN_ECL_FDS_FIX::F_ECL_FDS_FIX_06 to context.sts.orb.eclss.fds.fix;
        allocate Functions::FN_ECL_FDS_FIX::F_ECL_FDS_FIX_07 to context.sts.orb.eclss.fds.fix;
        allocate Functions::FN_ECL_FDS_FIX::F_ECL_FDS_FIX_08 to context.sts.orb.eclss.fds.fix;
        allocate Functions::FN_ECL_FDS_FIX::F_ECL_FDS_FIX_09 to context.sts.orb.eclss.fds.fix;
        allocate Functions::FN_ECL_FDS_FIX::F_ECL_FDS_FIX_10 to context.sts.orb.eclss.fds.fix;
        allocate Functions::FN_ECL_FDS_FIX::F_ECL_FDS_FIX_11 to context.sts.orb.eclss.fds.fix;
        allocate Functions::FN_ECL_FDS_FIX::F_ECL_FDS_FIX_12 to context.sts.orb.eclss.fds.fix;
        allocate Functions::FN_ECL_FDS_OPS::F_ECL_FDS_OPS_01 to context.sts.orb.eclss.fds.ops;
        allocate Functions::FN_ECL_FDS_OPS::F_ECL_FDS_OPS_02 to context.sts.orb.eclss.fds.ops;
        allocate Functions::FN_ECL_FDS_OPS::F_ECL_FDS_OPS_03 to context.sts.orb.eclss.fds.ops;
        allocate Functions::FN_ECL_FDS_OPS::F_ECL_FDS_OPS_04 to context.sts.orb.eclss.fds.ops;
        allocate Functions::FN_ECL_FDS_OPS::F_ECL_FDS_OPS_05 to context.sts.orb.eclss.fds.ops;
        allocate Functions::FN_ECL_FDS_OPS::F_ECL_FDS_OPS_06 to context.sts.orb.eclss.fds.ops;
        allocate Functions::FN_ECL_FDS_OPS::F_ECL_FDS_OPS_07 to context.sts.orb.eclss.fds.ops;
        allocate Functions::FN_ECL_FDS_OPS::F_ECL_FDS_OPS_08 to context.sts.orb.eclss.fds.ops;
        allocate Functions::FN_ECL_FDS_OPS::F_ECL_FDS_OPS_09 to context.sts.orb.eclss.fds.ops;
        allocate Functions::FN_ECL_FDS_OPS::F_ECL_FDS_OPS_10 to context.sts.orb.eclss.fds.ops;
        allocate Functions::FN_ECL_FDS_OPS::F_ECL_FDS_OPS_11 to context.sts.orb.eclss.fds.ops;
        allocate Functions::FN_ECL_FDS_OPS::F_ECL_FDS_OPS_12 to context.sts.orb.eclss.fds.ops;
        allocate Functions::FN_ECL_FDS_PFE::F_ECL_FDS_PFE_01 to context.sts.orb.eclss.fds.pfe;
        allocate Functions::FN_ECL_FDS_PFE::F_ECL_FDS_PFE_02 to context.sts.orb.eclss.fds.pfe;
        allocate Functions::FN_ECL_FDS_PFE::F_ECL_FDS_PFE_03 to context.sts.orb.eclss.fds.pfe;
        allocate Functions::FN_ECL_FDS_PFE::F_ECL_FDS_PFE_04 to context.sts.orb.eclss.fds.pfe;
        allocate Functions::FN_ECL_FDS_PFE::F_ECL_FDS_PFE_05 to context.sts.orb.eclss.fds.pfe;
        allocate Functions::FN_ECL_FDS_PFE::F_ECL_FDS_PFE_06 to context.sts.orb.eclss.fds.pfe;
        allocate Functions::FN_ECL_FDS_PFE::F_ECL_FDS_PFE_07 to context.sts.orb.eclss.fds.pfe;
        allocate Functions::FN_ECL_FDS_PFE::F_ECL_FDS_PFE_08 to context.sts.orb.eclss.fds.pfe;
        allocate Functions::FN_ECL_FDS_PFE::F_ECL_FDS_PFE_09 to context.sts.orb.eclss.fds.pfe;
        allocate Functions::FN_ECL_FDS_PFE::F_ECL_FDS_PFE_10 to context.sts.orb.eclss.fds.pfe;
        allocate Functions::FN_ECL_H2O::F_ECL_H2O_01 to context.sts.orb.eclss.h2o;
        allocate Functions::FN_ECL_H2O::F_ECL_H2O_02 to context.sts.orb.eclss.h2o;
        allocate Functions::FN_ECL_H2O::F_ECL_H2O_03 to context.sts.orb.eclss.h2o;
        allocate Functions::FN_ECL_H2O::F_ECL_H2O_04 to context.sts.orb.eclss.h2o;
        allocate Functions::FN_ECL_H2O::F_ECL_H2O_05 to context.sts.orb.eclss.h2o;
        allocate Functions::FN_ECL_H2O::F_ECL_H2O_06 to context.sts.orb.eclss.h2o;
        allocate Functions::FN_ECL_H2O::F_ECL_H2O_07 to context.sts.orb.eclss.h2o;
        allocate Functions::FN_ECL_H2O::F_ECL_H2O_08 to context.sts.orb.eclss.h2o;
        allocate Functions::FN_ECL_H2O::F_ECL_H2O_09 to context.sts.orb.eclss.h2o;
        allocate Functions::FN_ECL_H2O_DMP::F_ECL_H2O_DMP_01 to context.sts.orb.eclss.h2o.dmp;
        allocate Functions::FN_ECL_H2O_DMP::F_ECL_H2O_DMP_02 to context.sts.orb.eclss.h2o.dmp;
        allocate Functions::FN_ECL_H2O_DMP::F_ECL_H2O_DMP_03 to context.sts.orb.eclss.h2o.dmp;
        allocate Functions::FN_ECL_H2O_DMP::F_ECL_H2O_DMP_04 to context.sts.orb.eclss.h2o.dmp;
        allocate Functions::FN_ECL_H2O_DMP::F_ECL_H2O_DMP_05 to context.sts.orb.eclss.h2o.dmp;
        allocate Functions::FN_ECL_H2O_DMP::F_ECL_H2O_DMP_06 to context.sts.orb.eclss.h2o.dmp;
        allocate Functions::FN_ECL_H2O_DMP::F_ECL_H2O_DMP_07 to context.sts.orb.eclss.h2o.dmp;
        allocate Functions::FN_ECL_H2O_DMP::F_ECL_H2O_DMP_08 to context.sts.orb.eclss.h2o.dmp;
        allocate Functions::FN_ECL_H2O_DMP::F_ECL_H2O_DMP_09 to context.sts.orb.eclss.h2o.dmp;
        allocate Functions::FN_ECL_H2O_DMP::F_ECL_H2O_DMP_10 to context.sts.orb.eclss.h2o.dmp;
        allocate Functions::FN_ECL_H2O_DMP::F_ECL_H2O_DMP_11 to context.sts.orb.eclss.h2o.dmp;
        allocate Functions::FN_ECL_H2O_DMP::F_ECL_H2O_DMP_12 to context.sts.orb.eclss.h2o.dmp;
        allocate Functions::FN_ECL_H2O_FCW::F_ECL_H2O_FCW_01 to context.sts.orb.eclss.h2o.fcw;
        allocate Functions::FN_ECL_H2O_FCW::F_ECL_H2O_FCW_02 to context.sts.orb.eclss.h2o.fcw;
        allocate Functions::FN_ECL_H2O_FCW::F_ECL_H2O_FCW_03 to context.sts.orb.eclss.h2o.fcw;
        allocate Functions::FN_ECL_H2O_FCW::F_ECL_H2O_FCW_04 to context.sts.orb.eclss.h2o.fcw;
        allocate Functions::FN_ECL_H2O_FCW::F_ECL_H2O_FCW_05 to context.sts.orb.eclss.h2o.fcw;
        allocate Functions::FN_ECL_H2O_FCW::F_ECL_H2O_FCW_06 to context.sts.orb.eclss.h2o.fcw;
        allocate Functions::FN_ECL_H2O_FCW::F_ECL_H2O_FCW_07 to context.sts.orb.eclss.h2o.fcw;
        allocate Functions::FN_ECL_H2O_FCW::F_ECL_H2O_FCW_08 to context.sts.orb.eclss.h2o.fcw;
        allocate Functions::FN_ECL_H2O_FCW::F_ECL_H2O_FCW_09 to context.sts.orb.eclss.h2o.fcw;
        allocate Functions::FN_ECL_H2O_FCW::F_ECL_H2O_FCW_10 to context.sts.orb.eclss.h2o.fcw;
        allocate Functions::FN_ECL_H2O_FCW::F_ECL_H2O_FCW_11 to context.sts.orb.eclss.h2o.fcw;
        allocate Functions::FN_ECL_H2O_FCW::F_ECL_H2O_FCW_12 to context.sts.orb.eclss.h2o.fcw;
        allocate Functions::FN_ECL_H2O_GAL::F_ECL_H2O_GAL_01 to context.sts.orb.eclss.h2o.gal;
        allocate Functions::FN_ECL_H2O_GAL::F_ECL_H2O_GAL_02 to context.sts.orb.eclss.h2o.gal;
        allocate Functions::FN_ECL_H2O_GAL::F_ECL_H2O_GAL_03 to context.sts.orb.eclss.h2o.gal;
        allocate Functions::FN_ECL_H2O_GAL::F_ECL_H2O_GAL_04 to context.sts.orb.eclss.h2o.gal;
        allocate Functions::FN_ECL_H2O_GAL::F_ECL_H2O_GAL_05 to context.sts.orb.eclss.h2o.gal;
        allocate Functions::FN_ECL_H2O_GAL::F_ECL_H2O_GAL_06 to context.sts.orb.eclss.h2o.gal;
        allocate Functions::FN_ECL_H2O_GAL::F_ECL_H2O_GAL_07 to context.sts.orb.eclss.h2o.gal;
        allocate Functions::FN_ECL_H2O_GAL::F_ECL_H2O_GAL_08 to context.sts.orb.eclss.h2o.gal;
        allocate Functions::FN_ECL_H2O_GAL::F_ECL_H2O_GAL_09 to context.sts.orb.eclss.h2o.gal;
        allocate Functions::FN_ECL_H2O_GAL::F_ECL_H2O_GAL_10 to context.sts.orb.eclss.h2o.gal;
        allocate Functions::FN_ECL_H2O_GAL::F_ECL_H2O_GAL_11 to context.sts.orb.eclss.h2o.gal;
        allocate Functions::FN_ECL_H2O_GAL::F_ECL_H2O_GAL_12 to context.sts.orb.eclss.h2o.gal;
        allocate Functions::FN_ECL_H2O_PRS::F_ECL_H2O_PRS_01 to context.sts.orb.eclss.h2o.prs;
        allocate Functions::FN_ECL_H2O_PRS::F_ECL_H2O_PRS_02 to context.sts.orb.eclss.h2o.prs;
        allocate Functions::FN_ECL_H2O_PRS::F_ECL_H2O_PRS_03 to context.sts.orb.eclss.h2o.prs;
        allocate Functions::FN_ECL_H2O_PRS::F_ECL_H2O_PRS_04 to context.sts.orb.eclss.h2o.prs;
        allocate Functions::FN_ECL_H2O_PRS::F_ECL_H2O_PRS_05 to context.sts.orb.eclss.h2o.prs;
        allocate Functions::FN_ECL_H2O_PRS::F_ECL_H2O_PRS_06 to context.sts.orb.eclss.h2o.prs;
        allocate Functions::FN_ECL_H2O_PRS::F_ECL_H2O_PRS_07 to context.sts.orb.eclss.h2o.prs;
        allocate Functions::FN_ECL_H2O_PRS::F_ECL_H2O_PRS_08 to context.sts.orb.eclss.h2o.prs;
        allocate Functions::FN_ECL_H2O_PRS::F_ECL_H2O_PRS_09 to context.sts.orb.eclss.h2o.prs;
        allocate Functions::FN_ECL_H2O_PRS::F_ECL_H2O_PRS_10 to context.sts.orb.eclss.h2o.prs;
        allocate Functions::FN_ECL_H2O_PRS::F_ECL_H2O_PRS_11 to context.sts.orb.eclss.h2o.prs;
        allocate Functions::FN_ECL_H2O_PRS::F_ECL_H2O_PRS_12 to context.sts.orb.eclss.h2o.prs;
        allocate Functions::FN_ECL_H2O_SPL::F_ECL_H2O_SPL_01 to context.sts.orb.eclss.h2o.spl;
        allocate Functions::FN_ECL_H2O_SPL::F_ECL_H2O_SPL_02 to context.sts.orb.eclss.h2o.spl;
        allocate Functions::FN_ECL_H2O_SPL::F_ECL_H2O_SPL_03 to context.sts.orb.eclss.h2o.spl;
        allocate Functions::FN_ECL_H2O_SPL::F_ECL_H2O_SPL_04 to context.sts.orb.eclss.h2o.spl;
        allocate Functions::FN_ECL_H2O_SPL::F_ECL_H2O_SPL_05 to context.sts.orb.eclss.h2o.spl;
        allocate Functions::FN_ECL_H2O_SPL::F_ECL_H2O_SPL_06 to context.sts.orb.eclss.h2o.spl;
        allocate Functions::FN_ECL_H2O_SPL::F_ECL_H2O_SPL_07 to context.sts.orb.eclss.h2o.spl;
        allocate Functions::FN_ECL_H2O_SPL::F_ECL_H2O_SPL_08 to context.sts.orb.eclss.h2o.spl;
        allocate Functions::FN_ECL_H2O_SPL::F_ECL_H2O_SPL_09 to context.sts.orb.eclss.h2o.spl;
        allocate Functions::FN_ECL_H2O_SPL::F_ECL_H2O_SPL_10 to context.sts.orb.eclss.h2o.spl;
        allocate Functions::FN_ECL_H2O_SPL::F_ECL_H2O_SPL_11 to context.sts.orb.eclss.h2o.spl;
        allocate Functions::FN_ECL_H2O_SPL::F_ECL_H2O_SPL_12 to context.sts.orb.eclss.h2o.spl;
        allocate Functions::FN_ECL_H2O_WST::F_ECL_H2O_WST_01 to context.sts.orb.eclss.h2o.wst;
        allocate Functions::FN_ECL_H2O_WST::F_ECL_H2O_WST_02 to context.sts.orb.eclss.h2o.wst;
        allocate Functions::FN_ECL_H2O_WST::F_ECL_H2O_WST_03 to context.sts.orb.eclss.h2o.wst;
        allocate Functions::FN_ECL_H2O_WST::F_ECL_H2O_WST_04 to context.sts.orb.eclss.h2o.wst;
        allocate Functions::FN_ECL_H2O_WST::F_ECL_H2O_WST_05 to context.sts.orb.eclss.h2o.wst;
        allocate Functions::FN_ECL_H2O_WST::F_ECL_H2O_WST_06 to context.sts.orb.eclss.h2o.wst;
        allocate Functions::FN_ECL_H2O_WST::F_ECL_H2O_WST_07 to context.sts.orb.eclss.h2o.wst;
        allocate Functions::FN_ECL_H2O_WST::F_ECL_H2O_WST_08 to context.sts.orb.eclss.h2o.wst;
        allocate Functions::FN_ECL_H2O_WST::F_ECL_H2O_WST_09 to context.sts.orb.eclss.h2o.wst;
        allocate Functions::FN_ECL_H2O_WST::F_ECL_H2O_WST_10 to context.sts.orb.eclss.h2o.wst;
        allocate Functions::FN_ECL_H2O_WST::F_ECL_H2O_WST_11 to context.sts.orb.eclss.h2o.wst;
        allocate Functions::FN_ECL_H2O_WST::F_ECL_H2O_WST_12 to context.sts.orb.eclss.h2o.wst;
        allocate Functions::FN_ECL_PCS::F_ECL_PCS_01 to context.sts.orb.eclss.pcs;
        allocate Functions::FN_ECL_PCS::F_ECL_PCS_02 to context.sts.orb.eclss.pcs;
        allocate Functions::FN_ECL_PCS::F_ECL_PCS_03 to context.sts.orb.eclss.pcs;
        allocate Functions::FN_ECL_PCS::F_ECL_PCS_04 to context.sts.orb.eclss.pcs;
        allocate Functions::FN_ECL_PCS::F_ECL_PCS_05 to context.sts.orb.eclss.pcs;
        allocate Functions::FN_ECL_PCS::F_ECL_PCS_06 to context.sts.orb.eclss.pcs;
        allocate Functions::FN_ECL_PCS::F_ECL_PCS_07 to context.sts.orb.eclss.pcs;
        allocate Functions::FN_ECL_PCS::F_ECL_PCS_08 to context.sts.orb.eclss.pcs;
        allocate Functions::FN_ECL_PCS::F_ECL_PCS_09 to context.sts.orb.eclss.pcs;
        allocate Functions::FN_ECL_PCS::F_ECL_PCS_10 to context.sts.orb.eclss.pcs;
        allocate Functions::FN_ECL_PCS::F_ECL_PCS_11 to context.sts.orb.eclss.pcs;
        allocate Functions::FN_ECL_PCS_MNF::F_ECL_PCS_MNF_01 to context.sts.orb.eclss.pcs.mnf;
        allocate Functions::FN_ECL_PCS_MNF::F_ECL_PCS_MNF_02 to context.sts.orb.eclss.pcs.mnf;
        allocate Functions::FN_ECL_PCS_MNF::F_ECL_PCS_MNF_03 to context.sts.orb.eclss.pcs.mnf;
        allocate Functions::FN_ECL_PCS_MNF::F_ECL_PCS_MNF_04 to context.sts.orb.eclss.pcs.mnf;
        allocate Functions::FN_ECL_PCS_MNF::F_ECL_PCS_MNF_05 to context.sts.orb.eclss.pcs.mnf;
        allocate Functions::FN_ECL_PCS_MNF::F_ECL_PCS_MNF_06 to context.sts.orb.eclss.pcs.mnf;
        allocate Functions::FN_ECL_PCS_MNF::F_ECL_PCS_MNF_07 to context.sts.orb.eclss.pcs.mnf;
        allocate Functions::FN_ECL_PCS_MNF::F_ECL_PCS_MNF_08 to context.sts.orb.eclss.pcs.mnf;
        allocate Functions::FN_ECL_PCS_MNF::F_ECL_PCS_MNF_09 to context.sts.orb.eclss.pcs.mnf;
        allocate Functions::FN_ECL_PCS_MNF::F_ECL_PCS_MNF_10 to context.sts.orb.eclss.pcs.mnf;
        allocate Functions::FN_ECL_PCS_MNF::F_ECL_PCS_MNF_11 to context.sts.orb.eclss.pcs.mnf;
        allocate Functions::FN_ECL_PCS_MNF::F_ECL_PCS_MNF_12 to context.sts.orb.eclss.pcs.mnf;
        allocate Functions::FN_ECL_PCS_MON::F_ECL_PCS_MON_01 to context.sts.orb.eclss.pcs.mon;
        allocate Functions::FN_ECL_PCS_MON::F_ECL_PCS_MON_02 to context.sts.orb.eclss.pcs.mon;
        allocate Functions::FN_ECL_PCS_MON::F_ECL_PCS_MON_03 to context.sts.orb.eclss.pcs.mon;
        allocate Functions::FN_ECL_PCS_MON::F_ECL_PCS_MON_04 to context.sts.orb.eclss.pcs.mon;
        allocate Functions::FN_ECL_PCS_MON::F_ECL_PCS_MON_05 to context.sts.orb.eclss.pcs.mon;
        allocate Functions::FN_ECL_PCS_MON::F_ECL_PCS_MON_06 to context.sts.orb.eclss.pcs.mon;
        allocate Functions::FN_ECL_PCS_MON::F_ECL_PCS_MON_07 to context.sts.orb.eclss.pcs.mon;
        allocate Functions::FN_ECL_PCS_MON::F_ECL_PCS_MON_08 to context.sts.orb.eclss.pcs.mon;
        allocate Functions::FN_ECL_PCS_MON::F_ECL_PCS_MON_09 to context.sts.orb.eclss.pcs.mon;
        allocate Functions::FN_ECL_PCS_MON::F_ECL_PCS_MON_10 to context.sts.orb.eclss.pcs.mon;
        allocate Functions::FN_ECL_PCS_MON::F_ECL_PCS_MON_11 to context.sts.orb.eclss.pcs.mon;
        allocate Functions::FN_ECL_PCS_MON::F_ECL_PCS_MON_12 to context.sts.orb.eclss.pcs.mon;
        allocate Functions::FN_ECL_PCS_N2S::F_ECL_PCS_N2S_01 to context.sts.orb.eclss.pcs.n2s;
        allocate Functions::FN_ECL_PCS_N2S::F_ECL_PCS_N2S_02 to context.sts.orb.eclss.pcs.n2s;
        allocate Functions::FN_ECL_PCS_N2S::F_ECL_PCS_N2S_03 to context.sts.orb.eclss.pcs.n2s;
        allocate Functions::FN_ECL_PCS_N2S::F_ECL_PCS_N2S_04 to context.sts.orb.eclss.pcs.n2s;
        allocate Functions::FN_ECL_PCS_N2S::F_ECL_PCS_N2S_05 to context.sts.orb.eclss.pcs.n2s;
        allocate Functions::FN_ECL_PCS_N2S::F_ECL_PCS_N2S_06 to context.sts.orb.eclss.pcs.n2s;
        allocate Functions::FN_ECL_PCS_N2S::F_ECL_PCS_N2S_07 to context.sts.orb.eclss.pcs.n2s;
        allocate Functions::FN_ECL_PCS_N2S::F_ECL_PCS_N2S_08 to context.sts.orb.eclss.pcs.n2s;
        allocate Functions::FN_ECL_PCS_N2S::F_ECL_PCS_N2S_09 to context.sts.orb.eclss.pcs.n2s;
        allocate Functions::FN_ECL_PCS_N2S::F_ECL_PCS_N2S_10 to context.sts.orb.eclss.pcs.n2s;
        allocate Functions::FN_ECL_PCS_N2S::F_ECL_PCS_N2S_11 to context.sts.orb.eclss.pcs.n2s;
        allocate Functions::FN_ECL_PCS_N2S::F_ECL_PCS_N2S_12 to context.sts.orb.eclss.pcs.n2s;
        allocate Functions::FN_ECL_PCS_O2S::F_ECL_PCS_O2S_01 to context.sts.orb.eclss.pcs.o2s;
        allocate Functions::FN_ECL_PCS_O2S::F_ECL_PCS_O2S_02 to context.sts.orb.eclss.pcs.o2s;
        allocate Functions::FN_ECL_PCS_O2S::F_ECL_PCS_O2S_03 to context.sts.orb.eclss.pcs.o2s;
        allocate Functions::FN_ECL_PCS_O2S::F_ECL_PCS_O2S_04 to context.sts.orb.eclss.pcs.o2s;
        allocate Functions::FN_ECL_PCS_O2S::F_ECL_PCS_O2S_05 to context.sts.orb.eclss.pcs.o2s;
        allocate Functions::FN_ECL_PCS_O2S::F_ECL_PCS_O2S_06 to context.sts.orb.eclss.pcs.o2s;
        allocate Functions::FN_ECL_PCS_O2S::F_ECL_PCS_O2S_07 to context.sts.orb.eclss.pcs.o2s;
        allocate Functions::FN_ECL_PCS_O2S::F_ECL_PCS_O2S_08 to context.sts.orb.eclss.pcs.o2s;
        allocate Functions::FN_ECL_PCS_O2S::F_ECL_PCS_O2S_09 to context.sts.orb.eclss.pcs.o2s;
        allocate Functions::FN_ECL_PCS_O2S::F_ECL_PCS_O2S_10 to context.sts.orb.eclss.pcs.o2s;
        allocate Functions::FN_ECL_PCS_O2S::F_ECL_PCS_O2S_11 to context.sts.orb.eclss.pcs.o2s;
        allocate Functions::FN_ECL_PCS_O2S::F_ECL_PCS_O2S_12 to context.sts.orb.eclss.pcs.o2s;
        allocate Functions::FN_ECL_PCS_OPS::F_ECL_PCS_OPS_01 to context.sts.orb.eclss.pcs.ops;
        allocate Functions::FN_ECL_PCS_OPS::F_ECL_PCS_OPS_02 to context.sts.orb.eclss.pcs.ops;
        allocate Functions::FN_ECL_PCS_OPS::F_ECL_PCS_OPS_03 to context.sts.orb.eclss.pcs.ops;
        allocate Functions::FN_ECL_PCS_OPS::F_ECL_PCS_OPS_04 to context.sts.orb.eclss.pcs.ops;
        allocate Functions::FN_ECL_PCS_OPS::F_ECL_PCS_OPS_05 to context.sts.orb.eclss.pcs.ops;
        allocate Functions::FN_ECL_PCS_OPS::F_ECL_PCS_OPS_06 to context.sts.orb.eclss.pcs.ops;
        allocate Functions::FN_ECL_PCS_OPS::F_ECL_PCS_OPS_07 to context.sts.orb.eclss.pcs.ops;
        allocate Functions::FN_ECL_PCS_OPS::F_ECL_PCS_OPS_08 to context.sts.orb.eclss.pcs.ops;
        allocate Functions::FN_ECL_PCS_OPS::F_ECL_PCS_OPS_09 to context.sts.orb.eclss.pcs.ops;
        allocate Functions::FN_ECL_PCS_OPS::F_ECL_PCS_OPS_10 to context.sts.orb.eclss.pcs.ops;
        allocate Functions::FN_ECL_PCS_OPS::F_ECL_PCS_OPS_11 to context.sts.orb.eclss.pcs.ops;
        allocate Functions::FN_ECL_PCS_OPS::F_ECL_PCS_OPS_12 to context.sts.orb.eclss.pcs.ops;
        allocate Functions::FN_ECL_PCS_RLF::F_ECL_PCS_RLF_01 to context.sts.orb.eclss.pcs.rlf;
        allocate Functions::FN_ECL_PCS_RLF::F_ECL_PCS_RLF_02 to context.sts.orb.eclss.pcs.rlf;
        allocate Functions::FN_ECL_PCS_RLF::F_ECL_PCS_RLF_03 to context.sts.orb.eclss.pcs.rlf;
        allocate Functions::FN_ECL_PCS_RLF::F_ECL_PCS_RLF_04 to context.sts.orb.eclss.pcs.rlf;
        allocate Functions::FN_ECL_PCS_RLF::F_ECL_PCS_RLF_05 to context.sts.orb.eclss.pcs.rlf;
        allocate Functions::FN_ECL_PCS_RLF::F_ECL_PCS_RLF_06 to context.sts.orb.eclss.pcs.rlf;
        allocate Functions::FN_ECL_PCS_RLF::F_ECL_PCS_RLF_07 to context.sts.orb.eclss.pcs.rlf;
        allocate Functions::FN_ECL_PCS_RLF::F_ECL_PCS_RLF_08 to context.sts.orb.eclss.pcs.rlf;
        allocate Functions::FN_ECL_PCS_RLF::F_ECL_PCS_RLF_09 to context.sts.orb.eclss.pcs.rlf;
        allocate Functions::FN_ECL_PCS_RLF::F_ECL_PCS_RLF_10 to context.sts.orb.eclss.pcs.rlf;
        allocate Functions::FN_ECL_PCS_RLF::F_ECL_PCS_RLF_11 to context.sts.orb.eclss.pcs.rlf;
        allocate Functions::FN_ECL_WCS::F_ECL_WCS_01 to context.sts.orb.eclss.wcs;
        allocate Functions::FN_ECL_WCS::F_ECL_WCS_02 to context.sts.orb.eclss.wcs;
        allocate Functions::FN_ECL_WCS::F_ECL_WCS_03 to context.sts.orb.eclss.wcs;
        allocate Functions::FN_ECL_WCS::F_ECL_WCS_04 to context.sts.orb.eclss.wcs;
        allocate Functions::FN_ECL_WCS::F_ECL_WCS_05 to context.sts.orb.eclss.wcs;
        allocate Functions::FN_ECL_WCS::F_ECL_WCS_06 to context.sts.orb.eclss.wcs;
        allocate Functions::FN_ECL_WCS::F_ECL_WCS_07 to context.sts.orb.eclss.wcs;
        allocate Functions::FN_ECL_WCS::F_ECL_WCS_08 to context.sts.orb.eclss.wcs;
        allocate Functions::FN_ECL_WCS::F_ECL_WCS_09 to context.sts.orb.eclss.wcs;
        allocate Functions::FN_ECL_WCS_CMD::F_ECL_WCS_CMD_01 to context.sts.orb.eclss.wcs.cmd;
        allocate Functions::FN_ECL_WCS_CMD::F_ECL_WCS_CMD_02 to context.sts.orb.eclss.wcs.cmd;
        allocate Functions::FN_ECL_WCS_CMD::F_ECL_WCS_CMD_03 to context.sts.orb.eclss.wcs.cmd;
        allocate Functions::FN_ECL_WCS_CMD::F_ECL_WCS_CMD_04 to context.sts.orb.eclss.wcs.cmd;
        allocate Functions::FN_ECL_WCS_CMD::F_ECL_WCS_CMD_05 to context.sts.orb.eclss.wcs.cmd;
        allocate Functions::FN_ECL_WCS_CMD::F_ECL_WCS_CMD_06 to context.sts.orb.eclss.wcs.cmd;
        allocate Functions::FN_ECL_WCS_CMD::F_ECL_WCS_CMD_07 to context.sts.orb.eclss.wcs.cmd;
        allocate Functions::FN_ECL_WCS_CMD::F_ECL_WCS_CMD_08 to context.sts.orb.eclss.wcs.cmd;
        allocate Functions::FN_ECL_WCS_CMD::F_ECL_WCS_CMD_09 to context.sts.orb.eclss.wcs.cmd;
        allocate Functions::FN_ECL_WCS_CMD::F_ECL_WCS_CMD_10 to context.sts.orb.eclss.wcs.cmd;
        allocate Functions::FN_ECL_WCS_CMD::F_ECL_WCS_CMD_11 to context.sts.orb.eclss.wcs.cmd;
        allocate Functions::FN_ECL_WCS_CMD::F_ECL_WCS_CMD_12 to context.sts.orb.eclss.wcs.cmd;
        allocate Functions::FN_ECL_WCS_FSP::F_ECL_WCS_FSP_01 to context.sts.orb.eclss.wcs.fsp;
        allocate Functions::FN_ECL_WCS_FSP::F_ECL_WCS_FSP_02 to context.sts.orb.eclss.wcs.fsp;
        allocate Functions::FN_ECL_WCS_FSP::F_ECL_WCS_FSP_03 to context.sts.orb.eclss.wcs.fsp;
        allocate Functions::FN_ECL_WCS_FSP::F_ECL_WCS_FSP_04 to context.sts.orb.eclss.wcs.fsp;
        allocate Functions::FN_ECL_WCS_FSP::F_ECL_WCS_FSP_05 to context.sts.orb.eclss.wcs.fsp;
        allocate Functions::FN_ECL_WCS_FSP::F_ECL_WCS_FSP_06 to context.sts.orb.eclss.wcs.fsp;
        allocate Functions::FN_ECL_WCS_FSP::F_ECL_WCS_FSP_07 to context.sts.orb.eclss.wcs.fsp;
        allocate Functions::FN_ECL_WCS_FSP::F_ECL_WCS_FSP_08 to context.sts.orb.eclss.wcs.fsp;
        allocate Functions::FN_ECL_WCS_FSP::F_ECL_WCS_FSP_09 to context.sts.orb.eclss.wcs.fsp;
        allocate Functions::FN_ECL_WCS_FSP::F_ECL_WCS_FSP_10 to context.sts.orb.eclss.wcs.fsp;
        allocate Functions::FN_ECL_WCS_FSP::F_ECL_WCS_FSP_11 to context.sts.orb.eclss.wcs.fsp;
        allocate Functions::FN_ECL_WCS_FSP::F_ECL_WCS_FSP_12 to context.sts.orb.eclss.wcs.fsp;
        allocate Functions::FN_ECL_WCS_OPS::F_ECL_WCS_OPS_01 to context.sts.orb.eclss.wcs.ops;
        allocate Functions::FN_ECL_WCS_OPS::F_ECL_WCS_OPS_02 to context.sts.orb.eclss.wcs.ops;
        allocate Functions::FN_ECL_WCS_OPS::F_ECL_WCS_OPS_03 to context.sts.orb.eclss.wcs.ops;
        allocate Functions::FN_ECL_WCS_OPS::F_ECL_WCS_OPS_04 to context.sts.orb.eclss.wcs.ops;
        allocate Functions::FN_ECL_WCS_OPS::F_ECL_WCS_OPS_05 to context.sts.orb.eclss.wcs.ops;
        allocate Functions::FN_ECL_WCS_OPS::F_ECL_WCS_OPS_06 to context.sts.orb.eclss.wcs.ops;
        allocate Functions::FN_ECL_WCS_OPS::F_ECL_WCS_OPS_07 to context.sts.orb.eclss.wcs.ops;
        allocate Functions::FN_ECL_WCS_OPS::F_ECL_WCS_OPS_08 to context.sts.orb.eclss.wcs.ops;
        allocate Functions::FN_ECL_WCS_OPS::F_ECL_WCS_OPS_09 to context.sts.orb.eclss.wcs.ops;
        allocate Functions::FN_ECL_WCS_OPS::F_ECL_WCS_OPS_10 to context.sts.orb.eclss.wcs.ops;
        allocate Functions::FN_ECL_WCS_OPS::F_ECL_WCS_OPS_11 to context.sts.orb.eclss.wcs.ops;
        allocate Functions::FN_ECL_WCS_OPS::F_ECL_WCS_OPS_12 to context.sts.orb.eclss.wcs.ops;
        allocate Functions::FN_ECL_WCS_URN::F_ECL_WCS_URN_01 to context.sts.orb.eclss.wcs.urn;
        allocate Functions::FN_ECL_WCS_URN::F_ECL_WCS_URN_02 to context.sts.orb.eclss.wcs.urn;
        allocate Functions::FN_ECL_WCS_URN::F_ECL_WCS_URN_03 to context.sts.orb.eclss.wcs.urn;
        allocate Functions::FN_ECL_WCS_URN::F_ECL_WCS_URN_04 to context.sts.orb.eclss.wcs.urn;
        allocate Functions::FN_ECL_WCS_URN::F_ECL_WCS_URN_05 to context.sts.orb.eclss.wcs.urn;
        allocate Functions::FN_ECL_WCS_URN::F_ECL_WCS_URN_06 to context.sts.orb.eclss.wcs.urn;
        allocate Functions::FN_ECL_WCS_URN::F_ECL_WCS_URN_07 to context.sts.orb.eclss.wcs.urn;
        allocate Functions::FN_ECL_WCS_URN::F_ECL_WCS_URN_08 to context.sts.orb.eclss.wcs.urn;
        allocate Functions::FN_ECL_WCS_URN::F_ECL_WCS_URN_09 to context.sts.orb.eclss.wcs.urn;
        allocate Functions::FN_ECL_WCS_URN::F_ECL_WCS_URN_10 to context.sts.orb.eclss.wcs.urn;
        allocate Functions::FN_ECL_WCS_URN::F_ECL_WCS_URN_11 to context.sts.orb.eclss.wcs.urn;
        allocate Functions::FN_ECL_WCS_URN::F_ECL_WCS_URN_12 to context.sts.orb.eclss.wcs.urn;
        allocate Functions::FN_ECL_WCS_VAC::F_ECL_WCS_VAC_01 to context.sts.orb.eclss.wcs.vac;
        allocate Functions::FN_ECL_WCS_VAC::F_ECL_WCS_VAC_02 to context.sts.orb.eclss.wcs.vac;
        allocate Functions::FN_ECL_WCS_VAC::F_ECL_WCS_VAC_03 to context.sts.orb.eclss.wcs.vac;
        allocate Functions::FN_ECL_WCS_VAC::F_ECL_WCS_VAC_04 to context.sts.orb.eclss.wcs.vac;
        allocate Functions::FN_ECL_WCS_VAC::F_ECL_WCS_VAC_05 to context.sts.orb.eclss.wcs.vac;
        allocate Functions::FN_ECL_WCS_VAC::F_ECL_WCS_VAC_06 to context.sts.orb.eclss.wcs.vac;
        allocate Functions::FN_ECL_WCS_VAC::F_ECL_WCS_VAC_07 to context.sts.orb.eclss.wcs.vac;
        allocate Functions::FN_ECL_WCS_VAC::F_ECL_WCS_VAC_08 to context.sts.orb.eclss.wcs.vac;
        allocate Functions::FN_ECL_WCS_VAC::F_ECL_WCS_VAC_09 to context.sts.orb.eclss.wcs.vac;
        allocate Functions::FN_ECL_WCS_VAC::F_ECL_WCS_VAC_10 to context.sts.orb.eclss.wcs.vac;
        allocate Functions::FN_ECL_WCS_VAC::F_ECL_WCS_VAC_11 to context.sts.orb.eclss.wcs.vac;
        allocate Functions::FN_ECL_WCS_VAC::F_ECL_WCS_VAC_12 to context.sts.orb.eclss.wcs.vac;
        allocate Functions::FN_EPS::F_EPS_01 to context.sts.orb.eps;
        allocate Functions::FN_EPS::F_EPS_02 to context.sts.orb.eps;
        allocate Functions::FN_EPS::F_EPS_03 to context.sts.orb.eps;
        allocate Functions::FN_EPS::F_EPS_04 to context.sts.orb.eps;
        allocate Functions::FN_EPS::F_EPS_05 to context.sts.orb.eps;
        allocate Functions::FN_EPS_AC::F_EPS_AC_01 to context.sts.orb.eps.ac;
        allocate Functions::FN_EPS_AC::F_EPS_AC_02 to context.sts.orb.eps.ac;
        allocate Functions::FN_EPS_AC::F_EPS_AC_03 to context.sts.orb.eps.ac;
        allocate Functions::FN_EPS_AC::F_EPS_AC_04 to context.sts.orb.eps.ac;
        allocate Functions::FN_EPS_AC::F_EPS_AC_05 to context.sts.orb.eps.ac;
        allocate Functions::FN_EPS_DC::F_EPS_DC_01 to context.sts.orb.eps.dc;
        allocate Functions::FN_EPS_DC::F_EPS_DC_02 to context.sts.orb.eps.dc;
        allocate Functions::FN_EPS_DC::F_EPS_DC_03 to context.sts.orb.eps.dc;
        allocate Functions::FN_EPS_DC::F_EPS_DC_04 to context.sts.orb.eps.dc;
        allocate Functions::FN_EPS_DC::F_EPS_DC_05 to context.sts.orb.eps.dc;
        allocate Functions::FN_EPS_DC::F_EPS_DC_06 to context.sts.orb.eps.dc;
        allocate Functions::FN_EPS_DC::F_EPS_DC_07 to context.sts.orb.eps.dc;
        allocate Functions::FN_EPS_FCP::F_EPS_FCP_01 to context.sts.orb.eps.fcp;
        allocate Functions::FN_EPS_FCP::F_EPS_FCP_02 to context.sts.orb.eps.fcp;
        allocate Functions::FN_EPS_FCP::F_EPS_FCP_03 to context.sts.orb.eps.fcp;
        allocate Functions::FN_EPS_FCP::F_EPS_FCP_04 to context.sts.orb.eps.fcp;
        allocate Functions::FN_EPS_FCP::F_EPS_FCP_05 to context.sts.orb.eps.fcp;
        allocate Functions::FN_EPS_FCP::F_EPS_FCP_06 to context.sts.orb.eps.fcp;
        allocate Functions::FN_EPS_FCP::F_EPS_FCP_07 to context.sts.orb.eps.fcp;
        allocate Functions::FN_EPS_FCP::F_EPS_FCP_08 to context.sts.orb.eps.fcp;
        allocate Functions::FN_EPS_PRSD::F_EPS_PRSD_01 to context.sts.orb.eps.prsd;
        allocate Functions::FN_EPS_PRSD::F_EPS_PRSD_02 to context.sts.orb.eps.prsd;
        allocate Functions::FN_EPS_PRSD::F_EPS_PRSD_03 to context.sts.orb.eps.prsd;
        allocate Functions::FN_EPS_PRSD::F_EPS_PRSD_04 to context.sts.orb.eps.prsd;
        allocate Functions::FN_EPS_PRSD::F_EPS_PRSD_05 to context.sts.orb.eps.prsd;
        allocate Functions::FN_EPS_PRSD::F_EPS_PRSD_06 to context.sts.orb.eps.prsd;
        allocate Functions::FN_EPS_PRSD::F_EPS_PRSD_07 to context.sts.orb.eps.prsd;
        allocate Functions::FN_EPS_PRSD::F_EPS_PRSD_08 to context.sts.orb.eps.prsd;
        allocate Functions::FN_EVA::F_EVA_01 to context.sts.orb.eva;
        allocate Functions::FN_EVA::F_EVA_02 to context.sts.orb.eva;
        allocate Functions::FN_EVA::F_EVA_03 to context.sts.orb.eva;
        allocate Functions::FN_EVA::F_EVA_04 to context.sts.orb.eva;
        allocate Functions::FN_EVA::F_EVA_05 to context.sts.orb.eva;
        allocate Functions::FN_EVA::F_EVA_06 to context.sts.orb.eva;
        allocate Functions::FN_EVA::F_EVA_07 to context.sts.orb.eva;
        allocate Functions::FN_EVA_CHK::F_EVA_CHK_01 to context.sts.orb.eva.chk;
        allocate Functions::FN_EVA_CHK::F_EVA_CHK_02 to context.sts.orb.eva.chk;
        allocate Functions::FN_EVA_CHK::F_EVA_CHK_03 to context.sts.orb.eva.chk;
        allocate Functions::FN_EVA_CHK::F_EVA_CHK_04 to context.sts.orb.eva.chk;
        allocate Functions::FN_EVA_CHK::F_EVA_CHK_05 to context.sts.orb.eva.chk;
        allocate Functions::FN_EVA_CHK::F_EVA_CHK_06 to context.sts.orb.eva.chk;
        allocate Functions::FN_EVA_CHK::F_EVA_CHK_07 to context.sts.orb.eva.chk;
        allocate Functions::FN_EVA_CHK::F_EVA_CHK_08 to context.sts.orb.eva.chk;
        allocate Functions::FN_EVA_CHK::F_EVA_CHK_09 to context.sts.orb.eva.chk;
        allocate Functions::FN_EVA_CHK::F_EVA_CHK_10 to context.sts.orb.eva.chk;
        allocate Functions::FN_EVA_CHK::F_EVA_CHK_11 to context.sts.orb.eva.chk;
        allocate Functions::FN_EVA_CHK::F_EVA_CHK_12 to context.sts.orb.eva.chk;
        allocate Functions::FN_EVA_CHK::F_EVA_CHK_13 to context.sts.orb.eva.chk;
        allocate Functions::FN_EVA_DPR::F_EVA_DPR_01 to context.sts.orb.eva.dpr;
        allocate Functions::FN_EVA_DPR::F_EVA_DPR_02 to context.sts.orb.eva.dpr;
        allocate Functions::FN_EVA_DPR::F_EVA_DPR_03 to context.sts.orb.eva.dpr;
        allocate Functions::FN_EVA_DPR::F_EVA_DPR_04 to context.sts.orb.eva.dpr;
        allocate Functions::FN_EVA_DPR::F_EVA_DPR_05 to context.sts.orb.eva.dpr;
        allocate Functions::FN_EVA_DPR::F_EVA_DPR_06 to context.sts.orb.eva.dpr;
        allocate Functions::FN_EVA_DPR::F_EVA_DPR_07 to context.sts.orb.eva.dpr;
        allocate Functions::FN_EVA_DPR::F_EVA_DPR_08 to context.sts.orb.eva.dpr;
        allocate Functions::FN_EVA_DPR::F_EVA_DPR_09 to context.sts.orb.eva.dpr;
        allocate Functions::FN_EVA_DPR::F_EVA_DPR_10 to context.sts.orb.eva.dpr;
        allocate Functions::FN_EVA_DPR::F_EVA_DPR_11 to context.sts.orb.eva.dpr;
        allocate Functions::FN_EVA_DPR::F_EVA_DPR_12 to context.sts.orb.eva.dpr;
        allocate Functions::FN_EVA_EMG::F_EVA_EMG_01 to context.sts.orb.eva.emg;
        allocate Functions::FN_EVA_EMG::F_EVA_EMG_02 to context.sts.orb.eva.emg;
        allocate Functions::FN_EVA_EMG::F_EVA_EMG_03 to context.sts.orb.eva.emg;
        allocate Functions::FN_EVA_EMG::F_EVA_EMG_04 to context.sts.orb.eva.emg;
        allocate Functions::FN_EVA_EMG::F_EVA_EMG_05 to context.sts.orb.eva.emg;
        allocate Functions::FN_EVA_EMG::F_EVA_EMG_06 to context.sts.orb.eva.emg;
        allocate Functions::FN_EVA_EMG::F_EVA_EMG_07 to context.sts.orb.eva.emg;
        allocate Functions::FN_EVA_EMG::F_EVA_EMG_08 to context.sts.orb.eva.emg;
        allocate Functions::FN_EVA_EMG::F_EVA_EMG_09 to context.sts.orb.eva.emg;
        allocate Functions::FN_EVA_EMG::F_EVA_EMG_10 to context.sts.orb.eva.emg;
        allocate Functions::FN_EVA_EMG::F_EVA_EMG_11 to context.sts.orb.eva.emg;
        allocate Functions::FN_EVA_EMG::F_EVA_EMG_12 to context.sts.orb.eva.emg;
        allocate Functions::FN_EVA_EMG::F_EVA_EMG_13 to context.sts.orb.eva.emg;
        allocate Functions::FN_EVA_EMG::F_EVA_EMG_14 to context.sts.orb.eva.emg;
        allocate Functions::FN_EVA_MNT::F_EVA_MNT_01 to context.sts.orb.eva.mnt;
        allocate Functions::FN_EVA_MNT::F_EVA_MNT_02 to context.sts.orb.eva.mnt;
        allocate Functions::FN_EVA_MNT::F_EVA_MNT_03 to context.sts.orb.eva.mnt;
        allocate Functions::FN_EVA_MNT::F_EVA_MNT_04 to context.sts.orb.eva.mnt;
        allocate Functions::FN_EVA_MNT::F_EVA_MNT_05 to context.sts.orb.eva.mnt;
        allocate Functions::FN_EVA_MNT::F_EVA_MNT_06 to context.sts.orb.eva.mnt;
        allocate Functions::FN_EVA_MNT::F_EVA_MNT_07 to context.sts.orb.eva.mnt;
        allocate Functions::FN_EVA_MNT::F_EVA_MNT_08 to context.sts.orb.eva.mnt;
        allocate Functions::FN_EVA_MNT::F_EVA_MNT_09 to context.sts.orb.eva.mnt;
        allocate Functions::FN_EVA_MNT::F_EVA_MNT_10 to context.sts.orb.eva.mnt;
        allocate Functions::FN_EVA_MNT::F_EVA_MNT_11 to context.sts.orb.eva.mnt;
        allocate Functions::FN_EVA_MNT::F_EVA_MNT_12 to context.sts.orb.eva.mnt;
        allocate Functions::FN_EVA_MNT::F_EVA_MNT_13 to context.sts.orb.eva.mnt;
        allocate Functions::FN_EVA_OPS::F_EVA_OPS_01 to context.sts.orb.eva.ops;
        allocate Functions::FN_EVA_OPS::F_EVA_OPS_02 to context.sts.orb.eva.ops;
        allocate Functions::FN_EVA_OPS::F_EVA_OPS_03 to context.sts.orb.eva.ops;
        allocate Functions::FN_EVA_OPS::F_EVA_OPS_04 to context.sts.orb.eva.ops;
        allocate Functions::FN_EVA_OPS::F_EVA_OPS_05 to context.sts.orb.eva.ops;
        allocate Functions::FN_EVA_OPS::F_EVA_OPS_06 to context.sts.orb.eva.ops;
        allocate Functions::FN_EVA_OPS::F_EVA_OPS_07 to context.sts.orb.eva.ops;
        allocate Functions::FN_EVA_OPS::F_EVA_OPS_08 to context.sts.orb.eva.ops;
        allocate Functions::FN_EVA_OPS::F_EVA_OPS_09 to context.sts.orb.eva.ops;
        allocate Functions::FN_EVA_OPS::F_EVA_OPS_10 to context.sts.orb.eva.ops;
        allocate Functions::FN_EVA_OPS::F_EVA_OPS_11 to context.sts.orb.eva.ops;
        allocate Functions::FN_EVA_OPS::F_EVA_OPS_12 to context.sts.orb.eva.ops;
        allocate Functions::FN_EVA_OPS::F_EVA_OPS_13 to context.sts.orb.eva.ops;
        allocate Functions::FN_EVA_OPS::F_EVA_OPS_14 to context.sts.orb.eva.ops;
        allocate Functions::FN_EVA_TLS::F_EVA_TLS_01 to context.sts.orb.eva.tls;
        allocate Functions::FN_EVA_TLS::F_EVA_TLS_02 to context.sts.orb.eva.tls;
        allocate Functions::FN_EVA_TLS::F_EVA_TLS_03 to context.sts.orb.eva.tls;
        allocate Functions::FN_EVA_TLS::F_EVA_TLS_04 to context.sts.orb.eva.tls;
        allocate Functions::FN_EVA_TLS::F_EVA_TLS_05 to context.sts.orb.eva.tls;
        allocate Functions::FN_EVA_TLS::F_EVA_TLS_06 to context.sts.orb.eva.tls;
        allocate Functions::FN_EVA_TLS::F_EVA_TLS_07 to context.sts.orb.eva.tls;
        allocate Functions::FN_EVA_TLS::F_EVA_TLS_08 to context.sts.orb.eva.tls;
        allocate Functions::FN_EVA_TLS::F_EVA_TLS_09 to context.sts.orb.eva.tls;
        allocate Functions::FN_EVA_TLS::F_EVA_TLS_10 to context.sts.orb.eva.tls;
        allocate Functions::FN_EVA_TLS::F_EVA_TLS_11 to context.sts.orb.eva.tls;
        allocate Functions::FN_EVA_TLS::F_EVA_TLS_12 to context.sts.orb.eva.tls;
        allocate Functions::FN_GNC::F_GNC_01 to context.sts.orb.gnc;
        allocate Functions::FN_GNC::F_GNC_02 to context.sts.orb.gnc;
        allocate Functions::FN_GNC::F_GNC_03 to context.sts.orb.gnc;
        allocate Functions::FN_GNC::F_GNC_04 to context.sts.orb.gnc;
        allocate Functions::FN_GNC::F_GNC_05 to context.sts.orb.gnc;
        allocate Functions::FN_GNC_ACT::F_GNC_ACT_01 to context.sts.orb.gnc.act;
        allocate Functions::FN_GNC_ACT::F_GNC_ACT_02 to context.sts.orb.gnc.act;
        allocate Functions::FN_GNC_ACT::F_GNC_ACT_03 to context.sts.orb.gnc.act;
        allocate Functions::FN_GNC_ACT::F_GNC_ACT_04 to context.sts.orb.gnc.act;
        allocate Functions::FN_GNC_ACT::F_GNC_ACT_05 to context.sts.orb.gnc.act;
        allocate Functions::FN_GNC_ACT::F_GNC_ACT_06 to context.sts.orb.gnc.act;
        allocate Functions::FN_GNC_ACT::F_GNC_ACT_07 to context.sts.orb.gnc.act;
        allocate Functions::FN_GNC_ACT::F_GNC_ACT_08 to context.sts.orb.gnc.act;
        allocate Functions::FN_GNC_ACT::F_GNC_ACT_09 to context.sts.orb.gnc.act;
        allocate Functions::FN_GNC_ACT::F_GNC_ACT_10 to context.sts.orb.gnc.act;
        allocate Functions::FN_GNC_ACT::F_GNC_ACT_11 to context.sts.orb.gnc.act;
        allocate Functions::FN_GNC_ACT::F_GNC_ACT_12 to context.sts.orb.gnc.act;
        allocate Functions::FN_GNC_CCD::F_GNC_CCD_01 to context.sts.orb.gnc.ccd;
        allocate Functions::FN_GNC_CCD::F_GNC_CCD_02 to context.sts.orb.gnc.ccd;
        allocate Functions::FN_GNC_CCD::F_GNC_CCD_03 to context.sts.orb.gnc.ccd;
        allocate Functions::FN_GNC_CCD::F_GNC_CCD_04 to context.sts.orb.gnc.ccd;
        allocate Functions::FN_GNC_CCD::F_GNC_CCD_05 to context.sts.orb.gnc.ccd;
        allocate Functions::FN_GNC_CCD::F_GNC_CCD_06 to context.sts.orb.gnc.ccd;
        allocate Functions::FN_GNC_CCD::F_GNC_CCD_07 to context.sts.orb.gnc.ccd;
        allocate Functions::FN_GNC_CCD::F_GNC_CCD_08 to context.sts.orb.gnc.ccd;
        allocate Functions::FN_GNC_CCD::F_GNC_CCD_09 to context.sts.orb.gnc.ccd;
        allocate Functions::FN_GNC_CCD::F_GNC_CCD_10 to context.sts.orb.gnc.ccd;
        allocate Functions::FN_GNC_CCD::F_GNC_CCD_11 to context.sts.orb.gnc.ccd;
        allocate Functions::FN_GNC_CCD::F_GNC_CCD_12 to context.sts.orb.gnc.ccd;
        allocate Functions::FN_GNC_CCD::F_GNC_CCD_13 to context.sts.orb.gnc.ccd;
        allocate Functions::FN_GNC_FCS::F_GNC_FCS_01 to context.sts.orb.gnc.fcs;
        allocate Functions::FN_GNC_FCS::F_GNC_FCS_02 to context.sts.orb.gnc.fcs;
        allocate Functions::FN_GNC_FCS::F_GNC_FCS_03 to context.sts.orb.gnc.fcs;
        allocate Functions::FN_GNC_FCS::F_GNC_FCS_04 to context.sts.orb.gnc.fcs;
        allocate Functions::FN_GNC_FCS::F_GNC_FCS_05 to context.sts.orb.gnc.fcs;
        allocate Functions::FN_GNC_FCS::F_GNC_FCS_06 to context.sts.orb.gnc.fcs;
        allocate Functions::FN_GNC_FCS::F_GNC_FCS_07 to context.sts.orb.gnc.fcs;
        allocate Functions::FN_GNC_FCS::F_GNC_FCS_08 to context.sts.orb.gnc.fcs;
        allocate Functions::FN_GNC_FCS::F_GNC_FCS_09 to context.sts.orb.gnc.fcs;
        allocate Functions::FN_GNC_FCS::F_GNC_FCS_10 to context.sts.orb.gnc.fcs;
        allocate Functions::FN_GNC_FCS::F_GNC_FCS_11 to context.sts.orb.gnc.fcs;
        allocate Functions::FN_GNC_FCS::F_GNC_FCS_12 to context.sts.orb.gnc.fcs;
        allocate Functions::FN_GNC_GNS::F_GNC_GNS_01 to context.sts.orb.gnc.gns;
        allocate Functions::FN_GNC_GNS::F_GNC_GNS_02 to context.sts.orb.gnc.gns;
        allocate Functions::FN_GNC_GNS::F_GNC_GNS_03 to context.sts.orb.gnc.gns;
        allocate Functions::FN_GNC_GNS::F_GNC_GNS_04 to context.sts.orb.gnc.gns;
        allocate Functions::FN_GNC_GNS::F_GNC_GNS_05 to context.sts.orb.gnc.gns;
        allocate Functions::FN_GNC_GNS::F_GNC_GNS_06 to context.sts.orb.gnc.gns;
        allocate Functions::FN_GNC_GNS::F_GNC_GNS_07 to context.sts.orb.gnc.gns;
        allocate Functions::FN_GNC_GNS::F_GNC_GNS_08 to context.sts.orb.gnc.gns;
        allocate Functions::FN_GNC_GNS::F_GNC_GNS_09 to context.sts.orb.gnc.gns;
        allocate Functions::FN_GNC_GNS::F_GNC_GNS_10 to context.sts.orb.gnc.gns;
        allocate Functions::FN_GNC_GNS::F_GNC_GNS_11 to context.sts.orb.gnc.gns;
        allocate Functions::FN_GNC_GNS::F_GNC_GNS_12 to context.sts.orb.gnc.gns;
        allocate Functions::FN_GNC_INS::F_GNC_INS_01 to context.sts.orb.gnc.ins;
        allocate Functions::FN_GNC_INS::F_GNC_INS_02 to context.sts.orb.gnc.ins;
        allocate Functions::FN_GNC_INS::F_GNC_INS_03 to context.sts.orb.gnc.ins;
        allocate Functions::FN_GNC_INS::F_GNC_INS_04 to context.sts.orb.gnc.ins;
        allocate Functions::FN_GNC_INS::F_GNC_INS_05 to context.sts.orb.gnc.ins;
        allocate Functions::FN_GNC_INS::F_GNC_INS_06 to context.sts.orb.gnc.ins;
        allocate Functions::FN_GNC_INS::F_GNC_INS_07 to context.sts.orb.gnc.ins;
        allocate Functions::FN_GNC_INS::F_GNC_INS_08 to context.sts.orb.gnc.ins;
        allocate Functions::FN_GNC_INS::F_GNC_INS_09 to context.sts.orb.gnc.ins;
        allocate Functions::FN_GNC_INS::F_GNC_INS_10 to context.sts.orb.gnc.ins;
        allocate Functions::FN_GNC_INS::F_GNC_INS_11 to context.sts.orb.gnc.ins;
        allocate Functions::FN_GNC_INS::F_GNC_INS_12 to context.sts.orb.gnc.ins;
        allocate Functions::FN_GNC_NAS::F_GNC_NAS_01 to context.sts.orb.gnc.nas;
        allocate Functions::FN_GNC_NAS::F_GNC_NAS_02 to context.sts.orb.gnc.nas;
        allocate Functions::FN_GNC_NAS::F_GNC_NAS_03 to context.sts.orb.gnc.nas;
        allocate Functions::FN_GNC_NAS::F_GNC_NAS_04 to context.sts.orb.gnc.nas;
        allocate Functions::FN_GNC_NAS::F_GNC_NAS_05 to context.sts.orb.gnc.nas;
        allocate Functions::FN_GNC_NAS::F_GNC_NAS_06 to context.sts.orb.gnc.nas;
        allocate Functions::FN_GNC_NAS::F_GNC_NAS_07 to context.sts.orb.gnc.nas;
        allocate Functions::FN_GNC_NAS::F_GNC_NAS_08 to context.sts.orb.gnc.nas;
        allocate Functions::FN_GNC_NAS::F_GNC_NAS_09 to context.sts.orb.gnc.nas;
        allocate Functions::FN_GNC_NAS::F_GNC_NAS_10 to context.sts.orb.gnc.nas;
        allocate Functions::FN_GNC_NAS::F_GNC_NAS_11 to context.sts.orb.gnc.nas;
        allocate Functions::FN_GNC_NAS::F_GNC_NAS_12 to context.sts.orb.gnc.nas;
        allocate Functions::FN_GNC_OPS::F_GNC_OPS_01 to context.sts.orb.gnc.ops;
        allocate Functions::FN_GNC_OPS::F_GNC_OPS_02 to context.sts.orb.gnc.ops;
        allocate Functions::FN_GNC_OPS::F_GNC_OPS_03 to context.sts.orb.gnc.ops;
        allocate Functions::FN_GNC_OPS::F_GNC_OPS_04 to context.sts.orb.gnc.ops;
        allocate Functions::FN_GNC_OPS::F_GNC_OPS_05 to context.sts.orb.gnc.ops;
        allocate Functions::FN_GNC_OPS::F_GNC_OPS_06 to context.sts.orb.gnc.ops;
        allocate Functions::FN_GNC_OPS::F_GNC_OPS_07 to context.sts.orb.gnc.ops;
        allocate Functions::FN_GNC_OPS::F_GNC_OPS_08 to context.sts.orb.gnc.ops;
        allocate Functions::FN_GNC_OPS::F_GNC_OPS_09 to context.sts.orb.gnc.ops;
        allocate Functions::FN_GNC_OPS::F_GNC_OPS_10 to context.sts.orb.gnc.ops;
        allocate Functions::FN_GNC_OPS::F_GNC_OPS_11 to context.sts.orb.gnc.ops;
        allocate Functions::FN_GNC_OPS::F_GNC_OPS_12 to context.sts.orb.gnc.ops;
        allocate Functions::FN_MECH::F_MECH_01 to context.sts.orb.mech;
        allocate Functions::FN_MECH::F_MECH_02 to context.sts.orb.mech;
        allocate Functions::FN_MECH::F_MECH_03 to context.sts.orb.mech;
        allocate Functions::FN_MECH::F_MECH_04 to context.sts.orb.mech;
        allocate Functions::FN_MECH::F_MECH_05 to context.sts.orb.mech;
        allocate Functions::FN_MECH::F_MECH_06 to context.sts.orb.mech;
        allocate Functions::FN_MECH::F_MECH_07 to context.sts.orb.mech;
        allocate Functions::FN_MECH::F_MECH_08 to context.sts.orb.mech;
        allocate Functions::FN_MECH::F_MECH_09 to context.sts.orb.mech;
        allocate Functions::FN_MECH::F_MECH_10 to context.sts.orb.mech;
        allocate Functions::FN_MECH_ACT::F_MECH_ACT_01 to context.sts.orb.mech.act;
        allocate Functions::FN_MECH_ACT::F_MECH_ACT_02 to context.sts.orb.mech.act;
        allocate Functions::FN_MECH_ACT::F_MECH_ACT_03 to context.sts.orb.mech.act;
        allocate Functions::FN_MECH_ACT::F_MECH_ACT_04 to context.sts.orb.mech.act;
        allocate Functions::FN_MECH_ACT::F_MECH_ACT_05 to context.sts.orb.mech.act;
        allocate Functions::FN_MECH_ACT::F_MECH_ACT_06 to context.sts.orb.mech.act;
        allocate Functions::FN_MECH_ACT::F_MECH_ACT_07 to context.sts.orb.mech.act;
        allocate Functions::FN_MECH_DEC::F_MECH_DEC_01 to context.sts.orb.mech.dec;
        allocate Functions::FN_MECH_DEC::F_MECH_DEC_02 to context.sts.orb.mech.dec;
        allocate Functions::FN_MECH_DEC::F_MECH_DEC_03 to context.sts.orb.mech.dec;
        allocate Functions::FN_MECH_DEC::F_MECH_DEC_04 to context.sts.orb.mech.dec;
        allocate Functions::FN_MECH_DEC::F_MECH_DEC_05 to context.sts.orb.mech.dec;
        allocate Functions::FN_MECH_DEC::F_MECH_DEC_06 to context.sts.orb.mech.dec;
        allocate Functions::FN_MECH_DEC::F_MECH_DEC_07 to context.sts.orb.mech.dec;
        allocate Functions::FN_MECH_LDG::F_MECH_LDG_01 to context.sts.orb.mech.ldg;
        allocate Functions::FN_MECH_LDG::F_MECH_LDG_02 to context.sts.orb.mech.ldg;
        allocate Functions::FN_MECH_LDG::F_MECH_LDG_03 to context.sts.orb.mech.ldg;
        allocate Functions::FN_MECH_LDG::F_MECH_LDG_04 to context.sts.orb.mech.ldg;
        allocate Functions::FN_MECH_LDG::F_MECH_LDG_05 to context.sts.orb.mech.ldg;
        allocate Functions::FN_MECH_LDG::F_MECH_LDG_06 to context.sts.orb.mech.ldg;
        allocate Functions::FN_MECH_LDG::F_MECH_LDG_07 to context.sts.orb.mech.ldg;
        allocate Functions::FN_MECH_LDG::F_MECH_LDG_08 to context.sts.orb.mech.ldg;
        allocate Functions::FN_MECH_OPS::F_MECH_OPS_01 to context.sts.orb.mech.ops;
        allocate Functions::FN_MECH_OPS::F_MECH_OPS_02 to context.sts.orb.mech.ops;
        allocate Functions::FN_MECH_OPS::F_MECH_OPS_03 to context.sts.orb.mech.ops;
        allocate Functions::FN_MECH_OPS::F_MECH_OPS_04 to context.sts.orb.mech.ops;
        allocate Functions::FN_MECH_OPS::F_MECH_OPS_05 to context.sts.orb.mech.ops;
        allocate Functions::FN_MECH_OPS::F_MECH_OPS_06 to context.sts.orb.mech.ops;
        allocate Functions::FN_MECH_PLB::F_MECH_PLB_01 to context.sts.orb.mech.plb;
        allocate Functions::FN_MECH_PLB::F_MECH_PLB_02 to context.sts.orb.mech.plb;
        allocate Functions::FN_MECH_PLB::F_MECH_PLB_03 to context.sts.orb.mech.plb;
        allocate Functions::FN_MECH_PLB::F_MECH_PLB_04 to context.sts.orb.mech.plb;
        allocate Functions::FN_MECH_PLB::F_MECH_PLB_05 to context.sts.orb.mech.plb;
        allocate Functions::FN_MECH_PLB::F_MECH_PLB_06 to context.sts.orb.mech.plb;
        allocate Functions::FN_MECH_PLB::F_MECH_PLB_07 to context.sts.orb.mech.plb;
        allocate Functions::FN_MECH_VNT::F_MECH_VNT_01 to context.sts.orb.mech.vnt;
        allocate Functions::FN_MECH_VNT::F_MECH_VNT_02 to context.sts.orb.mech.vnt;
        allocate Functions::FN_MECH_VNT::F_MECH_VNT_03 to context.sts.orb.mech.vnt;
        allocate Functions::FN_MECH_VNT::F_MECH_VNT_04 to context.sts.orb.mech.vnt;
        allocate Functions::FN_MECH_VNT::F_MECH_VNT_05 to context.sts.orb.mech.vnt;
        allocate Functions::FN_MECH_VNT::F_MECH_VNT_06 to context.sts.orb.mech.vnt;
        allocate Functions::FN_MECH_VNT::F_MECH_VNT_07 to context.sts.orb.mech.vnt;
        allocate Functions::FN_MPS::F_MPS_01 to context.sts.orb.mps;
        allocate Functions::FN_MPS::F_MPS_02 to context.sts.orb.mps;
        allocate Functions::FN_MPS::F_MPS_03 to context.sts.orb.mps;
        allocate Functions::FN_MPS::F_MPS_04 to context.sts.orb.mps;
        allocate Functions::FN_MPS::F_MPS_05 to context.sts.orb.mps;
        allocate Functions::FN_MPS::F_MPS_06 to context.sts.orb.mps;
        allocate Functions::FN_MPS_CTL::F_MPS_CTL_01 to context.sts.orb.mps.ctl;
        allocate Functions::FN_MPS_CTL::F_MPS_CTL_02 to context.sts.orb.mps.ctl;
        allocate Functions::FN_MPS_CTL::F_MPS_CTL_03 to context.sts.orb.mps.ctl;
        allocate Functions::FN_MPS_CTL::F_MPS_CTL_04 to context.sts.orb.mps.ctl;
        allocate Functions::FN_MPS_CTL::F_MPS_CTL_05 to context.sts.orb.mps.ctl;
        allocate Functions::FN_MPS_CTL::F_MPS_CTL_06 to context.sts.orb.mps.ctl;
        allocate Functions::FN_MPS_CTL::F_MPS_CTL_07 to context.sts.orb.mps.ctl;
        allocate Functions::FN_MPS_CTL::F_MPS_CTL_08 to context.sts.orb.mps.ctl;
        allocate Functions::FN_MPS_CTL::F_MPS_CTL_09 to context.sts.orb.mps.ctl;
        allocate Functions::FN_MPS_CTL::F_MPS_CTL_10 to context.sts.orb.mps.ctl;
        allocate Functions::FN_MPS_CTL::F_MPS_CTL_11 to context.sts.orb.mps.ctl;
        allocate Functions::FN_MPS_CTL::F_MPS_CTL_12 to context.sts.orb.mps.ctl;
        allocate Functions::FN_MPS_CTL::F_MPS_CTL_13 to context.sts.orb.mps.ctl;
        allocate Functions::FN_MPS_DMP::F_MPS_DMP_01 to context.sts.orb.mps.dmp;
        allocate Functions::FN_MPS_DMP::F_MPS_DMP_02 to context.sts.orb.mps.dmp;
        allocate Functions::FN_MPS_DMP::F_MPS_DMP_03 to context.sts.orb.mps.dmp;
        allocate Functions::FN_MPS_DMP::F_MPS_DMP_04 to context.sts.orb.mps.dmp;
        allocate Functions::FN_MPS_DMP::F_MPS_DMP_05 to context.sts.orb.mps.dmp;
        allocate Functions::FN_MPS_DMP::F_MPS_DMP_06 to context.sts.orb.mps.dmp;
        allocate Functions::FN_MPS_DMP::F_MPS_DMP_07 to context.sts.orb.mps.dmp;
        allocate Functions::FN_MPS_DMP::F_MPS_DMP_08 to context.sts.orb.mps.dmp;
        allocate Functions::FN_MPS_DMP::F_MPS_DMP_09 to context.sts.orb.mps.dmp;
        allocate Functions::FN_MPS_DMP::F_MPS_DMP_10 to context.sts.orb.mps.dmp;
        allocate Functions::FN_MPS_DMP::F_MPS_DMP_11 to context.sts.orb.mps.dmp;
        allocate Functions::FN_MPS_DMP::F_MPS_DMP_12 to context.sts.orb.mps.dmp;
        allocate Functions::FN_MPS_DMP::F_MPS_DMP_13 to context.sts.orb.mps.dmp;
        allocate Functions::FN_MPS_HE::F_MPS_HE_01 to context.sts.orb.mps.he;
        allocate Functions::FN_MPS_HE::F_MPS_HE_02 to context.sts.orb.mps.he;
        allocate Functions::FN_MPS_HE::F_MPS_HE_03 to context.sts.orb.mps.he;
        allocate Functions::FN_MPS_HE::F_MPS_HE_04 to context.sts.orb.mps.he;
        allocate Functions::FN_MPS_HE::F_MPS_HE_05 to context.sts.orb.mps.he;
        allocate Functions::FN_MPS_HE::F_MPS_HE_06 to context.sts.orb.mps.he;
        allocate Functions::FN_MPS_HE::F_MPS_HE_07 to context.sts.orb.mps.he;
        allocate Functions::FN_MPS_HE::F_MPS_HE_08 to context.sts.orb.mps.he;
        allocate Functions::FN_MPS_HE::F_MPS_HE_09 to context.sts.orb.mps.he;
        allocate Functions::FN_MPS_HE::F_MPS_HE_10 to context.sts.orb.mps.he;
        allocate Functions::FN_MPS_HE::F_MPS_HE_11 to context.sts.orb.mps.he;
        allocate Functions::FN_MPS_HE::F_MPS_HE_12 to context.sts.orb.mps.he;
        allocate Functions::FN_MPS_HE::F_MPS_HE_13 to context.sts.orb.mps.he;
        allocate Functions::FN_MPS_OPS::F_MPS_OPS_01 to context.sts.orb.mps.ops;
        allocate Functions::FN_MPS_OPS::F_MPS_OPS_02 to context.sts.orb.mps.ops;
        allocate Functions::FN_MPS_OPS::F_MPS_OPS_03 to context.sts.orb.mps.ops;
        allocate Functions::FN_MPS_OPS::F_MPS_OPS_04 to context.sts.orb.mps.ops;
        allocate Functions::FN_MPS_OPS::F_MPS_OPS_05 to context.sts.orb.mps.ops;
        allocate Functions::FN_MPS_OPS::F_MPS_OPS_06 to context.sts.orb.mps.ops;
        allocate Functions::FN_MPS_OPS::F_MPS_OPS_07 to context.sts.orb.mps.ops;
        allocate Functions::FN_MPS_OPS::F_MPS_OPS_08 to context.sts.orb.mps.ops;
        allocate Functions::FN_MPS_OPS::F_MPS_OPS_09 to context.sts.orb.mps.ops;
        allocate Functions::FN_MPS_OPS::F_MPS_OPS_10 to context.sts.orb.mps.ops;
        allocate Functions::FN_MPS_OPS::F_MPS_OPS_11 to context.sts.orb.mps.ops;
        allocate Functions::FN_MPS_OPS::F_MPS_OPS_12 to context.sts.orb.mps.ops;
        allocate Functions::FN_MPS_OPS::F_MPS_OPS_13 to context.sts.orb.mps.ops;
        allocate Functions::FN_MPS_PMS::F_MPS_PMS_01 to context.sts.orb.mps.pms;
        allocate Functions::FN_MPS_PMS::F_MPS_PMS_02 to context.sts.orb.mps.pms;
        allocate Functions::FN_MPS_PMS::F_MPS_PMS_03 to context.sts.orb.mps.pms;
        allocate Functions::FN_MPS_PMS::F_MPS_PMS_04 to context.sts.orb.mps.pms;
        allocate Functions::FN_MPS_PMS::F_MPS_PMS_05 to context.sts.orb.mps.pms;
        allocate Functions::FN_MPS_PMS::F_MPS_PMS_06 to context.sts.orb.mps.pms;
        allocate Functions::FN_MPS_PMS::F_MPS_PMS_07 to context.sts.orb.mps.pms;
        allocate Functions::FN_MPS_PMS::F_MPS_PMS_08 to context.sts.orb.mps.pms;
        allocate Functions::FN_MPS_PMS::F_MPS_PMS_09 to context.sts.orb.mps.pms;
        allocate Functions::FN_MPS_PMS::F_MPS_PMS_10 to context.sts.orb.mps.pms;
        allocate Functions::FN_MPS_PMS::F_MPS_PMS_11 to context.sts.orb.mps.pms;
        allocate Functions::FN_MPS_PMS::F_MPS_PMS_12 to context.sts.orb.mps.pms;
        allocate Functions::FN_MPS_PMS::F_MPS_PMS_13 to context.sts.orb.mps.pms;
        allocate Functions::FN_MPS_SSME::F_MPS_SSME_01 to context.sts.orb.mps.ssme;
        allocate Functions::FN_MPS_SSME::F_MPS_SSME_02 to context.sts.orb.mps.ssme;
        allocate Functions::FN_MPS_SSME::F_MPS_SSME_03 to context.sts.orb.mps.ssme;
        allocate Functions::FN_MPS_SSME::F_MPS_SSME_04 to context.sts.orb.mps.ssme;
        allocate Functions::FN_MPS_SSME::F_MPS_SSME_05 to context.sts.orb.mps.ssme;
        allocate Functions::FN_MPS_SSME::F_MPS_SSME_06 to context.sts.orb.mps.ssme;
        allocate Functions::FN_MPS_SSME::F_MPS_SSME_07 to context.sts.orb.mps.ssme;
        allocate Functions::FN_MPS_SSME::F_MPS_SSME_08 to context.sts.orb.mps.ssme;
        allocate Functions::FN_MPS_SSME::F_MPS_SSME_09 to context.sts.orb.mps.ssme;
        allocate Functions::FN_MPS_SSME::F_MPS_SSME_10 to context.sts.orb.mps.ssme;
        allocate Functions::FN_MPS_SSME::F_MPS_SSME_11 to context.sts.orb.mps.ssme;
        allocate Functions::FN_MPS_SSME::F_MPS_SSME_12 to context.sts.orb.mps.ssme;
        allocate Functions::FN_MPS_TVC::F_MPS_TVC_01 to context.sts.orb.mps.tvc;
        allocate Functions::FN_MPS_TVC::F_MPS_TVC_02 to context.sts.orb.mps.tvc;
        allocate Functions::FN_MPS_TVC::F_MPS_TVC_03 to context.sts.orb.mps.tvc;
        allocate Functions::FN_MPS_TVC::F_MPS_TVC_04 to context.sts.orb.mps.tvc;
        allocate Functions::FN_MPS_TVC::F_MPS_TVC_05 to context.sts.orb.mps.tvc;
        allocate Functions::FN_MPS_TVC::F_MPS_TVC_06 to context.sts.orb.mps.tvc;
        allocate Functions::FN_MPS_TVC::F_MPS_TVC_07 to context.sts.orb.mps.tvc;
        allocate Functions::FN_MPS_TVC::F_MPS_TVC_08 to context.sts.orb.mps.tvc;
        allocate Functions::FN_MPS_TVC::F_MPS_TVC_09 to context.sts.orb.mps.tvc;
        allocate Functions::FN_MPS_TVC::F_MPS_TVC_10 to context.sts.orb.mps.tvc;
        allocate Functions::FN_MPS_TVC::F_MPS_TVC_11 to context.sts.orb.mps.tvc;
        allocate Functions::FN_MPS_TVC::F_MPS_TVC_12 to context.sts.orb.mps.tvc;
        allocate Functions::FN_MPS_TVC::F_MPS_TVC_13 to context.sts.orb.mps.tvc;
        allocate Functions::FN_OMS::F_OMS_01 to context.sts.orb.oms;
        allocate Functions::FN_OMS::F_OMS_02 to context.sts.orb.oms;
        allocate Functions::FN_OMS::F_OMS_03 to context.sts.orb.oms;
        allocate Functions::FN_OMS::F_OMS_04 to context.sts.orb.oms;
        allocate Functions::FN_OMS::F_OMS_05 to context.sts.orb.oms;
        allocate Functions::FN_OMS::F_OMS_06 to context.sts.orb.oms;
        allocate Functions::FN_OMS_ENG::F_OMS_ENG_01 to context.sts.orb.oms.eng;
        allocate Functions::FN_OMS_ENG::F_OMS_ENG_02 to context.sts.orb.oms.eng;
        allocate Functions::FN_OMS_ENG::F_OMS_ENG_03 to context.sts.orb.oms.eng;
        allocate Functions::FN_OMS_ENG::F_OMS_ENG_04 to context.sts.orb.oms.eng;
        allocate Functions::FN_OMS_ENG::F_OMS_ENG_05 to context.sts.orb.oms.eng;
        allocate Functions::FN_OMS_ENG::F_OMS_ENG_06 to context.sts.orb.oms.eng;
        allocate Functions::FN_OMS_ENG::F_OMS_ENG_07 to context.sts.orb.oms.eng;
        allocate Functions::FN_OMS_ENG::F_OMS_ENG_08 to context.sts.orb.oms.eng;
        allocate Functions::FN_OMS_ENG::F_OMS_ENG_09 to context.sts.orb.oms.eng;
        allocate Functions::FN_OMS_ENG::F_OMS_ENG_10 to context.sts.orb.oms.eng;
        allocate Functions::FN_OMS_ENG::F_OMS_ENG_11 to context.sts.orb.oms.eng;
        allocate Functions::FN_OMS_ENG::F_OMS_ENG_12 to context.sts.orb.oms.eng;
        allocate Functions::FN_OMS_ENG::F_OMS_ENG_13 to context.sts.orb.oms.eng;
        allocate Functions::FN_OMS_HE::F_OMS_HE_01 to context.sts.orb.oms.he;
        allocate Functions::FN_OMS_HE::F_OMS_HE_02 to context.sts.orb.oms.he;
        allocate Functions::FN_OMS_HE::F_OMS_HE_03 to context.sts.orb.oms.he;
        allocate Functions::FN_OMS_HE::F_OMS_HE_04 to context.sts.orb.oms.he;
        allocate Functions::FN_OMS_HE::F_OMS_HE_05 to context.sts.orb.oms.he;
        allocate Functions::FN_OMS_HE::F_OMS_HE_06 to context.sts.orb.oms.he;
        allocate Functions::FN_OMS_HE::F_OMS_HE_07 to context.sts.orb.oms.he;
        allocate Functions::FN_OMS_HE::F_OMS_HE_08 to context.sts.orb.oms.he;
        allocate Functions::FN_OMS_HE::F_OMS_HE_09 to context.sts.orb.oms.he;
        allocate Functions::FN_OMS_HE::F_OMS_HE_10 to context.sts.orb.oms.he;
        allocate Functions::FN_OMS_HE::F_OMS_HE_11 to context.sts.orb.oms.he;
        allocate Functions::FN_OMS_HE::F_OMS_HE_12 to context.sts.orb.oms.he;
        allocate Functions::FN_OMS_OPS::F_OMS_OPS_01 to context.sts.orb.oms.ops;
        allocate Functions::FN_OMS_OPS::F_OMS_OPS_02 to context.sts.orb.oms.ops;
        allocate Functions::FN_OMS_OPS::F_OMS_OPS_03 to context.sts.orb.oms.ops;
        allocate Functions::FN_OMS_OPS::F_OMS_OPS_04 to context.sts.orb.oms.ops;
        allocate Functions::FN_OMS_OPS::F_OMS_OPS_05 to context.sts.orb.oms.ops;
        allocate Functions::FN_OMS_OPS::F_OMS_OPS_06 to context.sts.orb.oms.ops;
        allocate Functions::FN_OMS_OPS::F_OMS_OPS_07 to context.sts.orb.oms.ops;
        allocate Functions::FN_OMS_OPS::F_OMS_OPS_08 to context.sts.orb.oms.ops;
        allocate Functions::FN_OMS_OPS::F_OMS_OPS_09 to context.sts.orb.oms.ops;
        allocate Functions::FN_OMS_OPS::F_OMS_OPS_10 to context.sts.orb.oms.ops;
        allocate Functions::FN_OMS_OPS::F_OMS_OPS_11 to context.sts.orb.oms.ops;
        allocate Functions::FN_OMS_OPS::F_OMS_OPS_12 to context.sts.orb.oms.ops;
        allocate Functions::FN_OMS_PSD::F_OMS_PSD_01 to context.sts.orb.oms.psd;
        allocate Functions::FN_OMS_PSD::F_OMS_PSD_02 to context.sts.orb.oms.psd;
        allocate Functions::FN_OMS_PSD::F_OMS_PSD_03 to context.sts.orb.oms.psd;
        allocate Functions::FN_OMS_PSD::F_OMS_PSD_04 to context.sts.orb.oms.psd;
        allocate Functions::FN_OMS_PSD::F_OMS_PSD_05 to context.sts.orb.oms.psd;
        allocate Functions::FN_OMS_PSD::F_OMS_PSD_06 to context.sts.orb.oms.psd;
        allocate Functions::FN_OMS_PSD::F_OMS_PSD_07 to context.sts.orb.oms.psd;
        allocate Functions::FN_OMS_PSD::F_OMS_PSD_08 to context.sts.orb.oms.psd;
        allocate Functions::FN_OMS_PSD::F_OMS_PSD_09 to context.sts.orb.oms.psd;
        allocate Functions::FN_OMS_PSD::F_OMS_PSD_10 to context.sts.orb.oms.psd;
        allocate Functions::FN_OMS_PSD::F_OMS_PSD_11 to context.sts.orb.oms.psd;
        allocate Functions::FN_OMS_PSD::F_OMS_PSD_12 to context.sts.orb.oms.psd;
        allocate Functions::FN_OMS_PSD::F_OMS_PSD_13 to context.sts.orb.oms.psd;
        allocate Functions::FN_OMS_THM::F_OMS_THM_01 to context.sts.orb.oms.thm;
        allocate Functions::FN_OMS_THM::F_OMS_THM_02 to context.sts.orb.oms.thm;
        allocate Functions::FN_OMS_THM::F_OMS_THM_03 to context.sts.orb.oms.thm;
        allocate Functions::FN_OMS_THM::F_OMS_THM_04 to context.sts.orb.oms.thm;
        allocate Functions::FN_OMS_THM::F_OMS_THM_05 to context.sts.orb.oms.thm;
        allocate Functions::FN_OMS_THM::F_OMS_THM_06 to context.sts.orb.oms.thm;
        allocate Functions::FN_OMS_THM::F_OMS_THM_07 to context.sts.orb.oms.thm;
        allocate Functions::FN_OMS_THM::F_OMS_THM_08 to context.sts.orb.oms.thm;
        allocate Functions::FN_OMS_THM::F_OMS_THM_09 to context.sts.orb.oms.thm;
        allocate Functions::FN_OMS_THM::F_OMS_THM_10 to context.sts.orb.oms.thm;
        allocate Functions::FN_OMS_THM::F_OMS_THM_11 to context.sts.orb.oms.thm;
        allocate Functions::FN_OMS_THM::F_OMS_THM_12 to context.sts.orb.oms.thm;
        allocate Functions::FN_OMS_TVC::F_OMS_TVC_01 to context.sts.orb.oms.tvc;
        allocate Functions::FN_OMS_TVC::F_OMS_TVC_02 to context.sts.orb.oms.tvc;
        allocate Functions::FN_OMS_TVC::F_OMS_TVC_03 to context.sts.orb.oms.tvc;
        allocate Functions::FN_OMS_TVC::F_OMS_TVC_04 to context.sts.orb.oms.tvc;
        allocate Functions::FN_OMS_TVC::F_OMS_TVC_05 to context.sts.orb.oms.tvc;
        allocate Functions::FN_OMS_TVC::F_OMS_TVC_06 to context.sts.orb.oms.tvc;
        allocate Functions::FN_OMS_TVC::F_OMS_TVC_07 to context.sts.orb.oms.tvc;
        allocate Functions::FN_OMS_TVC::F_OMS_TVC_08 to context.sts.orb.oms.tvc;
        allocate Functions::FN_OMS_TVC::F_OMS_TVC_09 to context.sts.orb.oms.tvc;
        allocate Functions::FN_OMS_TVC::F_OMS_TVC_10 to context.sts.orb.oms.tvc;
        allocate Functions::FN_OMS_TVC::F_OMS_TVC_11 to context.sts.orb.oms.tvc;
        allocate Functions::FN_OMS_TVC::F_OMS_TVC_12 to context.sts.orb.oms.tvc;
        allocate Functions::FN_OMS_XFD::F_OMS_XFD_01 to context.sts.orb.oms.xfd;
        allocate Functions::FN_OMS_XFD::F_OMS_XFD_02 to context.sts.orb.oms.xfd;
        allocate Functions::FN_OMS_XFD::F_OMS_XFD_03 to context.sts.orb.oms.xfd;
        allocate Functions::FN_OMS_XFD::F_OMS_XFD_04 to context.sts.orb.oms.xfd;
        allocate Functions::FN_OMS_XFD::F_OMS_XFD_05 to context.sts.orb.oms.xfd;
        allocate Functions::FN_OMS_XFD::F_OMS_XFD_06 to context.sts.orb.oms.xfd;
        allocate Functions::FN_OMS_XFD::F_OMS_XFD_07 to context.sts.orb.oms.xfd;
        allocate Functions::FN_OMS_XFD::F_OMS_XFD_08 to context.sts.orb.oms.xfd;
        allocate Functions::FN_OMS_XFD::F_OMS_XFD_09 to context.sts.orb.oms.xfd;
        allocate Functions::FN_OMS_XFD::F_OMS_XFD_10 to context.sts.orb.oms.xfd;
        allocate Functions::FN_OMS_XFD::F_OMS_XFD_11 to context.sts.orb.oms.xfd;
        allocate Functions::FN_OMS_XFD::F_OMS_XFD_12 to context.sts.orb.oms.xfd;
        allocate Functions::FN_OMS_XFD::F_OMS_XFD_13 to context.sts.orb.oms.xfd;
        allocate Functions::FN_PLS::F_PLS_01 to context.sts.orb.pls;
        allocate Functions::FN_PLS::F_PLS_02 to context.sts.orb.pls;
        allocate Functions::FN_PLS::F_PLS_03 to context.sts.orb.pls;
        allocate Functions::FN_PLS::F_PLS_04 to context.sts.orb.pls;
        allocate Functions::FN_PLS::F_PLS_05 to context.sts.orb.pls;
        allocate Functions::FN_PLS::F_PLS_06 to context.sts.orb.pls;
        allocate Functions::FN_PLS::F_PLS_07 to context.sts.orb.pls;
        allocate Functions::FN_PLS_ARM::F_PLS_ARM_01 to context.sts.orb.pls.arm;
        allocate Functions::FN_PLS_ARM::F_PLS_ARM_02 to context.sts.orb.pls.arm;
        allocate Functions::FN_PLS_ARM::F_PLS_ARM_03 to context.sts.orb.pls.arm;
        allocate Functions::FN_PLS_ARM::F_PLS_ARM_04 to context.sts.orb.pls.arm;
        allocate Functions::FN_PLS_ARM::F_PLS_ARM_05 to context.sts.orb.pls.arm;
        allocate Functions::FN_PLS_ARM::F_PLS_ARM_06 to context.sts.orb.pls.arm;
        allocate Functions::FN_PLS_ARM::F_PLS_ARM_07 to context.sts.orb.pls.arm;
        allocate Functions::FN_PLS_ARM::F_PLS_ARM_08 to context.sts.orb.pls.arm;
        allocate Functions::FN_PLS_CTL::F_PLS_CTL_01 to context.sts.orb.pls.ctl;
        allocate Functions::FN_PLS_CTL::F_PLS_CTL_02 to context.sts.orb.pls.ctl;
        allocate Functions::FN_PLS_CTL::F_PLS_CTL_03 to context.sts.orb.pls.ctl;
        allocate Functions::FN_PLS_CTL::F_PLS_CTL_04 to context.sts.orb.pls.ctl;
        allocate Functions::FN_PLS_CTL::F_PLS_CTL_05 to context.sts.orb.pls.ctl;
        allocate Functions::FN_PLS_CTL::F_PLS_CTL_06 to context.sts.orb.pls.ctl;
        allocate Functions::FN_PLS_CTL::F_PLS_CTL_07 to context.sts.orb.pls.ctl;
        allocate Functions::FN_PLS_MPM::F_PLS_MPM_01 to context.sts.orb.pls.mpm;
        allocate Functions::FN_PLS_MPM::F_PLS_MPM_02 to context.sts.orb.pls.mpm;
        allocate Functions::FN_PLS_MPM::F_PLS_MPM_03 to context.sts.orb.pls.mpm;
        allocate Functions::FN_PLS_MPM::F_PLS_MPM_04 to context.sts.orb.pls.mpm;
        allocate Functions::FN_PLS_MPM::F_PLS_MPM_05 to context.sts.orb.pls.mpm;
        allocate Functions::FN_PLS_MPM::F_PLS_MPM_06 to context.sts.orb.pls.mpm;
        allocate Functions::FN_PLS_MPM::F_PLS_MPM_07 to context.sts.orb.pls.mpm;
        allocate Functions::FN_PLS_ODS::F_PLS_ODS_01 to context.sts.orb.pls.ods;
        allocate Functions::FN_PLS_ODS::F_PLS_ODS_02 to context.sts.orb.pls.ods;
        allocate Functions::FN_PLS_ODS::F_PLS_ODS_03 to context.sts.orb.pls.ods;
        allocate Functions::FN_PLS_ODS::F_PLS_ODS_04 to context.sts.orb.pls.ods;
        allocate Functions::FN_PLS_ODS::F_PLS_ODS_05 to context.sts.orb.pls.ods;
        allocate Functions::FN_PLS_ODS::F_PLS_ODS_06 to context.sts.orb.pls.ods;
        allocate Functions::FN_PLS_ODS::F_PLS_ODS_07 to context.sts.orb.pls.ods;
        allocate Functions::FN_PLS_OPS::F_PLS_OPS_01 to context.sts.orb.pls.ops;
        allocate Functions::FN_PLS_OPS::F_PLS_OPS_02 to context.sts.orb.pls.ops;
        allocate Functions::FN_PLS_OPS::F_PLS_OPS_03 to context.sts.orb.pls.ops;
        allocate Functions::FN_PLS_OPS::F_PLS_OPS_04 to context.sts.orb.pls.ops;
        allocate Functions::FN_PLS_OPS::F_PLS_OPS_05 to context.sts.orb.pls.ops;
        allocate Functions::FN_PLS_OPS::F_PLS_OPS_06 to context.sts.orb.pls.ops;
        allocate Functions::FN_PLS_OPS::F_PLS_OPS_07 to context.sts.orb.pls.ops;
        allocate Functions::FN_PLS_PRL::F_PLS_PRL_01 to context.sts.orb.pls.prl;
        allocate Functions::FN_PLS_PRL::F_PLS_PRL_02 to context.sts.orb.pls.prl;
        allocate Functions::FN_PLS_PRL::F_PLS_PRL_03 to context.sts.orb.pls.prl;
        allocate Functions::FN_PLS_PRL::F_PLS_PRL_04 to context.sts.orb.pls.prl;
        allocate Functions::FN_PLS_PRL::F_PLS_PRL_05 to context.sts.orb.pls.prl;
        allocate Functions::FN_PLS_PRL::F_PLS_PRL_06 to context.sts.orb.pls.prl;
        allocate Functions::FN_PLS_PRL::F_PLS_PRL_07 to context.sts.orb.pls.prl;
        allocate Functions::FN_RCS::F_RCS_01 to context.sts.orb.rcs;
        allocate Functions::FN_RCS::F_RCS_02 to context.sts.orb.rcs;
        allocate Functions::FN_RCS::F_RCS_03 to context.sts.orb.rcs;
        allocate Functions::FN_RCS::F_RCS_04 to context.sts.orb.rcs;
        allocate Functions::FN_RCS::F_RCS_05 to context.sts.orb.rcs;
        allocate Functions::FN_RCS::F_RCS_06 to context.sts.orb.rcs;
        allocate Functions::FN_RCS::F_RCS_07 to context.sts.orb.rcs;
        allocate Functions::FN_RCS_HEP::F_RCS_HEP_01 to context.sts.orb.rcs.hep;
        allocate Functions::FN_RCS_HEP::F_RCS_HEP_02 to context.sts.orb.rcs.hep;
        allocate Functions::FN_RCS_HEP::F_RCS_HEP_03 to context.sts.orb.rcs.hep;
        allocate Functions::FN_RCS_HEP::F_RCS_HEP_04 to context.sts.orb.rcs.hep;
        allocate Functions::FN_RCS_HEP::F_RCS_HEP_05 to context.sts.orb.rcs.hep;
        allocate Functions::FN_RCS_HEP::F_RCS_HEP_06 to context.sts.orb.rcs.hep;
        allocate Functions::FN_RCS_HEP::F_RCS_HEP_07 to context.sts.orb.rcs.hep;
        allocate Functions::FN_RCS_HEP::F_RCS_HEP_08 to context.sts.orb.rcs.hep;
        allocate Functions::FN_RCS_HEP::F_RCS_HEP_09 to context.sts.orb.rcs.hep;
        allocate Functions::FN_RCS_HEP::F_RCS_HEP_10 to context.sts.orb.rcs.hep;
        allocate Functions::FN_RCS_HEP::F_RCS_HEP_11 to context.sts.orb.rcs.hep;
        allocate Functions::FN_RCS_HEP::F_RCS_HEP_12 to context.sts.orb.rcs.hep;
        allocate Functions::FN_RCS_HTR::F_RCS_HTR_01 to context.sts.orb.rcs.htr;
        allocate Functions::FN_RCS_HTR::F_RCS_HTR_02 to context.sts.orb.rcs.htr;
        allocate Functions::FN_RCS_HTR::F_RCS_HTR_03 to context.sts.orb.rcs.htr;
        allocate Functions::FN_RCS_HTR::F_RCS_HTR_04 to context.sts.orb.rcs.htr;
        allocate Functions::FN_RCS_HTR::F_RCS_HTR_05 to context.sts.orb.rcs.htr;
        allocate Functions::FN_RCS_HTR::F_RCS_HTR_06 to context.sts.orb.rcs.htr;
        allocate Functions::FN_RCS_HTR::F_RCS_HTR_07 to context.sts.orb.rcs.htr;
        allocate Functions::FN_RCS_HTR::F_RCS_HTR_08 to context.sts.orb.rcs.htr;
        allocate Functions::FN_RCS_HTR::F_RCS_HTR_09 to context.sts.orb.rcs.htr;
        allocate Functions::FN_RCS_HTR::F_RCS_HTR_10 to context.sts.orb.rcs.htr;
        allocate Functions::FN_RCS_HTR::F_RCS_HTR_11 to context.sts.orb.rcs.htr;
        allocate Functions::FN_RCS_HTR::F_RCS_HTR_12 to context.sts.orb.rcs.htr;
        allocate Functions::FN_RCS_JET::F_RCS_JET_01 to context.sts.orb.rcs.jet;
        allocate Functions::FN_RCS_JET::F_RCS_JET_02 to context.sts.orb.rcs.jet;
        allocate Functions::FN_RCS_JET::F_RCS_JET_03 to context.sts.orb.rcs.jet;
        allocate Functions::FN_RCS_JET::F_RCS_JET_04 to context.sts.orb.rcs.jet;
        allocate Functions::FN_RCS_JET::F_RCS_JET_05 to context.sts.orb.rcs.jet;
        allocate Functions::FN_RCS_JET::F_RCS_JET_06 to context.sts.orb.rcs.jet;
        allocate Functions::FN_RCS_JET::F_RCS_JET_07 to context.sts.orb.rcs.jet;
        allocate Functions::FN_RCS_JET::F_RCS_JET_08 to context.sts.orb.rcs.jet;
        allocate Functions::FN_RCS_JET::F_RCS_JET_09 to context.sts.orb.rcs.jet;
        allocate Functions::FN_RCS_JET::F_RCS_JET_10 to context.sts.orb.rcs.jet;
        allocate Functions::FN_RCS_JET::F_RCS_JET_11 to context.sts.orb.rcs.jet;
        allocate Functions::FN_RCS_JET::F_RCS_JET_12 to context.sts.orb.rcs.jet;
        allocate Functions::FN_RCS_OPS::F_RCS_OPS_01 to context.sts.orb.rcs.ops;
        allocate Functions::FN_RCS_OPS::F_RCS_OPS_02 to context.sts.orb.rcs.ops;
        allocate Functions::FN_RCS_OPS::F_RCS_OPS_03 to context.sts.orb.rcs.ops;
        allocate Functions::FN_RCS_OPS::F_RCS_OPS_04 to context.sts.orb.rcs.ops;
        allocate Functions::FN_RCS_OPS::F_RCS_OPS_05 to context.sts.orb.rcs.ops;
        allocate Functions::FN_RCS_OPS::F_RCS_OPS_06 to context.sts.orb.rcs.ops;
        allocate Functions::FN_RCS_OPS::F_RCS_OPS_07 to context.sts.orb.rcs.ops;
        allocate Functions::FN_RCS_OPS::F_RCS_OPS_08 to context.sts.orb.rcs.ops;
        allocate Functions::FN_RCS_OPS::F_RCS_OPS_09 to context.sts.orb.rcs.ops;
        allocate Functions::FN_RCS_OPS::F_RCS_OPS_10 to context.sts.orb.rcs.ops;
        allocate Functions::FN_RCS_OPS::F_RCS_OPS_11 to context.sts.orb.rcs.ops;
        allocate Functions::FN_RCS_OPS::F_RCS_OPS_12 to context.sts.orb.rcs.ops;
        allocate Functions::FN_RCS_PRP::F_RCS_PRP_01 to context.sts.orb.rcs.prp;
        allocate Functions::FN_RCS_PRP::F_RCS_PRP_02 to context.sts.orb.rcs.prp;
        allocate Functions::FN_RCS_PRP::F_RCS_PRP_03 to context.sts.orb.rcs.prp;
        allocate Functions::FN_RCS_PRP::F_RCS_PRP_04 to context.sts.orb.rcs.prp;
        allocate Functions::FN_RCS_PRP::F_RCS_PRP_05 to context.sts.orb.rcs.prp;
        allocate Functions::FN_RCS_PRP::F_RCS_PRP_06 to context.sts.orb.rcs.prp;
        allocate Functions::FN_RCS_PRP::F_RCS_PRP_07 to context.sts.orb.rcs.prp;
        allocate Functions::FN_RCS_PRP::F_RCS_PRP_08 to context.sts.orb.rcs.prp;
        allocate Functions::FN_RCS_PRP::F_RCS_PRP_09 to context.sts.orb.rcs.prp;
        allocate Functions::FN_RCS_PRP::F_RCS_PRP_10 to context.sts.orb.rcs.prp;
        allocate Functions::FN_RCS_PRP::F_RCS_PRP_11 to context.sts.orb.rcs.prp;
        allocate Functions::FN_RCS_PRP::F_RCS_PRP_12 to context.sts.orb.rcs.prp;
        allocate Functions::FN_RCS_RJD::F_RCS_RJD_01 to context.sts.orb.rcs.rjd;
        allocate Functions::FN_RCS_RJD::F_RCS_RJD_02 to context.sts.orb.rcs.rjd;
        allocate Functions::FN_RCS_RJD::F_RCS_RJD_03 to context.sts.orb.rcs.rjd;
        allocate Functions::FN_RCS_RJD::F_RCS_RJD_04 to context.sts.orb.rcs.rjd;
        allocate Functions::FN_RCS_RJD::F_RCS_RJD_05 to context.sts.orb.rcs.rjd;
        allocate Functions::FN_RCS_RJD::F_RCS_RJD_06 to context.sts.orb.rcs.rjd;
        allocate Functions::FN_RCS_RJD::F_RCS_RJD_07 to context.sts.orb.rcs.rjd;
        allocate Functions::FN_RCS_RJD::F_RCS_RJD_08 to context.sts.orb.rcs.rjd;
        allocate Functions::FN_RCS_RJD::F_RCS_RJD_09 to context.sts.orb.rcs.rjd;
        allocate Functions::FN_RCS_RJD::F_RCS_RJD_10 to context.sts.orb.rcs.rjd;
        allocate Functions::FN_RCS_RJD::F_RCS_RJD_11 to context.sts.orb.rcs.rjd;
        allocate Functions::FN_RCS_RJD::F_RCS_RJD_12 to context.sts.orb.rcs.rjd;
        allocate Functions::FN_RCS_RM::F_RCS_RM_01 to context.sts.orb.rcs.rm;
        allocate Functions::FN_RCS_RM::F_RCS_RM_02 to context.sts.orb.rcs.rm;
        allocate Functions::FN_RCS_RM::F_RCS_RM_03 to context.sts.orb.rcs.rm;
        allocate Functions::FN_RCS_RM::F_RCS_RM_04 to context.sts.orb.rcs.rm;
        allocate Functions::FN_RCS_RM::F_RCS_RM_05 to context.sts.orb.rcs.rm;
        allocate Functions::FN_RCS_RM::F_RCS_RM_06 to context.sts.orb.rcs.rm;
        allocate Functions::FN_RCS_RM::F_RCS_RM_07 to context.sts.orb.rcs.rm;
        allocate Functions::FN_RCS_RM::F_RCS_RM_08 to context.sts.orb.rcs.rm;
        allocate Functions::FN_RCS_RM::F_RCS_RM_09 to context.sts.orb.rcs.rm;
        allocate Functions::FN_RCS_RM::F_RCS_RM_10 to context.sts.orb.rcs.rm;
        allocate Functions::FN_RCS_RM::F_RCS_RM_11 to context.sts.orb.rcs.rm;
        allocate Functions::FN_RCS_RM::F_RCS_RM_12 to context.sts.orb.rcs.rm;
        allocate Functions::FN_STR::F_STR_01 to context.sts.orb.str;
        allocate Functions::FN_STR::F_STR_02 to context.sts.orb.str;
        allocate Functions::FN_STR::F_STR_03 to context.sts.orb.str;
        allocate Functions::FN_STR::F_STR_04 to context.sts.orb.str;
        allocate Functions::FN_STR::F_STR_05 to context.sts.orb.str;
        allocate Functions::FN_STR::F_STR_06 to context.sts.orb.str;
        allocate Functions::FN_STR::F_STR_07 to context.sts.orb.str;
        allocate Functions::FN_STR::F_STR_08 to context.sts.orb.str;
        allocate Functions::FN_STR_AFT::F_STR_AFT_01 to context.sts.orb.str.aft;
        allocate Functions::FN_STR_AFT::F_STR_AFT_02 to context.sts.orb.str.aft;
        allocate Functions::FN_STR_AFT::F_STR_AFT_03 to context.sts.orb.str.aft;
        allocate Functions::FN_STR_AFT::F_STR_AFT_04 to context.sts.orb.str.aft;
        allocate Functions::FN_STR_AFT::F_STR_AFT_05 to context.sts.orb.str.aft;
        allocate Functions::FN_STR_AFT::F_STR_AFT_06 to context.sts.orb.str.aft;
        allocate Functions::FN_STR_AFT::F_STR_AFT_07 to context.sts.orb.str.aft;
        allocate Functions::FN_STR_CRM::F_STR_CRM_01 to context.sts.orb.str.crm;
        allocate Functions::FN_STR_CRM::F_STR_CRM_02 to context.sts.orb.str.crm;
        allocate Functions::FN_STR_CRM::F_STR_CRM_03 to context.sts.orb.str.crm;
        allocate Functions::FN_STR_CRM::F_STR_CRM_04 to context.sts.orb.str.crm;
        allocate Functions::FN_STR_CRM::F_STR_CRM_05 to context.sts.orb.str.crm;
        allocate Functions::FN_STR_CRM::F_STR_CRM_06 to context.sts.orb.str.crm;
        allocate Functions::FN_STR_CRM::F_STR_CRM_07 to context.sts.orb.str.crm;
        allocate Functions::FN_STR_FWD::F_STR_FWD_01 to context.sts.orb.str.fwd;
        allocate Functions::FN_STR_FWD::F_STR_FWD_02 to context.sts.orb.str.fwd;
        allocate Functions::FN_STR_FWD::F_STR_FWD_03 to context.sts.orb.str.fwd;
        allocate Functions::FN_STR_FWD::F_STR_FWD_04 to context.sts.orb.str.fwd;
        allocate Functions::FN_STR_FWD::F_STR_FWD_05 to context.sts.orb.str.fwd;
        allocate Functions::FN_STR_FWD::F_STR_FWD_06 to context.sts.orb.str.fwd;
        allocate Functions::FN_STR_FWD::F_STR_FWD_07 to context.sts.orb.str.fwd;
        allocate Functions::FN_STR_MID::F_STR_MID_01 to context.sts.orb.str.mid;
        allocate Functions::FN_STR_MID::F_STR_MID_02 to context.sts.orb.str.mid;
        allocate Functions::FN_STR_MID::F_STR_MID_03 to context.sts.orb.str.mid;
        allocate Functions::FN_STR_MID::F_STR_MID_04 to context.sts.orb.str.mid;
        allocate Functions::FN_STR_MID::F_STR_MID_05 to context.sts.orb.str.mid;
        allocate Functions::FN_STR_MID::F_STR_MID_06 to context.sts.orb.str.mid;
        allocate Functions::FN_STR_MID::F_STR_MID_07 to context.sts.orb.str.mid;
        allocate Functions::FN_STR_OPS::F_STR_OPS_01 to context.sts.orb.str.ops;
        allocate Functions::FN_STR_OPS::F_STR_OPS_02 to context.sts.orb.str.ops;
        allocate Functions::FN_STR_OPS::F_STR_OPS_03 to context.sts.orb.str.ops;
        allocate Functions::FN_STR_OPS::F_STR_OPS_04 to context.sts.orb.str.ops;
        allocate Functions::FN_STR_OPS::F_STR_OPS_05 to context.sts.orb.str.ops;
        allocate Functions::FN_STR_OPS::F_STR_OPS_06 to context.sts.orb.str.ops;
        allocate Functions::FN_STR_OPS::F_STR_OPS_07 to context.sts.orb.str.ops;
        allocate Functions::FN_STR_WNG::F_STR_WNG_01 to context.sts.orb.str.wng;
        allocate Functions::FN_STR_WNG::F_STR_WNG_02 to context.sts.orb.str.wng;
        allocate Functions::FN_STR_WNG::F_STR_WNG_03 to context.sts.orb.str.wng;
        allocate Functions::FN_STR_WNG::F_STR_WNG_04 to context.sts.orb.str.wng;
        allocate Functions::FN_STR_WNG::F_STR_WNG_05 to context.sts.orb.str.wng;
        allocate Functions::FN_STR_WNG::F_STR_WNG_06 to context.sts.orb.str.wng;
        allocate Functions::FN_STR_WNG::F_STR_WNG_07 to context.sts.orb.str.wng;
        allocate Functions::FN_STR_WNG::F_STR_WNG_08 to context.sts.orb.str.wng;
        allocate Functions::FN_TCS::F_TCS_01 to context.sts.orb.tcs;
        allocate Functions::FN_TCS::F_TCS_02 to context.sts.orb.tcs;
        allocate Functions::FN_TCS::F_TCS_03 to context.sts.orb.tcs;
        allocate Functions::FN_TCS::F_TCS_04 to context.sts.orb.tcs;
        allocate Functions::FN_TCS_PTC::F_TCS_PTC_01 to context.sts.orb.tcs.ptc;
        allocate Functions::FN_TCS_PTC::F_TCS_PTC_02 to context.sts.orb.tcs.ptc;
        allocate Functions::FN_TCS_PTC::F_TCS_PTC_03 to context.sts.orb.tcs.ptc;
        allocate Functions::FN_TCS_PTC::F_TCS_PTC_04 to context.sts.orb.tcs.ptc;
        allocate Functions::FN_TCS_PTC::F_TCS_PTC_05 to context.sts.orb.tcs.ptc;
        allocate Functions::FN_TCS_PTC::F_TCS_PTC_06 to context.sts.orb.tcs.ptc;
        allocate Functions::FN_TPS::F_TPS_01 to context.sts.orb.tps;
        allocate Functions::FN_TPS::F_TPS_02 to context.sts.orb.tps;
        allocate Functions::FN_TPS::F_TPS_03 to context.sts.orb.tps;
        allocate Functions::FN_TPS::F_TPS_04 to context.sts.orb.tps;
        allocate Functions::FN_TPS::F_TPS_05 to context.sts.orb.tps;
        allocate Functions::FN_TPS::F_TPS_06 to context.sts.orb.tps;
        allocate Functions::FN_SRB::F_SRB_01 to context.sts.srb;
        allocate Functions::FN_SRB::F_SRB_02 to context.sts.srb;
        allocate Functions::FN_SRB::F_SRB_03 to context.sts.srb;
        allocate Functions::FN_SRB::F_SRB_04 to context.sts.srb;
        allocate Functions::FN_SRB_ATT::F_SRB_ATT_01 to context.sts.srb.att;
        allocate Functions::FN_SRB_ATT::F_SRB_ATT_02 to context.sts.srb.att;
        allocate Functions::FN_SRB_ATT::F_SRB_ATT_03 to context.sts.srb.att;
        allocate Functions::FN_SRB_ATT::F_SRB_ATT_04 to context.sts.srb.att;
        allocate Functions::FN_SRB_ATT::F_SRB_ATT_05 to context.sts.srb.att;
        allocate Functions::FN_SRB_ATT::F_SRB_ATT_06 to context.sts.srb.att;
        allocate Functions::FN_SRB_ATT::F_SRB_ATT_07 to context.sts.srb.att;
        allocate Functions::FN_SRB_AVN::F_SRB_AVN_01 to context.sts.srb.avn;
        allocate Functions::FN_SRB_AVN::F_SRB_AVN_02 to context.sts.srb.avn;
        allocate Functions::FN_SRB_AVN::F_SRB_AVN_03 to context.sts.srb.avn;
        allocate Functions::FN_SRB_AVN::F_SRB_AVN_04 to context.sts.srb.avn;
        allocate Functions::FN_SRB_AVN::F_SRB_AVN_05 to context.sts.srb.avn;
        allocate Functions::FN_SRB_AVN::F_SRB_AVN_06 to context.sts.srb.avn;
        allocate Functions::FN_SRB_AVN::F_SRB_AVN_07 to context.sts.srb.avn;
        allocate Functions::FN_SRB_AVN::F_SRB_AVN_08 to context.sts.srb.avn;
        allocate Functions::FN_SRB_HDP::F_SRB_HDP_01 to context.sts.srb.hdp;
        allocate Functions::FN_SRB_HDP::F_SRB_HDP_02 to context.sts.srb.hdp;
        allocate Functions::FN_SRB_HDP::F_SRB_HDP_03 to context.sts.srb.hdp;
        allocate Functions::FN_SRB_HDP::F_SRB_HDP_04 to context.sts.srb.hdp;
        allocate Functions::FN_SRB_HDP::F_SRB_HDP_05 to context.sts.srb.hdp;
        allocate Functions::FN_SRB_HDP::F_SRB_HDP_06 to context.sts.srb.hdp;
        allocate Functions::FN_SRB_HDP::F_SRB_HDP_07 to context.sts.srb.hdp;
        allocate Functions::FN_SRB_MTR::F_SRB_MTR_01 to context.sts.srb.mtr;
        allocate Functions::FN_SRB_MTR::F_SRB_MTR_02 to context.sts.srb.mtr;
        allocate Functions::FN_SRB_MTR::F_SRB_MTR_03 to context.sts.srb.mtr;
        allocate Functions::FN_SRB_MTR::F_SRB_MTR_04 to context.sts.srb.mtr;
        allocate Functions::FN_SRB_MTR::F_SRB_MTR_05 to context.sts.srb.mtr;
        allocate Functions::FN_SRB_MTR::F_SRB_MTR_06 to context.sts.srb.mtr;
        allocate Functions::FN_SRB_MTR::F_SRB_MTR_07 to context.sts.srb.mtr;
        allocate Functions::FN_SRB_MTR::F_SRB_MTR_08 to context.sts.srb.mtr;
        allocate Functions::FN_SRB_MTR::F_SRB_MTR_09 to context.sts.srb.mtr;
        allocate Functions::FN_SRB_REC::F_SRB_REC_01 to context.sts.srb.rec;
        allocate Functions::FN_SRB_REC::F_SRB_REC_02 to context.sts.srb.rec;
        allocate Functions::FN_SRB_REC::F_SRB_REC_03 to context.sts.srb.rec;
        allocate Functions::FN_SRB_REC::F_SRB_REC_04 to context.sts.srb.rec;
        allocate Functions::FN_SRB_REC::F_SRB_REC_05 to context.sts.srb.rec;
        allocate Functions::FN_SRB_REC::F_SRB_REC_06 to context.sts.srb.rec;
        allocate Functions::FN_SRB_TVC::F_SRB_TVC_01 to context.sts.srb.tvc;
        allocate Functions::FN_SRB_TVC::F_SRB_TVC_02 to context.sts.srb.tvc;
        allocate Functions::FN_SRB_TVC::F_SRB_TVC_03 to context.sts.srb.tvc;
        allocate Functions::FN_SRB_TVC::F_SRB_TVC_04 to context.sts.srb.tvc;
        allocate Functions::FN_SRB_TVC::F_SRB_TVC_05 to context.sts.srb.tvc;
        allocate Functions::FN_SRB_TVC::F_SRB_TVC_06 to context.sts.srb.tvc;
        allocate Functions::FN_SRB_TVC::F_SRB_TVC_07 to context.sts.srb.tvc;
        allocate Functions::FN_SRB_TVC::F_SRB_TVC_08 to context.sts.srb.tvc;
    }
    // ---- 物理の割付：系の部品 → 機器、機能 → 機器
    package PhysicalAllocation {
        allocate context.sts.orb.ct to Physical::orbiterLayout.avb3a.phy_ct_01;
        allocate Functions::FN_CT_SBD::F_CT_SBD_07 to Physical::orbiterLayout.avb3a.phy_ct_01;
        allocate Functions::FN_CT_SBD::F_CT_SBD_08 to Physical::orbiterLayout.avb3a.phy_ct_01;
        allocate context.sts.orb.ct to Physical::orbiterLayout.fwd.phy_ct_02;
        allocate Functions::FN_CT_SBD::F_CT_SBD_04 to Physical::orbiterLayout.fwd.phy_ct_02;
        allocate Functions::FN_CT_SBD::F_CT_SBD_12 to Physical::orbiterLayout.fwd.phy_ct_02;
        allocate context.sts.orb.ct to Physical::orbiterLayout.plb.phy_ct_03;
        allocate Functions::FN_CT_KU::F_CT_KU_01 to Physical::orbiterLayout.plb.phy_ct_03;
        allocate Functions::FN_CT_KU::F_CT_KU_06 to Physical::orbiterLayout.plb.phy_ct_03;
        allocate Functions::FN_CT_KU::F_CT_KU_07 to Physical::orbiterLayout.plb.phy_ct_03;
        allocate Functions::FN_CT_KU::F_CT_KU_09 to Physical::orbiterLayout.plb.phy_ct_03;
        allocate context.sts.orb.ct to Physical::orbiterLayout.avb3a.phy_ct_04;
        allocate Functions::FN_CT_KU::F_CT_KU_01 to Physical::orbiterLayout.avb3a.phy_ct_04;
        allocate Functions::FN_CT_KU::F_CT_KU_05 to Physical::orbiterLayout.avb3a.phy_ct_04;
        allocate Functions::FN_CT_KU::F_CT_KU_06 to Physical::orbiterLayout.avb3a.phy_ct_04;
        allocate Functions::FN_CT_KU::F_CT_KU_10 to Physical::orbiterLayout.avb3a.phy_ct_04;
        allocate context.sts.orb.ct to Physical::orbiterLayout.avb3a.phy_ct_05;
        allocate Functions::FN_CT_UHF::F_CT_UHF_01 to Physical::orbiterLayout.avb3a.phy_ct_05;
        allocate Functions::FN_CT_UHF::F_CT_UHF_02 to Physical::orbiterLayout.avb3a.phy_ct_05;
        allocate Functions::FN_CT_UHF::F_CT_UHF_03 to Physical::orbiterLayout.avb3a.phy_ct_05;
        allocate Functions::FN_CT_UHF::F_CT_UHF_04 to Physical::orbiterLayout.avb3a.phy_ct_05;
        allocate context.sts.orb.ct to Physical::orbiterLayout.avb1.phy_ct_06;
        allocate Functions::FN_CT_AUD::F_CT_AUD_02 to Physical::orbiterLayout.avb1.phy_ct_06;
        allocate Functions::FN_CT_AUD::F_CT_AUD_05 to Physical::orbiterLayout.avb1.phy_ct_06;
        allocate Functions::FN_CT_AUD::F_CT_AUD_06 to Physical::orbiterLayout.avb1.phy_ct_06;
        allocate context.sts.orb.ct to Physical::orbiterLayout.avb3a.phy_ct_07;
        allocate Functions::FN_CT_SBD::F_CT_SBD_03 to Physical::orbiterLayout.avb3a.phy_ct_07;
        allocate Functions::FN_CT_SBD::F_CT_SBD_06 to Physical::orbiterLayout.avb3a.phy_ct_07;
        allocate Functions::FN_CT_SBD::F_CT_SBD_07 to Physical::orbiterLayout.avb3a.phy_ct_07;
        allocate Functions::FN_CT_SBD::F_CT_SBD_08 to Physical::orbiterLayout.avb3a.phy_ct_07;
        allocate context.sts.orb.ct to Physical::orbiterLayout.fwd.phy_ct_08;
        allocate Functions::FN_CT_SBD::F_CT_SBD_04 to Physical::orbiterLayout.fwd.phy_ct_08;
        allocate Functions::FN_CT_SBD::F_CT_SBD_12 to Physical::orbiterLayout.fwd.phy_ct_08;
        allocate Functions::FN_CT_UHF::F_CT_UHF_04 to Physical::orbiterLayout.fwd.phy_ct_08;
        allocate Functions::FN_CT_UHF::F_CT_UHF_07 to Physical::orbiterLayout.fwd.phy_ct_08;
        allocate context.sts.orb.ct to Physical::orbiterLayout.avb3b.phy_ct_09;
        allocate Functions::FN_CT_KU::F_CT_KU_02 to Physical::orbiterLayout.avb3b.phy_ct_09;
        allocate Functions::FN_CT_KU::F_CT_KU_05 to Physical::orbiterLayout.avb3b.phy_ct_09;
        allocate context.sts.orb.ct to Physical::orbiterLayout.avbf.phy_ct_10;
        allocate Functions::FN_CT_INST::F_CT_INST_02 to Physical::orbiterLayout.avbf.phy_ct_10;
        allocate Functions::FN_CT_INST::F_CT_INST_04 to Physical::orbiterLayout.avbf.phy_ct_10;
        allocate Functions::FN_CT_INST::F_CT_INST_05 to Physical::orbiterLayout.avbf.phy_ct_10;
        allocate Functions::FN_CT_INST::F_CT_INST_06 to Physical::orbiterLayout.avbf.phy_ct_10;
        allocate context.sts.orb.ct to Physical::orbiterLayout.airlock.phy_ct_11;
        allocate Functions::FN_CT_UHF::F_CT_UHF_01 to Physical::orbiterLayout.airlock.phy_ct_11;
        allocate Functions::FN_CT_UHF::F_CT_UHF_06 to Physical::orbiterLayout.airlock.phy_ct_11;
        allocate Functions::FN_CT_UHF::F_CT_UHF_07 to Physical::orbiterLayout.airlock.phy_ct_11;
        allocate Functions::FN_CT_UHF::F_CT_UHF_08 to Physical::orbiterLayout.airlock.phy_ct_11;
        allocate context.sts.orb.ct to Physical::orbiterLayout.fd.phy_ct_12;
        allocate Functions::FN_CT_CCTV::F_CT_CCTV_04 to Physical::orbiterLayout.fd.phy_ct_12;
        allocate Functions::FN_CT_CCTV::F_CT_CCTV_07 to Physical::orbiterLayout.fd.phy_ct_12;
        allocate context.sts.orb.dps to Physical::orbiterLayout.avbf.phy_dps_01;
        allocate Functions::FN_DPS::F_DPS_01 to Physical::orbiterLayout.avbf.phy_dps_01;
        allocate Functions::FN_DPS::F_DPS_02 to Physical::orbiterLayout.avbf.phy_dps_01;
        allocate Functions::FN_DPS::F_DPS_03 to Physical::orbiterLayout.avbf.phy_dps_01;
        allocate Functions::FN_DPS::F_DPS_04 to Physical::orbiterLayout.avbf.phy_dps_01;
        allocate context.sts.orb.dps to Physical::orbiterLayout.avbf.phy_dps_02;
        allocate Functions::FN_DPS_FSW::F_DPS_FSW_06 to Physical::orbiterLayout.avbf.phy_dps_02;
        allocate Functions::FN_DPS_FSW::F_DPS_FSW_07 to Physical::orbiterLayout.avbf.phy_dps_02;
        allocate Functions::FN_DPS_FSW::F_DPS_FSW_08 to Physical::orbiterLayout.avbf.phy_dps_02;
        allocate Functions::FN_DPS_FSW::F_DPS_FSW_09 to Physical::orbiterLayout.avbf.phy_dps_02;
        allocate context.sts.orb.dps to Physical::orbiterLayout.multi.phy_dps_03;
        allocate Functions::FN_DPS_BUS::F_DPS_BUS_03 to Physical::orbiterLayout.multi.phy_dps_03;
        allocate Functions::FN_DPS_BUS::F_DPS_BUS_04 to Physical::orbiterLayout.multi.phy_dps_03;
        allocate Functions::FN_DPS_BUS::F_DPS_BUS_06 to Physical::orbiterLayout.multi.phy_dps_03;
        allocate Functions::FN_DPS_BUS::F_DPS_BUS_08 to Physical::orbiterLayout.multi.phy_dps_03;
        allocate context.sts.orb.dps to Physical::orbiterLayout.fd.phy_dps_04;
        allocate Functions::FN_DPS_MEDS::F_DPS_MEDS_01 to Physical::orbiterLayout.fd.phy_dps_04;
        allocate Functions::FN_DPS_MEDS::F_DPS_MEDS_02 to Physical::orbiterLayout.fd.phy_dps_04;
        allocate Functions::FN_DPS_MEDS::F_DPS_MEDS_03 to Physical::orbiterLayout.fd.phy_dps_04;
        allocate Functions::FN_DPS_MEDS::F_DPS_MEDS_04 to Physical::orbiterLayout.fd.phy_dps_04;
        allocate context.sts.orb.dps to Physical::orbiterLayout.avb3b.phy_dps_05;
        allocate Functions::FN_DPS_MTU::F_DPS_MTU_01 to Physical::orbiterLayout.avb3b.phy_dps_05;
        allocate Functions::FN_DPS_MTU::F_DPS_MTU_02 to Physical::orbiterLayout.avb3b.phy_dps_05;
        allocate Functions::FN_DPS_MTU::F_DPS_MTU_03 to Physical::orbiterLayout.avb3b.phy_dps_05;
        allocate Functions::FN_DPS_MTU::F_DPS_MTU_04 to Physical::orbiterLayout.avb3b.phy_dps_05;
        allocate context.sts.orb.dps to Physical::orbiterLayout.multi.phy_dps_06;
        allocate Functions::FN_DPS_BUS::F_DPS_BUS_01 to Physical::orbiterLayout.multi.phy_dps_06;
        allocate Functions::FN_DPS_BUS::F_DPS_BUS_02 to Physical::orbiterLayout.multi.phy_dps_06;
        allocate Functions::FN_DPS_BUS::F_DPS_BUS_03 to Physical::orbiterLayout.multi.phy_dps_06;
        allocate Functions::FN_DPS_BUS::F_DPS_BUS_04 to Physical::orbiterLayout.multi.phy_dps_06;
        allocate context.sts.orb.dps to Physical::orbiterLayout.avba.phy_dps_07;
        allocate Functions::FN_DPS_ASC::F_DPS_ASC_01 to Physical::orbiterLayout.avba.phy_dps_07;
        allocate Functions::FN_DPS_ASC::F_DPS_ASC_02 to Physical::orbiterLayout.avba.phy_dps_07;
        allocate Functions::FN_DPS_ASC::F_DPS_ASC_03 to Physical::orbiterLayout.avba.phy_dps_07;
        allocate Functions::FN_DPS_ASC::F_DPS_ASC_04 to Physical::orbiterLayout.avba.phy_dps_07;
        allocate context.sts.orb.gnc to Physical::orbiterLayout.fd.phy_gnc_01;
        allocate Functions::FN_GNC::F_GNC_01 to Physical::orbiterLayout.fd.phy_gnc_01;
        allocate Functions::FN_GNC::F_GNC_03 to Physical::orbiterLayout.fd.phy_gnc_01;
        allocate context.sts.orb.gnc to Physical::orbiterLayout.fwd.phy_gnc_02;
        allocate Functions::FN_GNC_INS::F_GNC_INS_08 to Physical::orbiterLayout.fwd.phy_gnc_02;
        allocate Functions::FN_GNC_INS::F_GNC_INS_09 to Physical::orbiterLayout.fwd.phy_gnc_02;
        allocate Functions::FN_GNC_INS::F_GNC_INS_11 to Physical::orbiterLayout.fwd.phy_gnc_02;
        allocate context.sts.orb.gnc to Physical::orbiterLayout.avbf.phy_gnc_03;
        allocate Functions::FN_GNC::F_GNC_01 to Physical::orbiterLayout.avbf.phy_gnc_03;
        allocate context.sts.orb.gnc to Physical::orbiterLayout.multi.phy_gnc_04;
        allocate Functions::FN_GNC::F_GNC_01 to Physical::orbiterLayout.multi.phy_gnc_04;
        allocate context.sts.orb.gnc to Physical::orbiterLayout.avbf.phy_gnc_05;
        allocate Functions::FN_GNC::F_GNC_01 to Physical::orbiterLayout.avbf.phy_gnc_05;
        allocate context.sts.orb.gnc to Physical::orbiterLayout.avba.phy_gnc_06;
        allocate Functions::FN_GNC::F_GNC_05 to Physical::orbiterLayout.avba.phy_gnc_06;
        allocate context.sts.orb.rcs to Physical::orbiterLayout.frcs.phy_rcs_01;
        allocate Functions::FN_RCS_JET::F_RCS_JET_01 to Physical::orbiterLayout.frcs.phy_rcs_01;
        allocate Functions::FN_RCS_JET::F_RCS_JET_02 to Physical::orbiterLayout.frcs.phy_rcs_01;
        allocate Functions::FN_RCS_JET::F_RCS_JET_03 to Physical::orbiterLayout.frcs.phy_rcs_01;
        allocate Functions::FN_RCS_JET::F_RCS_JET_04 to Physical::orbiterLayout.frcs.phy_rcs_01;
        allocate context.sts.orb.rcs to Physical::orbiterLayout.pod.phy_rcs_02;
        allocate Functions::FN_RCS_JET::F_RCS_JET_01 to Physical::orbiterLayout.pod.phy_rcs_02;
        allocate Functions::FN_RCS_JET::F_RCS_JET_02 to Physical::orbiterLayout.pod.phy_rcs_02;
        allocate Functions::FN_RCS_JET::F_RCS_JET_03 to Physical::orbiterLayout.pod.phy_rcs_02;
        allocate Functions::FN_RCS_JET::F_RCS_JET_04 to Physical::orbiterLayout.pod.phy_rcs_02;
        allocate context.sts.orb.rcs to Physical::orbiterLayout.frcs.phy_rcs_03;
        allocate Functions::FN_RCS_PRP::F_RCS_PRP_01 to Physical::orbiterLayout.frcs.phy_rcs_03;
        allocate Functions::FN_RCS_PRP::F_RCS_PRP_02 to Physical::orbiterLayout.frcs.phy_rcs_03;
        allocate Functions::FN_RCS_PRP::F_RCS_PRP_03 to Physical::orbiterLayout.frcs.phy_rcs_03;
        allocate Functions::FN_RCS_PRP::F_RCS_PRP_04 to Physical::orbiterLayout.frcs.phy_rcs_03;
        allocate Functions::FN_RCS_HEP::F_RCS_HEP_01 to Physical::orbiterLayout.frcs.phy_rcs_03;
        allocate Functions::FN_RCS_HEP::F_RCS_HEP_02 to Physical::orbiterLayout.frcs.phy_rcs_03;
        allocate Functions::FN_RCS_HEP::F_RCS_HEP_08 to Physical::orbiterLayout.frcs.phy_rcs_03;
        allocate context.sts.orb.rcs to Physical::orbiterLayout.pod.phy_rcs_04;
        allocate Functions::FN_RCS_PRP::F_RCS_PRP_01 to Physical::orbiterLayout.pod.phy_rcs_04;
        allocate Functions::FN_RCS_PRP::F_RCS_PRP_02 to Physical::orbiterLayout.pod.phy_rcs_04;
        allocate Functions::FN_RCS_PRP::F_RCS_PRP_03 to Physical::orbiterLayout.pod.phy_rcs_04;
        allocate Functions::FN_RCS_PRP::F_RCS_PRP_04 to Physical::orbiterLayout.pod.phy_rcs_04;
        allocate Functions::FN_RCS_HEP::F_RCS_HEP_01 to Physical::orbiterLayout.pod.phy_rcs_04;
        allocate Functions::FN_RCS_HEP::F_RCS_HEP_02 to Physical::orbiterLayout.pod.phy_rcs_04;
        allocate Functions::FN_RCS_HEP::F_RCS_HEP_08 to Physical::orbiterLayout.pod.phy_rcs_04;
        allocate context.sts.orb.rcs to Physical::orbiterLayout.avbf.phy_rcs_05;
        allocate Functions::FN_RCS_RJD::F_RCS_RJD_01 to Physical::orbiterLayout.avbf.phy_rcs_05;
        allocate Functions::FN_RCS_RJD::F_RCS_RJD_02 to Physical::orbiterLayout.avbf.phy_rcs_05;
        allocate Functions::FN_RCS_RJD::F_RCS_RJD_03 to Physical::orbiterLayout.avbf.phy_rcs_05;
        allocate context.sts.orb.rcs to Physical::orbiterLayout.pod.phy_rcs_06;
        allocate Functions::FN_RCS_PRP::F_RCS_PRP_04 to Physical::orbiterLayout.pod.phy_rcs_06;
        allocate Functions::FN_RCS_PRP::F_RCS_PRP_07 to Physical::orbiterLayout.pod.phy_rcs_06;
        allocate Functions::FN_RCS_PRP::F_RCS_PRP_09 to Physical::orbiterLayout.pod.phy_rcs_06;
        allocate Functions::FN_RCS_PRP::F_RCS_PRP_10 to Physical::orbiterLayout.pod.phy_rcs_06;
        allocate context.sts.orb.rcs to Physical::orbiterLayout.avba.phy_rcs_07;
        allocate Functions::FN_RCS_RJD::F_RCS_RJD_01 to Physical::orbiterLayout.avba.phy_rcs_07;
        allocate Functions::FN_RCS_RJD::F_RCS_RJD_02 to Physical::orbiterLayout.avba.phy_rcs_07;
        allocate Functions::FN_RCS_RJD::F_RCS_RJD_04 to Physical::orbiterLayout.avba.phy_rcs_07;
        allocate Functions::FN_RCS_RJD::F_RCS_RJD_06 to Physical::orbiterLayout.avba.phy_rcs_07;
        allocate context.sts.orb.rcs to Physical::orbiterLayout.multi.phy_rcs_08;
        allocate Functions::FN_RCS_HTR::F_RCS_HTR_01 to Physical::orbiterLayout.multi.phy_rcs_08;
        allocate Functions::FN_RCS_HTR::F_RCS_HTR_02 to Physical::orbiterLayout.multi.phy_rcs_08;
        allocate Functions::FN_RCS_HTR::F_RCS_HTR_03 to Physical::orbiterLayout.multi.phy_rcs_08;
        allocate Functions::FN_RCS_HTR::F_RCS_HTR_05 to Physical::orbiterLayout.multi.phy_rcs_08;
        allocate context.sts.orb.eps to Physical::orbiterLayout.mid.phy_eps_01;
        allocate Functions::FN_EPS::F_EPS_01 to Physical::orbiterLayout.mid.phy_eps_01;
        allocate Functions::FN_EPS::F_EPS_03 to Physical::orbiterLayout.mid.phy_eps_01;
        allocate Functions::FN_EPS::F_EPS_04 to Physical::orbiterLayout.mid.phy_eps_01;
        allocate context.sts.orb.eps to Physical::orbiterLayout.mid.phy_eps_02;
        allocate Functions::FN_EPS::F_EPS_01 to Physical::orbiterLayout.mid.phy_eps_02;
        allocate Functions::FN_EPS::F_EPS_02 to Physical::orbiterLayout.mid.phy_eps_02;
        allocate context.sts.orb.eps to Physical::orbiterLayout.avbf.phy_eps_03;
        allocate Functions::FN_EPS::F_EPS_01 to Physical::orbiterLayout.avbf.phy_eps_03;
        allocate context.sts.orb.eps to Physical::orbiterLayout.multi.phy_eps_04;
        allocate Functions::FN_EPS::F_EPS_01 to Physical::orbiterLayout.multi.phy_eps_04;
        allocate Functions::FN_EPS::F_EPS_04 to Physical::orbiterLayout.multi.phy_eps_04;
        allocate context.sts.orb.eps to Physical::orbiterLayout.multi.phy_eps_05;
        allocate Functions::FN_EPS::F_EPS_01 to Physical::orbiterLayout.multi.phy_eps_05;
        allocate context.sts.orb.eclss to Physical::orbiterLayout.leb.phy_eclss_01;
        allocate Functions::FN_ECLSS::F_ECLSS_01 to Physical::orbiterLayout.leb.phy_eclss_01;
        allocate Functions::FN_ECLSS::F_ECLSS_04 to Physical::orbiterLayout.leb.phy_eclss_01;
        allocate context.sts.orb.eclss to Physical::orbiterLayout.leb.phy_eclss_02;
        allocate Functions::FN_ECLSS::F_ECLSS_01 to Physical::orbiterLayout.leb.phy_eclss_02;
        allocate Functions::FN_ECLSS::F_ECLSS_02 to Physical::orbiterLayout.leb.phy_eclss_02;
        allocate context.sts.orb.eclss to Physical::orbiterLayout.plb.phy_eclss_03;
        allocate Functions::FN_ECLSS::F_ECLSS_03 to Physical::orbiterLayout.plb.phy_eclss_03;
        allocate context.sts.orb.eclss to Physical::orbiterLayout.mid.phy_eclss_04;
        allocate Functions::FN_ECLSS::F_ECLSS_01 to Physical::orbiterLayout.mid.phy_eclss_04;
        allocate Functions::FN_ECLSS::F_ECLSS_02 to Physical::orbiterLayout.mid.phy_eclss_04;
        allocate context.sts.orb.eclss to Physical::orbiterLayout.plb.phy_eclss_05;
        allocate Functions::FN_ECLSS::F_ECLSS_01 to Physical::orbiterLayout.plb.phy_eclss_05;
        allocate Functions::FN_ECLSS::F_ECLSS_05 to Physical::orbiterLayout.plb.phy_eclss_05;
        allocate context.sts.orb.eclss to Physical::orbiterLayout.aft.phy_eclss_06;
        allocate Functions::FN_ECLSS::F_ECLSS_05 to Physical::orbiterLayout.aft.phy_eclss_06;
        allocate Functions::FN_ECLSS::F_ECLSS_06 to Physical::orbiterLayout.aft.phy_eclss_06;
        allocate context.sts.orb.eclss to Physical::orbiterLayout.mid.phy_eclss_07;
        allocate Functions::FN_ECL_ATCS::F_ECL_ATCS_01 to Physical::orbiterLayout.mid.phy_eclss_07;
        allocate Functions::FN_ECL_ATCS::F_ECL_ATCS_02 to Physical::orbiterLayout.mid.phy_eclss_07;
        allocate Functions::FN_ECL_ATCS::F_ECL_ATCS_03 to Physical::orbiterLayout.mid.phy_eclss_07;
        allocate context.sts.orb.eclss to Physical::orbiterLayout.multi.phy_eclss_08;
        allocate Functions::FN_ECL_ATCS::F_ECL_ATCS_02 to Physical::orbiterLayout.multi.phy_eclss_08;
        allocate Functions::FN_ECL_ATCS::F_ECL_ATCS_07 to Physical::orbiterLayout.multi.phy_eclss_08;
        allocate context.sts.orb.eclss to Physical::orbiterLayout.aft.phy_eclss_09;
        allocate Functions::FN_ECL_ATCS::F_ECL_ATCS_01 to Physical::orbiterLayout.aft.phy_eclss_09;
        allocate Functions::FN_APU_CIR::F_APU_CIR_02 to Physical::orbiterLayout.aft.phy_eclss_09;
        allocate Functions::FN_APU_CIR::F_APU_CIR_07 to Physical::orbiterLayout.aft.phy_eclss_09;
        allocate Functions::FN_APU_CIR::F_APU_CIR_11 to Physical::orbiterLayout.aft.phy_eclss_09;
        allocate context.sts.orb.eclss to Physical::orbiterLayout.aft.phy_eclss_10;
        allocate Functions::FN_ECL_ATCS::F_ECL_ATCS_03 to Physical::orbiterLayout.aft.phy_eclss_10;
        allocate Functions::FN_ECL_ATCS::F_ECL_ATCS_05 to Physical::orbiterLayout.aft.phy_eclss_10;
        allocate context.sts.orb.eclss to Physical::orbiterLayout.multi.phy_eclss_11;
        allocate Functions::FN_ECL_ARS::F_ECL_ARS_02 to Physical::orbiterLayout.multi.phy_eclss_11;
        allocate Functions::FN_ECL_ARS::F_ECL_ARS_05 to Physical::orbiterLayout.multi.phy_eclss_11;
        allocate context.sts.orb.eclss to Physical::orbiterLayout.leb.phy_eclss_12;
        allocate Functions::FN_ECL_ARS::F_ECL_ARS_01 to Physical::orbiterLayout.leb.phy_eclss_12;
        allocate Functions::FN_ECL_ARS::F_ECL_ARS_03 to Physical::orbiterLayout.leb.phy_eclss_12;
        allocate context.sts.orb.eclss to Physical::orbiterLayout.leb.phy_eclss_13;
        allocate Functions::FN_ECL_ARS::F_ECL_ARS_01 to Physical::orbiterLayout.leb.phy_eclss_13;
        allocate Functions::FN_ECL_ARS::F_ECL_ARS_02 to Physical::orbiterLayout.leb.phy_eclss_13;
        allocate Functions::FN_ECL_ARS::F_ECL_ARS_04 to Physical::orbiterLayout.leb.phy_eclss_13;
        allocate Functions::FN_ECL_ARS::F_ECL_ARS_08 to Physical::orbiterLayout.leb.phy_eclss_13;
        allocate context.sts.orb.eclss to Physical::orbiterLayout.avbf.phy_eclss_14;
        allocate Functions::FN_ECL_ARS::F_ECL_ARS_07 to Physical::orbiterLayout.avbf.phy_eclss_14;
        allocate context.sts.orb.eclss to Physical::orbiterLayout.fd.phy_eclss_15;
        allocate Functions::FN_ECL_ARS::F_ECL_ARS_07 to Physical::orbiterLayout.fd.phy_eclss_15;
        allocate context.sts.orb.eclss to Physical::orbiterLayout.avbf.phy_eclss_16;
        allocate Functions::FN_ECL_ARS::F_ECL_ARS_07 to Physical::orbiterLayout.avbf.phy_eclss_16;
        allocate context.sts.orb.eclss to Physical::orbiterLayout.multi.phy_eclss_17;
        allocate Functions::FN_ECL_ARS::F_ECL_ARS_02 to Physical::orbiterLayout.multi.phy_eclss_17;
        allocate Functions::FN_ECL_ARS::F_ECL_ARS_06 to Physical::orbiterLayout.multi.phy_eclss_17;
        allocate Functions::FN_ECL_ARS::F_ECL_ARS_07 to Physical::orbiterLayout.multi.phy_eclss_17;
        allocate context.sts.orb.eclss to Physical::orbiterLayout.multi.phy_eclss_18;
        allocate Functions::FN_ECL_PCS::F_ECL_PCS_01 to Physical::orbiterLayout.multi.phy_eclss_18;
        allocate Functions::FN_ECL_PCS::F_ECL_PCS_02 to Physical::orbiterLayout.multi.phy_eclss_18;
        allocate Functions::FN_ECL_PCS::F_ECL_PCS_03 to Physical::orbiterLayout.multi.phy_eclss_18;
        allocate Functions::FN_ECL_PCS::F_ECL_PCS_05 to Physical::orbiterLayout.multi.phy_eclss_18;
        allocate context.sts.orb.eclss to Physical::orbiterLayout.multi.phy_eclss_19;
        allocate Functions::FN_ECL_PCS::F_ECL_PCS_01 to Physical::orbiterLayout.multi.phy_eclss_19;
        allocate Functions::FN_ECL_PCS::F_ECL_PCS_02 to Physical::orbiterLayout.multi.phy_eclss_19;
        allocate Functions::FN_ECL_PCS::F_ECL_PCS_03 to Physical::orbiterLayout.multi.phy_eclss_19;
        allocate Functions::FN_ECL_PCS::F_ECL_PCS_06 to Physical::orbiterLayout.multi.phy_eclss_19;
        allocate context.sts.orb.eclss to Physical::orbiterLayout.md.phy_eclss_20;
        allocate Functions::FN_ECL_PCS::F_ECL_PCS_02 to Physical::orbiterLayout.md.phy_eclss_20;
        allocate Functions::FN_ECL_PCS::F_ECL_PCS_03 to Physical::orbiterLayout.md.phy_eclss_20;
        allocate Functions::FN_ECL_PCS::F_ECL_PCS_10 to Physical::orbiterLayout.md.phy_eclss_20;
        allocate Functions::FN_ECL_PCS::F_ECL_PCS_11 to Physical::orbiterLayout.md.phy_eclss_20;
        allocate context.sts.orb.eclss to Physical::orbiterLayout.md.phy_eclss_21;
        allocate Functions::FN_ECL_PCS::F_ECL_PCS_04 to Physical::orbiterLayout.md.phy_eclss_21;
        allocate context.sts.orb.eclss to Physical::orbiterLayout.multi.phy_eclss_22;
        allocate Functions::FN_ECL_PCS::F_ECL_PCS_10 to Physical::orbiterLayout.multi.phy_eclss_22;
        allocate Functions::FN_ECL_PCS::F_ECL_PCS_11 to Physical::orbiterLayout.multi.phy_eclss_22;
        allocate context.sts.orb.eclss to Physical::orbiterLayout.leb.phy_eclss_23;
        allocate Functions::FN_ECL_H2O::F_ECL_H2O_01 to Physical::orbiterLayout.leb.phy_eclss_23;
        allocate Functions::FN_ECL_H2O::F_ECL_H2O_04 to Physical::orbiterLayout.leb.phy_eclss_23;
        allocate Functions::FN_ECL_H2O::F_ECL_H2O_05 to Physical::orbiterLayout.leb.phy_eclss_23;
        allocate context.sts.orb.eclss to Physical::orbiterLayout.leb.phy_eclss_24;
        allocate Functions::FN_ECL_H2O::F_ECL_H2O_01 to Physical::orbiterLayout.leb.phy_eclss_24;
        allocate Functions::FN_ECL_H2O::F_ECL_H2O_02 to Physical::orbiterLayout.leb.phy_eclss_24;
        allocate Functions::FN_ECL_H2O::F_ECL_H2O_06 to Physical::orbiterLayout.leb.phy_eclss_24;
        allocate Functions::FN_ECL_H2O::F_ECL_H2O_07 to Physical::orbiterLayout.leb.phy_eclss_24;
        allocate context.sts.orb.eclss to Physical::orbiterLayout.multi.phy_eclss_25;
        allocate Functions::FN_ECL_H2O::F_ECL_H2O_06 to Physical::orbiterLayout.multi.phy_eclss_25;
        allocate Functions::FN_ECL_H2O::F_ECL_H2O_08 to Physical::orbiterLayout.multi.phy_eclss_25;
        allocate context.sts.orb.eclss to Physical::orbiterLayout.md.phy_eclss_26;
        allocate Functions::FN_ECL_H2O::F_ECL_H2O_08 to Physical::orbiterLayout.md.phy_eclss_26;
        allocate Functions::FN_ECL_H2O::F_ECL_H2O_09 to Physical::orbiterLayout.md.phy_eclss_26;
        allocate context.sts.orb.eclss to Physical::orbiterLayout.md.phy_eclss_27;
        allocate Functions::FN_ECL_WCS::F_ECL_WCS_01 to Physical::orbiterLayout.md.phy_eclss_27;
        allocate Functions::FN_ECL_WCS::F_ECL_WCS_02 to Physical::orbiterLayout.md.phy_eclss_27;
        allocate Functions::FN_ECL_WCS::F_ECL_WCS_03 to Physical::orbiterLayout.md.phy_eclss_27;
        allocate Functions::FN_ECL_WCS::F_ECL_WCS_04 to Physical::orbiterLayout.md.phy_eclss_27;
        allocate context.sts.orb.eclss to Physical::orbiterLayout.multi.phy_eclss_28;
        allocate Functions::FN_ECL_WCS::F_ECL_WCS_03 to Physical::orbiterLayout.multi.phy_eclss_28;
        allocate Functions::FN_ECL_WCS::F_ECL_WCS_06 to Physical::orbiterLayout.multi.phy_eclss_28;
        allocate Functions::FN_ECL_WCS::F_ECL_WCS_08 to Physical::orbiterLayout.multi.phy_eclss_28;
        allocate context.sts.orb.eclss to Physical::orbiterLayout.multi.phy_eclss_29;
        allocate Functions::FN_ECL_ARS::F_ECL_ARS_01 to Physical::orbiterLayout.multi.phy_eclss_29;
        allocate Functions::FN_ECL_ARS::F_ECL_ARS_02 to Physical::orbiterLayout.multi.phy_eclss_29;
        allocate Functions::FN_ECL_ARS::F_ECL_ARS_03 to Physical::orbiterLayout.multi.phy_eclss_29;
        allocate context.sts.orb.eclss to Physical::orbiterLayout.multi.phy_eclss_30;
        allocate Functions::FN_ECL_ARS::F_ECL_ARS_01 to Physical::orbiterLayout.multi.phy_eclss_30;
        allocate Functions::FN_ECL_ARS::F_ECL_ARS_02 to Physical::orbiterLayout.multi.phy_eclss_30;
        allocate Functions::FN_ECL_ARS::F_ECL_ARS_03 to Physical::orbiterLayout.multi.phy_eclss_30;
        allocate context.sts.orb.eclss to Physical::orbiterLayout.multi.phy_eclss_31;
        allocate Functions::FN_ECL_FDS::F_ECL_FDS_01 to Physical::orbiterLayout.multi.phy_eclss_31;
        allocate Functions::FN_ECL_FDS::F_ECL_FDS_04 to Physical::orbiterLayout.multi.phy_eclss_31;
        allocate Functions::FN_ECL_FDS::F_ECL_FDS_05 to Physical::orbiterLayout.multi.phy_eclss_31;
        allocate Functions::FN_ECL_FDS::F_ECL_FDS_06 to Physical::orbiterLayout.multi.phy_eclss_31;
        allocate context.sts.orb.eclss to Physical::orbiterLayout.multi.phy_eclss_32;
        allocate Functions::FN_ECL_WCS::F_ECL_WCS_01 to Physical::orbiterLayout.multi.phy_eclss_32;
        allocate Functions::FN_ECL_WCS::F_ECL_WCS_03 to Physical::orbiterLayout.multi.phy_eclss_32;
        allocate Functions::FN_ECL_WCS::F_ECL_WCS_06 to Physical::orbiterLayout.multi.phy_eclss_32;
        allocate Functions::FN_ECL_WCS::F_ECL_WCS_08 to Physical::orbiterLayout.multi.phy_eclss_32;
        allocate context.sts.orb.eclss to Physical::orbiterLayout.multi.phy_eclss_33;
        allocate Functions::FN_ECL_H2O::F_ECL_H2O_01 to Physical::orbiterLayout.multi.phy_eclss_33;
        allocate Functions::FN_ECL_H2O::F_ECL_H2O_02 to Physical::orbiterLayout.multi.phy_eclss_33;
        allocate Functions::FN_ECL_H2O::F_ECL_H2O_03 to Physical::orbiterLayout.multi.phy_eclss_33;
        allocate Functions::FN_ECL_H2O::F_ECL_H2O_06 to Physical::orbiterLayout.multi.phy_eclss_33;
        allocate context.sts.orb.eclss to Physical::orbiterLayout.multi.phy_eclss_34;
        allocate Functions::FN_ECL_ARS::F_ECL_ARS_02 to Physical::orbiterLayout.multi.phy_eclss_34;
        allocate Functions::FN_ECL_ARS::F_ECL_ARS_03 to Physical::orbiterLayout.multi.phy_eclss_34;
        allocate Functions::FN_ECL_ARS::F_ECL_ARS_04 to Physical::orbiterLayout.multi.phy_eclss_34;
        allocate Functions::FN_ECL_ARS::F_ECL_ARS_05 to Physical::orbiterLayout.multi.phy_eclss_34;
        allocate context.sts.orb.eclss to Physical::orbiterLayout.airlock.phy_eclss_35;
        allocate Functions::FN_ECL_ALS::F_ECL_ALS_01 to Physical::orbiterLayout.airlock.phy_eclss_35;
        allocate Functions::FN_ECL_ALS::F_ECL_ALS_02 to Physical::orbiterLayout.airlock.phy_eclss_35;
        allocate Functions::FN_ECL_ALS::F_ECL_ALS_04 to Physical::orbiterLayout.airlock.phy_eclss_35;
        allocate Functions::FN_ECL_ALS::F_ECL_ALS_05 to Physical::orbiterLayout.airlock.phy_eclss_35;
        allocate context.sts.orb.eclss to Physical::orbiterLayout.airlock.phy_eclss_36;
        allocate Functions::FN_ECL_ALS::F_ECL_ALS_10 to Physical::orbiterLayout.airlock.phy_eclss_36;
        allocate context.sts.orb.eclss to Physical::orbiterLayout.airlock.phy_eclss_37;
        allocate Functions::FN_ECL_ALS::F_ECL_ALS_09 to Physical::orbiterLayout.airlock.phy_eclss_37;
        allocate context.sts.orb.eclss to Physical::orbiterLayout.airlock.phy_eclss_38;
        allocate Functions::FN_ECL_ALS::F_ECL_ALS_01 to Physical::orbiterLayout.airlock.phy_eclss_38;
        allocate Functions::FN_ECL_ALS::F_ECL_ALS_03 to Physical::orbiterLayout.airlock.phy_eclss_38;
        allocate Functions::FN_ECL_ALS::F_ECL_ALS_09 to Physical::orbiterLayout.airlock.phy_eclss_38;
        allocate Functions::FN_ECL_ALS::F_ECL_ALS_10 to Physical::orbiterLayout.airlock.phy_eclss_38;
        allocate context.sts.orb.eclss to Physical::orbiterLayout.airlock.phy_eclss_39;
        allocate Functions::FN_ECL_ALS::F_ECL_ALS_01 to Physical::orbiterLayout.airlock.phy_eclss_39;
        allocate Functions::FN_ECL_ALS::F_ECL_ALS_02 to Physical::orbiterLayout.airlock.phy_eclss_39;
        allocate Functions::FN_ECL_ALS::F_ECL_ALS_04 to Physical::orbiterLayout.airlock.phy_eclss_39;
        allocate Functions::FN_ECL_ALS::F_ECL_ALS_05 to Physical::orbiterLayout.airlock.phy_eclss_39;
        allocate context.sts.orb.apu to Physical::orbiterLayout.aft.phy_apu_01;
        allocate Functions::FN_APU_TRB::F_APU_TRB_02 to Physical::orbiterLayout.aft.phy_apu_01;
        allocate Functions::FN_APU_TRB::F_APU_TRB_04 to Physical::orbiterLayout.aft.phy_apu_01;
        allocate Functions::FN_APU_CTL::F_APU_CTL_01 to Physical::orbiterLayout.aft.phy_apu_01;
        allocate Functions::FN_APU_CTL::F_APU_CTL_02 to Physical::orbiterLayout.aft.phy_apu_01;
        allocate Functions::FN_APU_CTL::F_APU_CTL_07 to Physical::orbiterLayout.aft.phy_apu_01;
        allocate Functions::FN_APU_CTL::F_APU_CTL_10 to Physical::orbiterLayout.aft.phy_apu_01;
        allocate context.sts.orb.apu to Physical::orbiterLayout.aft.phy_apu_02;
        allocate Functions::FN_APU_FUL::F_APU_FUL_01 to Physical::orbiterLayout.aft.phy_apu_02;
        allocate Functions::FN_APU_FUL::F_APU_FUL_02 to Physical::orbiterLayout.aft.phy_apu_02;
        allocate Functions::FN_APU_FUL::F_APU_FUL_03 to Physical::orbiterLayout.aft.phy_apu_02;
        allocate Functions::FN_APU_FUL::F_APU_FUL_06 to Physical::orbiterLayout.aft.phy_apu_02;
        allocate context.sts.orb.apu to Physical::orbiterLayout.aft.phy_apu_03;
        allocate Functions::FN_APU::F_APU_01 to Physical::orbiterLayout.aft.phy_apu_03;
        allocate Functions::FN_APU::F_APU_03 to Physical::orbiterLayout.aft.phy_apu_03;
        allocate context.sts.orb.apu to Physical::orbiterLayout.aft.phy_apu_04;
        allocate Functions::FN_APU::F_APU_01 to Physical::orbiterLayout.aft.phy_apu_04;
        allocate Functions::FN_APU::F_APU_02 to Physical::orbiterLayout.aft.phy_apu_04;
        allocate Functions::FN_APU::F_APU_04 to Physical::orbiterLayout.aft.phy_apu_04;
        allocate context.sts.orb.apu to Physical::orbiterLayout.aft.phy_apu_05;
        allocate Functions::FN_APU::F_APU_01 to Physical::orbiterLayout.aft.phy_apu_05;
        allocate Functions::FN_APU::F_APU_02 to Physical::orbiterLayout.aft.phy_apu_05;
        allocate context.sts.orb.apu to Physical::orbiterLayout.aft.phy_apu_06;
        allocate Functions::FN_APU_TRB::F_APU_TRB_01 to Physical::orbiterLayout.aft.phy_apu_06;
        allocate Functions::FN_APU_TRB::F_APU_TRB_02 to Physical::orbiterLayout.aft.phy_apu_06;
        allocate Functions::FN_APU_TRB::F_APU_TRB_04 to Physical::orbiterLayout.aft.phy_apu_06;
        allocate context.sts.orb.apu to Physical::orbiterLayout.multi.phy_apu_07;
        allocate Functions::FN_APU_HYD::F_APU_HYD_01 to Physical::orbiterLayout.multi.phy_apu_07;
        allocate Functions::FN_APU_HYD::F_APU_HYD_04 to Physical::orbiterLayout.multi.phy_apu_07;
        allocate Functions::FN_APU_HYD::F_APU_HYD_06 to Physical::orbiterLayout.multi.phy_apu_07;
        allocate Functions::FN_APU_HYD::F_APU_HYD_09 to Physical::orbiterLayout.multi.phy_apu_07;
        allocate context.sts.orb.oms to Physical::orbiterLayout.pod.phy_oms_01;
        allocate Functions::FN_OMS_ENG::F_OMS_ENG_01 to Physical::orbiterLayout.pod.phy_oms_01;
        allocate Functions::FN_OMS_ENG::F_OMS_ENG_02 to Physical::orbiterLayout.pod.phy_oms_01;
        allocate Functions::FN_OMS_ENG::F_OMS_ENG_07 to Physical::orbiterLayout.pod.phy_oms_01;
        allocate Functions::FN_OMS_ENG::F_OMS_ENG_08 to Physical::orbiterLayout.pod.phy_oms_01;
        allocate context.sts.orb.oms to Physical::orbiterLayout.pod.phy_oms_02;
        allocate Functions::FN_OMS::F_OMS_01 to Physical::orbiterLayout.pod.phy_oms_02;
        allocate Functions::FN_OMS::F_OMS_03 to Physical::orbiterLayout.pod.phy_oms_02;
        allocate Functions::FN_OMS::F_OMS_04 to Physical::orbiterLayout.pod.phy_oms_02;
        allocate context.sts.orb.oms to Physical::orbiterLayout.pod.phy_oms_03;
        allocate Functions::FN_OMS_HE::F_OMS_HE_01 to Physical::orbiterLayout.pod.phy_oms_03;
        allocate Functions::FN_OMS_HE::F_OMS_HE_02 to Physical::orbiterLayout.pod.phy_oms_03;
        allocate Functions::FN_OMS_HE::F_OMS_HE_07 to Physical::orbiterLayout.pod.phy_oms_03;
        allocate Functions::FN_OMS_HE::F_OMS_HE_09 to Physical::orbiterLayout.pod.phy_oms_03;
        allocate context.sts.orb.oms to Physical::orbiterLayout.pod.phy_oms_04;
        allocate Functions::FN_OMS::F_OMS_01 to Physical::orbiterLayout.pod.phy_oms_04;
        allocate Functions::FN_OMS::F_OMS_03 to Physical::orbiterLayout.pod.phy_oms_04;
        allocate context.sts.orb.oms to Physical::orbiterLayout.aft.phy_oms_05;
        allocate Functions::FN_OMS::F_OMS_01 to Physical::orbiterLayout.aft.phy_oms_05;
        allocate Functions::FN_OMS::F_OMS_03 to Physical::orbiterLayout.aft.phy_oms_05;
        allocate context.sts.orb.mps to Physical::orbiterLayout.aft.phy_mps_01;
        allocate Functions::FN_MPS::F_MPS_01 to Physical::orbiterLayout.aft.phy_mps_01;
        allocate Functions::FN_MPS::F_MPS_02 to Physical::orbiterLayout.aft.phy_mps_01;
        allocate Functions::FN_MPS::F_MPS_03 to Physical::orbiterLayout.aft.phy_mps_01;
        allocate context.sts.orb.mps to Physical::orbiterLayout.aft.phy_mps_02;
        allocate Functions::FN_MPS_CTL::F_MPS_CTL_01 to Physical::orbiterLayout.aft.phy_mps_02;
        allocate Functions::FN_MPS_CTL::F_MPS_CTL_03 to Physical::orbiterLayout.aft.phy_mps_02;
        allocate Functions::FN_MPS_CTL::F_MPS_CTL_04 to Physical::orbiterLayout.aft.phy_mps_02;
        allocate Functions::FN_MPS_CTL::F_MPS_CTL_05 to Physical::orbiterLayout.aft.phy_mps_02;
        allocate context.sts.orb.mps to Physical::orbiterLayout.aft.phy_mps_03;
        allocate Functions::FN_MPS_TVC::F_MPS_TVC_03 to Physical::orbiterLayout.aft.phy_mps_03;
        allocate Functions::FN_MPS_TVC::F_MPS_TVC_05 to Physical::orbiterLayout.aft.phy_mps_03;
        allocate Functions::FN_MPS_TVC::F_MPS_TVC_06 to Physical::orbiterLayout.aft.phy_mps_03;
        allocate Functions::FN_MPS_TVC::F_MPS_TVC_07 to Physical::orbiterLayout.aft.phy_mps_03;
        allocate context.sts.orb.mps to Physical::orbiterLayout.avba.phy_mps_04;
        allocate Functions::FN_MPS_TVC::F_MPS_TVC_01 to Physical::orbiterLayout.avba.phy_mps_04;
        allocate Functions::FN_MPS_TVC::F_MPS_TVC_02 to Physical::orbiterLayout.avba.phy_mps_04;
        allocate Functions::FN_MPS_TVC::F_MPS_TVC_03 to Physical::orbiterLayout.avba.phy_mps_04;
        allocate context.sts.orb.mps to Physical::orbiterLayout.multi.phy_mps_05;
        allocate Functions::FN_MPS::F_MPS_02 to Physical::orbiterLayout.multi.phy_mps_05;
        allocate context.sts.orb.mps to Physical::orbiterLayout.aft.phy_mps_06;
        allocate Functions::FN_MPS::F_MPS_02 to Physical::orbiterLayout.aft.phy_mps_06;
        allocate context.sts.orb.mps to Physical::orbiterLayout.aft.phy_mps_07;
        allocate Functions::FN_MPS_PMS::F_MPS_PMS_01 to Physical::orbiterLayout.aft.phy_mps_07;
        allocate Functions::FN_MPS_PMS::F_MPS_PMS_06 to Physical::orbiterLayout.aft.phy_mps_07;
        allocate context.sts.orb.mps to Physical::orbiterLayout.aft.phy_mps_08;
        allocate Functions::FN_MPS_DMP::F_MPS_DMP_01 to Physical::orbiterLayout.aft.phy_mps_08;
        allocate Functions::FN_MPS_DMP::F_MPS_DMP_04 to Physical::orbiterLayout.aft.phy_mps_08;
        allocate Functions::FN_MPS_DMP::F_MPS_DMP_06 to Physical::orbiterLayout.aft.phy_mps_08;
        allocate Functions::FN_MPS_DMP::F_MPS_DMP_07 to Physical::orbiterLayout.aft.phy_mps_08;
        allocate context.sts.orb.tps to Physical::orbiterLayout.fwd.phy_tps_01;
        allocate Functions::FN_TPS::F_TPS_01 to Physical::orbiterLayout.fwd.phy_tps_01;
        allocate Functions::FN_TPS::F_TPS_02 to Physical::orbiterLayout.fwd.phy_tps_01;
        allocate context.sts.orb.tps to Physical::orbiterLayout.wing.phy_tps_02;
        allocate Functions::FN_TPS::F_TPS_02 to Physical::orbiterLayout.wing.phy_tps_02;
        allocate context.sts.orb.tps to Physical::orbiterLayout.multi.phy_tps_03;
        allocate Functions::FN_TPS::F_TPS_03 to Physical::orbiterLayout.multi.phy_tps_03;
        allocate Functions::FN_TPS::F_TPS_04 to Physical::orbiterLayout.multi.phy_tps_03;
        allocate context.sts.orb.tps to Physical::orbiterLayout.multi.phy_tps_04;
        allocate Functions::FN_TPS::F_TPS_05 to Physical::orbiterLayout.multi.phy_tps_04;
        allocate context.sts.orb.tps to Physical::orbiterLayout.multi.phy_tps_05;
        allocate Functions::FN_TPS::F_TPS_06 to Physical::orbiterLayout.multi.phy_tps_05;
        allocate context.sts.orb.str to Physical::orbiterLayout.fwd.phy_str_01;
        allocate Functions::FN_STR::F_STR_01 to Physical::orbiterLayout.fwd.phy_str_01;
        allocate Functions::FN_STR::F_STR_02 to Physical::orbiterLayout.fwd.phy_str_01;
        allocate context.sts.orb.str to Physical::orbiterLayout.multi.phy_str_02;
        allocate Functions::FN_STR::F_STR_03 to Physical::orbiterLayout.multi.phy_str_02;
        allocate Functions::FN_STR::F_STR_04 to Physical::orbiterLayout.multi.phy_str_02;
        allocate context.sts.orb.str to Physical::orbiterLayout.mid.phy_str_03;
        allocate Functions::FN_STR::F_STR_05 to Physical::orbiterLayout.mid.phy_str_03;
        allocate context.sts.orb.str to Physical::orbiterLayout.wing.phy_str_04;
        allocate Functions::FN_STR::F_STR_01 to Physical::orbiterLayout.wing.phy_str_04;
        allocate context.sts.orb.str to Physical::orbiterLayout.aft.phy_str_05;
        allocate Functions::FN_STR_AFT::F_STR_AFT_01 to Physical::orbiterLayout.aft.phy_str_05;
        allocate Functions::FN_STR_AFT::F_STR_AFT_02 to Physical::orbiterLayout.aft.phy_str_05;
        allocate Functions::FN_STR_AFT::F_STR_AFT_03 to Physical::orbiterLayout.aft.phy_str_05;
        allocate Functions::FN_STR_AFT::F_STR_AFT_05 to Physical::orbiterLayout.aft.phy_str_05;
        allocate Functions::FN_STR_WNG::F_STR_WNG_05 to Physical::orbiterLayout.aft.phy_str_05;
        allocate context.sts.orb.str to Physical::orbiterLayout.vt.phy_str_06;
        allocate Functions::FN_STR::F_STR_01 to Physical::orbiterLayout.vt.phy_str_06;
        allocate context.sts.orb.mech to Physical::orbiterLayout.plb.phy_mech_01;
        allocate Functions::FN_MECH::F_MECH_01 to Physical::orbiterLayout.plb.phy_mech_01;
        allocate Functions::FN_MECH::F_MECH_02 to Physical::orbiterLayout.plb.phy_mech_01;
        allocate Functions::FN_MECH::F_MECH_10 to Physical::orbiterLayout.plb.phy_mech_01;
        allocate context.sts.orb.mech to Physical::orbiterLayout.aft.phy_mech_02;
        allocate Functions::FN_MECH_VNT::F_MECH_VNT_05 to Physical::orbiterLayout.aft.phy_mech_02;
        allocate context.sts.orb.mech to Physical::orbiterLayout.multi.phy_mech_03;
        allocate Functions::FN_MECH_VNT::F_MECH_VNT_01 to Physical::orbiterLayout.multi.phy_mech_03;
        allocate Functions::FN_MECH_VNT::F_MECH_VNT_02 to Physical::orbiterLayout.multi.phy_mech_03;
        allocate Functions::FN_MECH_VNT::F_MECH_VNT_03 to Physical::orbiterLayout.multi.phy_mech_03;
        allocate Functions::FN_MECH_VNT::F_MECH_VNT_04 to Physical::orbiterLayout.multi.phy_mech_03;
        allocate context.sts.orb.mech to Physical::orbiterLayout.fwd.phy_mech_04;
        allocate Functions::FN_MECH::F_MECH_03 to Physical::orbiterLayout.fwd.phy_mech_04;
        allocate Functions::FN_MECH::F_MECH_04 to Physical::orbiterLayout.fwd.phy_mech_04;
        allocate Functions::FN_MECH::F_MECH_06 to Physical::orbiterLayout.fwd.phy_mech_04;
        allocate context.sts.orb.mech to Physical::orbiterLayout.wing.phy_mech_05;
        allocate Functions::FN_MECH::F_MECH_03 to Physical::orbiterLayout.wing.phy_mech_05;
        allocate Functions::FN_MECH::F_MECH_05 to Physical::orbiterLayout.wing.phy_mech_05;
        allocate context.sts.orb.mech to Physical::orbiterLayout.vt.phy_mech_06;
        allocate Functions::FN_MECH_DEC::F_MECH_DEC_01 to Physical::orbiterLayout.vt.phy_mech_06;
        allocate Functions::FN_MECH_DEC::F_MECH_DEC_02 to Physical::orbiterLayout.vt.phy_mech_06;
        allocate context.sts.orb.cw to Physical::orbiterLayout.avb3a.phy_cw_01;
        allocate Functions::FN_CW::F_CW_02 to Physical::orbiterLayout.avb3a.phy_cw_01;
        allocate Functions::FN_CW::F_CW_05 to Physical::orbiterLayout.avb3a.phy_cw_01;
        allocate Functions::FN_CW::F_CW_07 to Physical::orbiterLayout.avb3a.phy_cw_01;
        allocate context.sts.orb.cw to Physical::orbiterLayout.fd.phy_cw_02;
        allocate Functions::FN_CW::F_CW_02 to Physical::orbiterLayout.fd.phy_cw_02;
        allocate Functions::FN_CW::F_CW_03 to Physical::orbiterLayout.fd.phy_cw_02;
        allocate Functions::FN_CW::F_CW_06 to Physical::orbiterLayout.fd.phy_cw_02;
        allocate context.sts.orb.cw to Physical::orbiterLayout.multi.phy_cw_03;
        allocate Functions::FN_CW::F_CW_02 to Physical::orbiterLayout.multi.phy_cw_03;
        allocate Functions::FN_CW::F_CW_03 to Physical::orbiterLayout.multi.phy_cw_03;
        allocate context.sts.orb.cw to Physical::orbiterLayout.fd.phy_cw_04;
        allocate Functions::FN_CW_ALT::F_CW_ALT_02 to Physical::orbiterLayout.fd.phy_cw_04;
        allocate Functions::FN_CW_ALT::F_CW_ALT_04 to Physical::orbiterLayout.fd.phy_cw_04;
        allocate Functions::FN_CW_ALT::F_CW_ALT_05 to Physical::orbiterLayout.fd.phy_cw_04;
        allocate Functions::FN_CW_ALT::F_CW_ALT_06 to Physical::orbiterLayout.fd.phy_cw_04;
        allocate context.sts.orb.cw to Physical::orbiterLayout.multi.phy_cw_05;
        allocate Functions::FN_CW_PRI::F_CW_PRI_01 to Physical::orbiterLayout.multi.phy_cw_05;
        allocate Functions::FN_CW_PRI::F_CW_PRI_02 to Physical::orbiterLayout.multi.phy_cw_05;
        allocate Functions::FN_CW_PRI::F_CW_PRI_03 to Physical::orbiterLayout.multi.phy_cw_05;
        allocate Functions::FN_CW_ANN::F_CW_ANN_04 to Physical::orbiterLayout.multi.phy_cw_05;
        allocate context.sts.orb.crew to Physical::orbiterLayout.multi.phy_crew_01;
        allocate Functions::FN_CREW_ESC::F_CREW_ESC_01 to Physical::orbiterLayout.multi.phy_crew_01;
        allocate Functions::FN_CREW_ESC::F_CREW_ESC_02 to Physical::orbiterLayout.multi.phy_crew_01;
        allocate Functions::FN_CREW_ESC::F_CREW_ESC_03 to Physical::orbiterLayout.multi.phy_crew_01;
        allocate context.sts.orb.crew to Physical::orbiterLayout.md.phy_crew_02;
        allocate Functions::FN_CREW::F_CREW_01 to Physical::orbiterLayout.md.phy_crew_02;
        allocate Functions::FN_CREW::F_CREW_02 to Physical::orbiterLayout.md.phy_crew_02;
        allocate context.sts.orb.crew to Physical::orbiterLayout.md.phy_crew_03;
        allocate Functions::FN_CREW_ESC::F_CREW_ESC_02 to Physical::orbiterLayout.md.phy_crew_03;
        allocate Functions::FN_CREW_ESC::F_CREW_ESC_05 to Physical::orbiterLayout.md.phy_crew_03;
        allocate Functions::FN_CREW_ESC::F_CREW_ESC_06 to Physical::orbiterLayout.md.phy_crew_03;
        allocate Functions::FN_CREW_ESC::F_CREW_ESC_07 to Physical::orbiterLayout.md.phy_crew_03;
        allocate context.sts.orb.crew to Physical::orbiterLayout.md.phy_crew_04;
        allocate Functions::FN_CREW_ESC::F_CREW_ESC_02 to Physical::orbiterLayout.md.phy_crew_04;
        allocate Functions::FN_CREW_ESC::F_CREW_ESC_06 to Physical::orbiterLayout.md.phy_crew_04;
        allocate Functions::FN_CREW_ESC::F_CREW_ESC_08 to Physical::orbiterLayout.md.phy_crew_04;
        allocate context.sts.orb.crew to Physical::orbiterLayout.fd.phy_crew_05;
        allocate Functions::FN_CREW_ESC::F_CREW_ESC_07 to Physical::orbiterLayout.fd.phy_crew_05;
        allocate context.sts.orb.pls to Physical::orbiterLayout.plb.phy_pls_01;
        allocate Functions::FN_PLS_ARM::F_PLS_ARM_01 to Physical::orbiterLayout.plb.phy_pls_01;
        allocate Functions::FN_PLS_ARM::F_PLS_ARM_02 to Physical::orbiterLayout.plb.phy_pls_01;
        allocate Functions::FN_PLS_ARM::F_PLS_ARM_03 to Physical::orbiterLayout.plb.phy_pls_01;
        allocate Functions::FN_PLS_ARM::F_PLS_ARM_04 to Physical::orbiterLayout.plb.phy_pls_01;
        allocate context.sts.orb.pls to Physical::orbiterLayout.plb.phy_pls_02;
        allocate Functions::FN_PLS_MPM::F_PLS_MPM_01 to Physical::orbiterLayout.plb.phy_pls_02;
        allocate Functions::FN_PLS_MPM::F_PLS_MPM_02 to Physical::orbiterLayout.plb.phy_pls_02;
        allocate Functions::FN_PLS_MPM::F_PLS_MPM_03 to Physical::orbiterLayout.plb.phy_pls_02;
        allocate Functions::FN_PLS_MPM::F_PLS_MPM_04 to Physical::orbiterLayout.plb.phy_pls_02;
        allocate context.sts.orb.pls to Physical::orbiterLayout.fd.phy_pls_03;
        allocate Functions::FN_PLS_CTL::F_PLS_CTL_01 to Physical::orbiterLayout.fd.phy_pls_03;
        allocate Functions::FN_PLS_CTL::F_PLS_CTL_02 to Physical::orbiterLayout.fd.phy_pls_03;
        allocate Functions::FN_PLS_CTL::F_PLS_CTL_07 to Physical::orbiterLayout.fd.phy_pls_03;
        allocate context.sts.orb.pls to Physical::orbiterLayout.plb.phy_pls_04;
        allocate Functions::FN_PLS_ODS::F_PLS_ODS_01 to Physical::orbiterLayout.plb.phy_pls_04;
        allocate Functions::FN_PLS_ODS::F_PLS_ODS_04 to Physical::orbiterLayout.plb.phy_pls_04;
        allocate Functions::FN_PLS_ODS::F_PLS_ODS_05 to Physical::orbiterLayout.plb.phy_pls_04;
        allocate context.sts.orb.pls to Physical::orbiterLayout.airlock.phy_pls_05;
        allocate Functions::FN_PLS_ODS::F_PLS_ODS_07 to Physical::orbiterLayout.airlock.phy_pls_05;
        allocate context.sts.orb.eva to Physical::orbiterLayout.airlock.phy_eva_01;
        allocate Functions::FN_EVA_CHK::F_EVA_CHK_01 to Physical::orbiterLayout.airlock.phy_eva_01;
        allocate Functions::FN_EVA_CHK::F_EVA_CHK_02 to Physical::orbiterLayout.airlock.phy_eva_01;
        allocate Functions::FN_EVA_CHK::F_EVA_CHK_03 to Physical::orbiterLayout.airlock.phy_eva_01;
        allocate Functions::FN_EVA_CHK::F_EVA_CHK_04 to Physical::orbiterLayout.airlock.phy_eva_01;
        allocate context.sts.orb.eva to Physical::orbiterLayout.airlock.phy_eva_02;
        allocate Functions::FN_EVA_DPR::F_EVA_DPR_01 to Physical::orbiterLayout.airlock.phy_eva_02;
        allocate Functions::FN_EVA_DPR::F_EVA_DPR_03 to Physical::orbiterLayout.airlock.phy_eva_02;
        allocate Functions::FN_EVA_DPR::F_EVA_DPR_04 to Physical::orbiterLayout.airlock.phy_eva_02;
        allocate Functions::FN_EVA_DPR::F_EVA_DPR_05 to Physical::orbiterLayout.airlock.phy_eva_02;
        allocate context.sts.orb.eva to Physical::orbiterLayout.plb.phy_eva_03;
        allocate Functions::FN_EVA_TLS::F_EVA_TLS_01 to Physical::orbiterLayout.plb.phy_eva_03;
        allocate Functions::FN_EVA_TLS::F_EVA_TLS_02 to Physical::orbiterLayout.plb.phy_eva_03;
        allocate Functions::FN_EVA_TLS::F_EVA_TLS_03 to Physical::orbiterLayout.plb.phy_eva_03;
        allocate context.sts.orb.eva to Physical::orbiterLayout.multi.phy_eva_04;
        allocate Functions::FN_EVA_TLS::F_EVA_TLS_08 to Physical::orbiterLayout.multi.phy_eva_04;
        allocate context.sts.orb.eva to Physical::orbiterLayout.plb.phy_eva_05;
        allocate Functions::FN_EVA_TLS::F_EVA_TLS_06 to Physical::orbiterLayout.plb.phy_eva_05;
        allocate context.sts.orb.eva to Physical::orbiterLayout.md.phy_eva_06;
        allocate Functions::FN_EVA_MNT::F_EVA_MNT_01 to Physical::orbiterLayout.md.phy_eva_06;
        allocate Functions::FN_EVA_MNT::F_EVA_MNT_09 to Physical::orbiterLayout.md.phy_eva_06;
        allocate Functions::FN_EVA_MNT::F_EVA_MNT_10 to Physical::orbiterLayout.md.phy_eva_06;
        allocate context.sts.orb.eva to Physical::orbiterLayout.multi.phy_eva_07;
        allocate Functions::FN_EVA_OPS::F_EVA_OPS_02 to Physical::orbiterLayout.multi.phy_eva_07;
        allocate context.sts.orb.eva to Physical::orbiterLayout.plb.phy_eva_08;
        allocate Functions::FN_EVA_EMG::F_EVA_EMG_01 to Physical::orbiterLayout.plb.phy_eva_08;
        allocate Functions::FN_EVA_EMG::F_EVA_EMG_02 to Physical::orbiterLayout.plb.phy_eva_08;
        allocate context.sts.orb.eva to Physical::orbiterLayout.md.phy_eva_09;
        allocate Functions::FN_EVA_TLS::F_EVA_TLS_01 to Physical::orbiterLayout.md.phy_eva_09;
    }
    // ---- 振る舞いの割付：活動図の行動 → 部品、シーケンス図の生存線 → 部品
    package BehaviorAllocation {
        doc /* 活動・シーケンスの定義ごとに使用（action・occurrence）を置き、その中の行動・生存線を割り付ける */
        action mpsHeliumLeakResponse : SSD_BEH_ORB_002::MpsHeliumLeakResponse;
        action fuelCellCoolingLossResponse : SSD_BEH_ORB_002::FuelCellCoolingLossResponse;
        action fireResponse : SSD_BEH_ORB_002::FireResponse;
        action cabinLeakResponse : SSD_BEH_ORB_004::CabinLeakResponse;
        action evaOperation : SSD_BEH_ORB_004::EvaOperation;
        action payloadBayDoorCloseFailure : SSD_BEH_ORB_004::PayloadBayDoorCloseFailure;
        occurrence deorbitToLanding : SSD_BEH_ORB_003::DeorbitToLanding;
        occurrence ascent : SSD_BEH_ORB_003::Ascent;
        occurrence commandTelemetryPath : SSD_BEH_ORB_003::CommandTelemetryPath;
        occurrence arsAirOperations : SSD_BEH_ORB_003::ArsAirOperations;
        occurrence rcrsWaterLoopOperations : SSD_BEH_ORB_003::RcrsWaterLoopOperations;
        occurrence pressureWaterWasteOperations : SSD_BEH_ORB_003::PressureWaterWasteOperations;
        occurrence smokeDetectionAndSuppression : SSD_BEH_ORB_003::SmokeDetectionAndSuppression;
        occurrence cabinTempHumidityControl : SSD_BEH_ORB_003::CabinTempHumidityControl;
        allocate mpsHeliumLeakResponse.AC_HE_01 to context.sts.orb.mps.ops;
        allocate mpsHeliumLeakResponse.AC_HE_02 to context.sts.orb.mps.ops;
        allocate mpsHeliumLeakResponse.AC_HE_02 to context.sts.orb.mps.he;
        allocate mpsHeliumLeakResponse.AC_HE_03 to context.sts.orb.mps.ops;
        allocate mpsHeliumLeakResponse.AC_HE_04 to context.sts.orb.mps.he;
        allocate mpsHeliumLeakResponse.AC_HE_04 to context.sts.orb.mps.ops;
        allocate mpsHeliumLeakResponse.AC_HE_05 to context.sts.orb.mps.he;
        allocate mpsHeliumLeakResponse.AC_HE_06 to context.sts.orb.mps.pms;
        allocate fuelCellCoolingLossResponse.AC_FC_01 to context.sts.orb.eps.fcp;
        allocate fuelCellCoolingLossResponse.AC_FC_07 to context.sts.orb.eps.fcp;
        allocate fuelCellCoolingLossResponse.AC_FC_02 to context.sts.orb.eps.fcp;
        allocate fuelCellCoolingLossResponse.AC_FC_03 to context.sts.orb.eps.fcp;
        allocate fuelCellCoolingLossResponse.AC_FC_04 to context.sts.orb.eps.dc;
        allocate fuelCellCoolingLossResponse.AC_FC_05 to context.sts.orb.eps.fcp;
        allocate fuelCellCoolingLossResponse.AC_FC_05 to context.sts.orb.eps.dc;
        allocate fuelCellCoolingLossResponse.AC_FC_06 to context.sts.orb.eps.fcp;
        allocate fuelCellCoolingLossResponse.AC_FC_08 to context.sts.orb.eps.fcp;
        allocate fireResponse.AC_FR_01 to context.sts.orb.eclss.fds.alm;
        allocate fireResponse.AC_FR_02 to context.sts.orb.eclss.fds.ops;
        allocate fireResponse.AC_FR_03 to context.sts.orb.eclss.fds.ops;
        allocate fireResponse.AC_FR_03 to context.sts.orb.eclss.pcs;
        allocate fireResponse.AC_FR_04 to context.sts.orb.eclss.fds.fix;
        allocate fireResponse.AC_FR_04 to context.sts.orb.eclss.fds.pfe;
        allocate fireResponse.AC_FR_04 to context.sts.orb.eclss.fds.ops;
        allocate fireResponse.AC_FR_05 to context.sts.orb.eclss.ars.co2;
        allocate fireResponse.AC_FR_05 to context.sts.orb.eclss.fds.ops;
        allocate fireResponse.AC_FR_06 to context.sts.orb.eclss.fds.ops;
        allocate fireResponse.AC_FR_07 to context.sts.orb.eclss.fds.ops;
        allocate cabinLeakResponse.AC_LK_01 to context.sts.orb.eclss.pcs;
        allocate cabinLeakResponse.AC_LK_02 to context.sts.orb.eclss.pcs;
        allocate cabinLeakResponse.AC_LK_03 to context.sts.orb.eclss.pcs;
        allocate cabinLeakResponse.AC_LK_04 to context.sts.orb.eclss.pcs;
        allocate cabinLeakResponse.AC_LK_05 to context.sts.orb.eps.dc;
        allocate evaOperation.AC_EV_01 to context.sts.orb.eva.chk;
        allocate evaOperation.AC_EV_01 to context.sts.orb.eva.ops;
        allocate evaOperation.AC_EV_02 to context.sts.orb.eva.chk;
        allocate evaOperation.AC_EV_03 to context.sts.orb.eva.chk;
        allocate evaOperation.AC_EV_04 to context.sts.orb.eva.dpr;
        allocate evaOperation.AC_EV_05 to context.sts.orb.eva.dpr;
        allocate evaOperation.AC_EV_06 to context.sts.orb.eva.dpr;
        allocate evaOperation.AC_EV_07 to context.sts.orb.eva.tls;
        allocate evaOperation.AC_EV_08 to context.sts.orb.eva.ops;
        allocate evaOperation.AC_EV_09 to context.sts.orb.eva.dpr;
        allocate evaOperation.AC_EV_10 to context.sts.orb.eva.emg;
        allocate evaOperation.AC_EV_11 to context.sts.orb.eva.mnt;
        allocate payloadBayDoorCloseFailure.AC_PB_01 to context.sts.orb.mech.plb;
        allocate payloadBayDoorCloseFailure.AC_PB_02 to context.sts.orb.mech.act;
        allocate payloadBayDoorCloseFailure.AC_PB_02 to context.sts.orb.mech.ops;
        allocate payloadBayDoorCloseFailure.AC_PB_03 to context.sts.orb.mech.ops;
        allocate payloadBayDoorCloseFailure.AC_PB_04 to context.sts.orb.eva.emg;
        allocate payloadBayDoorCloseFailure.AC_PB_05 to context.sts.orb.eva.ops;
        allocate deorbitToLanding.mcc to context.ext.mcc;
        allocate deorbitToLanding.gpc to context.sts.orb.dps;
        allocate deorbitToLanding.oms to context.sts.orb.oms;
        allocate deorbitToLanding.apu to context.sts.orb.apu;
        allocate deorbitToLanding.eclss to context.sts.orb.eclss.atcs;
        allocate deorbitToLanding.mech to context.sts.orb.mech;
        allocate ascent.lps to context.ext.lps;
        allocate ascent.gpc to context.sts.orb.dps;
        allocate ascent.eps to context.sts.orb.eps;
        allocate ascent.apu to context.sts.orb.apu;
        allocate ascent.mps to context.sts.orb.mps;
        allocate ascent.et to context.sts.et;
        allocate ascent.srb to context.sts.srb;
        allocate ascent.oms to context.sts.orb.oms;
        allocate commandTelemetryPath.mcc to context.ext.mcc;
        allocate commandTelemetryPath.net to context.ext.net;
        allocate commandTelemetryPath.sband to context.sts.orb.ct.sbd;
        allocate commandTelemetryPath.gpc to context.sts.orb.dps;
        allocate commandTelemetryPath.system to context.sts.orb.mech.act;
        allocate commandTelemetryPath.inst to context.sts.orb.ct.inst;
        allocate arsAirOperations.cacFanOps to context.sts.orb.eclss.ars.cac.ops;
        allocate arsAirOperations.cacFan to context.sts.orb.eclss.ars.cac.fan;
        allocate arsAirOperations.cacMon to context.sts.orb.eclss.ars.cac.mon;
        allocate arsAirOperations.avbOps to context.sts.orb.eclss.ars.avb.ops;
        allocate arsAirOperations.avbFan to context.sts.orb.eclss.ars.avb.fan;
        allocate arsAirOperations.avbMon to context.sts.orb.eclss.ars.avb.mon;
        allocate arsAirOperations.imuOps to context.sts.orb.eclss.ars.imu.ops;
        allocate arsAirOperations.imuFan to context.sts.orb.eclss.ars.imu.fan;
        allocate arsAirOperations.imuMon to context.sts.orb.eclss.ars.imu.mon;
        allocate arsAirOperations.dps to context.sts.orb.dps;
        allocate rcrsWaterLoopOperations.rcrsOps to context.sts.orb.eclss.ars.rcrs.ops;
        allocate rcrsWaterLoopOperations.rcrsCtl to context.sts.orb.eclss.ars.rcrs.ctl;
        allocate rcrsWaterLoopOperations.rcrsBed to context.sts.orb.eclss.ars.rcrs.bed;
        allocate rcrsWaterLoopOperations.rcrsUsc to context.sts.orb.eclss.ars.rcrs.usc;
        allocate rcrsWaterLoopOperations.rcrsMon to context.sts.orb.eclss.ars.rcrs.mon;
        allocate rcrsWaterLoopOperations.dps to context.sts.orb.dps;
        allocate rcrsWaterLoopOperations.wclOps to context.sts.orb.eclss.ars.wcl.ops;
        allocate rcrsWaterLoopOperations.wclPmp to context.sts.orb.eclss.ars.wcl.pmp;
        allocate rcrsWaterLoopOperations.wclIch to context.sts.orb.eclss.ars.wcl.ich;
        allocate rcrsWaterLoopOperations.wclMon to context.sts.orb.eclss.ars.wcl.mon;
        allocate pressureWaterWasteOperations.pcsOps to context.sts.orb.eclss.pcs.ops;
        allocate pressureWaterWasteOperations.pcsMnf to context.sts.orb.eclss.pcs.mnf;
        allocate pressureWaterWasteOperations.pcsO2s to context.sts.orb.eclss.pcs.o2s;
        allocate pressureWaterWasteOperations.pcsMon to context.sts.orb.eclss.pcs.mon;
        allocate pressureWaterWasteOperations.wcsOps to context.sts.orb.eclss.wcs.ops;
        allocate pressureWaterWasteOperations.wcsFsp to context.sts.orb.eclss.wcs.fsp;
        allocate pressureWaterWasteOperations.wcsCmd to context.sts.orb.eclss.wcs.cmd;
        allocate pressureWaterWasteOperations.wcsVac to context.sts.orb.eclss.wcs.vac;
        allocate pressureWaterWasteOperations.h2oSys to context.sts.orb.eclss.h2o;
        allocate pressureWaterWasteOperations.alsMon to context.sts.orb.eclss.als.mon;
        allocate pressureWaterWasteOperations.dps to context.sts.orb.dps;
        allocate smokeDetectionAndSuppression.smokeDetector to context.sts.orb.eclss.fds.det;
        allocate smokeDetectionAndSuppression.smokeAlarm to context.sts.orb.eclss.fds.alm;
        allocate smokeDetectionAndSuppression.dpsAvionics to context.sts.orb.dps;
        allocate smokeDetectionAndSuppression.fireOps to context.sts.orb.eclss.fds.ops;
        allocate smokeDetectionAndSuppression.bayFireExt to context.sts.orb.eclss.fds.fix;
        allocate smokeDetectionAndSuppression.portableExt to context.sts.orb.eclss.fds.pfe;
        allocate cabinTempHumidityControl.thcOps to context.sts.orb.eclss.ars.thc.ops;
        allocate cabinTempHumidityControl.thcMon to context.sts.orb.eclss.ars.thc.mon;
        allocate cabinTempHumidityControl.thcTcv to context.sts.orb.eclss.ars.thc.tcv;
        allocate cabinTempHumidityControl.thcSep to context.sts.orb.eclss.ars.thc.sep;
        allocate cabinTempHumidityControl.dps to context.sts.orb.dps;
    }
}
