// SysML v2 テキスト：妥当性確認定義書（関係者の期待に対する飛行の実績の判定。検証との違い）
// SSD-VAL-ORB-001 妥当性確認定義書（関係者の期待に対する飛行の実績の判定。検証との違い） の表から生成（lib/build_docs_cy.py・rev_cy/cydata.py）。根拠の頁は SSD-VAL-ORB-001 にある。
package SSD_VAL_ORB_001 {
    doc /* SSD-VAL-ORB-001 妥当性確認定義書（関係者の期待に対する飛行の実績の判定。検証との違い）。関係者の期待を part def StakeholderExpectation、妥当性確認のケースを part def ValidationCase の使用として持つ。期待・判定・実績は文字列の属性で、パッケージへの矢印は張らない。要求への関係（導出・充足・検証）は張らず、トレースの外に置く。 */
    private import ScalarValues::*;
    part def StakeholderExpectation {
        doc /* 関係者の定量の期待（NASA SP-4221 の本文。想定・売り込みの数字を含む） */
        attribute expectation : String;
        attribute value : String;
        attribute who : String;
        attribute year : String;
        attribute klass : String;
    }
    part def ValidationCase {
        doc /* 妥当性確認のケース：運用の期待に対し、実際に飛んだシステムの実績で判定する（検証とは別） */
        attribute expectationId : String;
        attribute verdict : String;
        attribute actual : String;
    }
    part <'VEX-01'> vex_01 : StakeholderExpectation { doc /* Flights per year of a reusable launch vehicle (Douglas 'Astr */ :>> expectation = "Flights per year of a reusable launch vehicle (Douglas 'Astro' concept)"; :>> value = "240 flights per year"; :>> who = "Douglas Aircraft paper on the Astro two-stage fully reusable launch vehicle"; :>> year = "1963"; :>> klass = "範囲外"; }
    part <'VEX-02'> vex_02 : StakeholderExpectation { doc /* Cost per flight of a reusable launch vehicle (Douglas 'Astro */ :>> expectation = "Cost per flight of a reusable launch vehicle (Douglas 'Astro' concept)"; :>> value = "$1.5 million per flight"; :>> who = "Douglas Aircraft paper on the Astro two-stage fully reusable launch vehicle"; :>> year = "1963"; :>> klass = "範囲外"; }
    part <'VEX-03'> vex_03 : StakeholderExpectation { doc /* Turnaround of the second stage between flights (Douglas 'Ast */ :>> expectation = "Turnaround of the second stage between flights (Douglas 'Astro' concept)"; :>> value = "2.5 to 5 days (two-shift operation)"; :>> who = "Douglas Aircraft paper on the Astro two-stage fully reusable launch vehicle"; :>> year = "1963"; :>> klass = "範囲外"; }
    part <'VEX-04'> vex_04 : StakeholderExpectation { doc /* Payload mass and volume for the Shuttle as set by Mueller to */ :>> expectation = "Payload mass and volume for the Shuttle as set by Mueller to the study contractors"; :>> value = "50,000 pounds carried up and down; volume of 10,000 cubic feet; bay 15 or 22 feet in diameter"; :>> who = "George Mueller, NASA, to the Space Shuttle study contractors"; :>> year = "1969"; :>> klass = "L1 要求になった期待"; }
    part <'VEX-05'> vex_05 : StakeholderExpectation { doc /* Crossrange needed by NASA's own baseline */ :>> expectation = "Crossrange needed by NASA's own baseline"; :>> value = "250 to 400 nautical miles of crossrange (return to Cape Canaveral at least once every 24 hours)"; :>> who = "NASA baseline document \"Desired System Characteristics\""; :>> year = "1969"; :>> klass = "L1 要求になった期待"; }
    part <'VEX-06'> vex_06 : StakeholderExpectation { doc /* Cost of delivering payload to orbit (goal): reduce from the  */ :>> expectation = "Cost of delivering payload to orbit (goal): reduce from the Saturn V figure to between $20 and $50 per pound"; :>> value = "$20 to $50 per pound (from about $1,000 per pound)"; :>> who = "George Mueller, NASA Office of Manned Space Flight, opening remarks at the Space"; :>> year = "1969"; :>> klass = "運用の期待"; }
    part <'VEX-07'> vex_07 : StakeholderExpectation { doc /* Cost per flight implied by Mueller's per-pound goal at a 50, */ :>> expectation = "Cost per flight implied by Mueller's per-pound goal at a 50,000-pound payload"; :>> value = "$1 million to $2.5 million per flight (at 50,000 pounds payload)"; :>> who = "Author's conversion of Mueller's cost goal (50,000-pound payload standard of the"; :>> year = "1969"; :>> klass = "運用の期待"; }
    part <'VEX-08'> vex_08 : StakeholderExpectation { doc /* Flights per year in the Bureau of the Budget's Shuttle vs Ti */ :>> expectation = "Flights per year in the Bureau of the Budget's Shuttle vs Titan III comparison (five scenarios)"; :>> value = "28 to 55 flights per year (NASA 15/20/25 + DoD 15/20/30 per year)"; :>> who = "Bureau of the Budget (BOB) analysis comparing the Shuttle with Titan III"; :>> year = "1969"; :>> klass = "運用の期待"; }
    part <'VEX-09'> vex_09 : StakeholderExpectation { doc /* Crew and passenger capacity of the Shuttle */ :>> expectation = "Crew and passenger capacity of the Shuttle"; :>> value = "a crew of two and twelve passengers into low orbit"; :>> who = "Dale Myers, NASA Associate Administrator for Manned Space Flight, congressional "; :>> year = "1970"; :>> klass = "L1 要求になった期待"; }
    part <'VEX-10'> vex_10 : StakeholderExpectation { doc /* Payload bay dimensions agreed by Paine and Seamans */ :>> expectation = "Payload bay dimensions agreed by Paine and Seamans"; :>> value = "15 feet diameter by 60 feet long"; :>> who = "NASA (Paine) and the Air Force (Seamans), Level I requirement"; :>> year = "1970"; :>> klass = "L1 要求になった期待"; }
    part <'VEX-11'> vex_11 : StakeholderExpectation { doc /* NASA baseline mission: payload to space station orbit */ :>> expectation = "NASA baseline mission: payload to space station orbit"; :>> value = "25,000 pounds to a 55-degree-inclination orbit"; :>> who = "NASA, baseline mission in the Study Control Document (response of October 2)"; :>> year = "1970"; :>> klass = "L1 要求になった期待"; }
    part <'VEX-12'> vex_12 : StakeholderExpectation { doc /* Flight rate and cost per flight for a fully reusable two-sta */ :>> expectation = "Flight rate and cost per flight for a fully reusable two-stage shuttle (Hunter's proposal)"; :>> value = "95 flights per year; about $350,000 per flight; about $7 per pound"; :>> who = "Max Hunter, Lockheed (LMSC), talk at the University of Michigan"; :>> year = "1970"; :>> klass = "運用の期待"; }
    part <'VEX-13'> vex_13 : StakeholderExpectation { doc /* Number of DoD payloads forecast for the Shuttle era and the  */ :>> expectation = "Number of DoD payloads forecast for the Shuttle era and the share needing Titan III if the bay were 12 x 40 ft"; :>> value = "149 payloads (Option G) or 232 payloads (Option B) forecast for 1981 to 1990; 71 or 129 would need T"; :>> who = "U.S. Air Force (Grant Hansen, Assistant Secretary of the Air Force) mission mode"; :>> year = "1971"; :>> klass = "運用の期待"; }
    part <'VEX-14'> vex_14 : StakeholderExpectation { doc /* Payload capacity and crossrange agreed at the Williamsburg m */ :>> expectation = "Payload capacity and crossrange agreed at the Williamsburg meeting"; :>> value = "40,000 pounds into polar orbit; 65,000 pounds due east from Cape Canaveral; crossrange 1,100 nautica"; :>> who = "NASA, giving the Air Force what it wanted (Williamsburg meeting with contractors"; :>> year = "1971"; :>> klass = "L1 要求になった期待"; }
    part <'VEX-15'> vex_15 : StakeholderExpectation { doc /* Turnaround between flights of the booster and orbiter (Phase */ :>> expectation = "Turnaround between flights of the booster and orbiter (Phase B fully reusable shuttle)"; :>> value = "as little as two weeks"; :>> who = "Phase B contractors North American Rockwell and McDonnell Douglas, fully reusabl"; :>> year = "1971"; :>> klass = "運用の期待"; }
    part <'VEX-16'> vex_16 : StakeholderExpectation { doc /* Break-even number of flights for the Shuttle (equal-capabili */ :>> expectation = "Break-even number of flights for the Shuttle (equal-capability analysis, 10 percent discount)"; :>> value = "506 flights between 1978 and 1990 (39 flights per year)"; :>> who = "Mathematica (Klaus Heiss) equal-capability studies"; :>> year = "1971"; :>> klass = "運用の期待"; }
    part <'VEX-17'> vex_17 : StakeholderExpectation { doc /* Cost per flight of NASA's preferred concept: Mark I and impr */ :>> expectation = "Cost per flight of NASA's preferred concept: Mark I and improved Mark II orbiter"; :>> value = "$9.0 million per flight (Mark I); $5.5 million per flight (Mark II)"; :>> who = "NASA estimate, reported in the Flax Committee report"; :>> year = "1971"; :>> klass = "運用の期待"; }
    part <'VEX-18'> vex_18 : StakeholderExpectation { doc /* Upper limit of cost per flight that remains cost-effective a */ :>> expectation = "Upper limit of cost per flight that remains cost-effective against expendables (TAOS tradeoff)"; :>> value = "up to $10 million per flight (expendables: $12 million per flight)"; :>> who = "Klaus Heiss, Mathematica, for NASA"; :>> year = "1971"; :>> klass = "運用の期待"; }
    part <'VEX-19'> vex_19 : StakeholderExpectation { doc /* Operating cost per flight of the candidate shuttles in NASA' */ :>> expectation = "Operating cost per flight of the candidate shuttles in NASA's December 1971 counteroffer"; :>> value = "$6.6 to $7.7 million per flight (Case 4, 15 x 60 ft, 65,000 lb: $7.7 million)"; :>> who = "NASA (Fletcher letter to Weinberger, December 29, 1971)"; :>> year = "1971"; :>> klass = "運用の期待"; }
    part <'VEX-20'> vex_20 : StakeholderExpectation { doc /* Payload cost per pound for the candidate shuttles in NASA's  */ :>> expectation = "Payload cost per pound for the candidate shuttles in NASA's December 1971 counteroffer"; :>> value = "$115 to $223 per pound (Case 4, 15 x 60 ft, 65,000 lb: $118 per pound)"; :>> who = "NASA (Fletcher letter to Weinberger, December 29, 1971)"; :>> year = "1971"; :>> klass = "運用の期待"; }
    part <'VEX-21'> vex_21 : StakeholderExpectation { doc /* Reduction in the cost of space flight (President's announcem */ :>> expectation = "Reduction in the cost of space flight (President's announcement meeting)"; :>> value = "tenfold reduction in the cost of space flight"; :>> who = "NASA's Fletcher, agreed by President Nixon at the meeting of January 5, 1972"; :>> year = "1972"; :>> klass = "運用の期待"; }
    part <'VEX-22'> vex_22 : StakeholderExpectation { doc /* Cost per flight with reusable solid rocket boosters */ :>> expectation = "Cost per flight with reusable solid rocket boosters"; :>> value = "around $10 million per flight"; :>> who = "NASA Marshall and its contractors (reusable solid booster choice)"; :>> year = "1972"; :>> klass = "運用の期待"; }
    part <'VEX-23'> vex_23 : StakeholderExpectation { doc /* Development cost ceiling for the Shuttle */ :>> expectation = "Development cost ceiling for the Shuttle"; :>> value = "$5.5 billion development cost"; :>> who = "OMB's Weinberger and Shultz"; :>> year = "1972"; :>> klass = "範囲外"; }
    part <'VEX-24'> vex_24 : StakeholderExpectation { doc /* Crossrange demanded by the Air Force */ :>> expectation = "Crossrange demanded by the Air Force"; :>> value = "1,100 nautical miles"; :>> who = "U.S. Air Force"; :>> year = ""; :>> klass = "L1 要求になった期待"; }
    part <'VEX-25'> vex_25 : StakeholderExpectation { doc /* Service life of the Space Shuttle Main Engine */ :>> expectation = "Service life of the Space Shuttle Main Engine"; :>> value = "100 starts and a 10-hour life"; :>> who = "NASA (initial SSME plan)"; :>> year = ""; :>> klass = "運用の期待"; }
    part <'VEX-26'> vex_26 : StakeholderExpectation { doc /* Marginal cost per flight of the fully reusable shuttle, and  */ :>> expectation = "Marginal cost per flight of the fully reusable shuttle, and development cost"; :>> value = "$4.6 million per flight (marginal); $9.92 billion development; 65,000 pounds payload"; :>> who = "Aerospace Corp. estimates feeding Mathematica's economic study"; :>> year = ""; :>> klass = "運用の期待"; }
    part <'VEX-27'> vex_27 : StakeholderExpectation { doc /* Baseline mission model: total flights and flights per year */ :>> expectation = "Baseline mission model: total flights and flights per year"; :>> value = "736 shuttle flights during 1978-1990 (about 57 flights per year)"; :>> who = "Aerospace Corp. baseline mission model (NASA, Air Force, Comsat wish lists) used"; :>> year = ""; :>> klass = "運用の期待"; }
    part <'VEX-28'> vex_28 : StakeholderExpectation { doc /* Savings in payload recurring costs from 'payload effects' */ :>> expectation = "Savings in payload recurring costs from 'payload effects'"; :>> value = "about 50 percent savings in payload recurring costs"; :>> who = "NASA / Aerospace Corp. / Lockheed payload-effects analysis"; :>> year = ""; :>> klass = "運用の期待"; }
    part <'VCS-01'> vcs_01 : ValidationCase { doc /* VEX-06 */ :>> expectationId = "VEX-06"; :>> verdict = "確認できない"; :>> actual = "費用の記録を取っていない"; }
    part <'VCS-02'> vcs_02 : ValidationCase { doc /* VEX-07 */ :>> expectationId = "VEX-07"; :>> verdict = "確認できない"; :>> actual = "費用の記録を取っていない"; }
    part <'VCS-03'> vcs_03 : ValidationCase { doc /* VEX-08 */ :>> expectationId = "VEX-08"; :>> verdict = "満たさなかった"; :>> actual = "年あたり最大 8（上限 18）"; }
    part <'VCS-04'> vcs_04 : ValidationCase { doc /* VEX-12 */ :>> expectationId = "VEX-12"; :>> verdict = "満たさなかった"; :>> actual = "年あたり最大 8（上限 18）"; }
    part <'VCS-05'> vcs_05 : ValidationCase { doc /* VEX-13 */ :>> expectationId = "VEX-13"; :>> verdict = "確認できない"; :>> actual = "国防総省のペイロード数を取っていない（類型 MT-06 の飛行は別の単位）"; }
    part <'VCS-06'> vcs_06 : ValidationCase { doc /* VEX-15 */ :>> expectationId = "VEX-15"; :>> verdict = "確認できない"; :>> actual = "記録のある 94組の同じオービタの着陸から次の打上げまでの最短は 55日（STS-41B→STS-41C）"; }
    part <'VCS-07'> vcs_07 : ValidationCase { doc /* VEX-16 */ :>> expectationId = "VEX-16"; :>> verdict = "満たさなかった"; :>> actual = "1990年までの飛行は最大 44"; }
    part <'VCS-08'> vcs_08 : ValidationCase { doc /* VEX-17 */ :>> expectationId = "VEX-17"; :>> verdict = "確認できない"; :>> actual = "費用の記録を取っていない"; }
    part <'VCS-09'> vcs_09 : ValidationCase { doc /* VEX-18 */ :>> expectationId = "VEX-18"; :>> verdict = "確認できない"; :>> actual = "費用の記録を取っていない"; }
    part <'VCS-10'> vcs_10 : ValidationCase { doc /* VEX-19 */ :>> expectationId = "VEX-19"; :>> verdict = "確認できない"; :>> actual = "費用の記録を取っていない"; }
    part <'VCS-11'> vcs_11 : ValidationCase { doc /* VEX-20 */ :>> expectationId = "VEX-20"; :>> verdict = "確認できない"; :>> actual = "費用の記録を取っていない"; }
    part <'VCS-12'> vcs_12 : ValidationCase { doc /* VEX-21 */ :>> expectationId = "VEX-21"; :>> verdict = "確認できない"; :>> actual = "費用の記録を取っていない"; }
    part <'VCS-13'> vcs_13 : ValidationCase { doc /* VEX-22 */ :>> expectationId = "VEX-22"; :>> verdict = "確認できない"; :>> actual = "費用の記録を取っていない"; }
    part <'VCS-14'> vcs_14 : ValidationCase { doc /* VEX-25 */ :>> expectationId = "VEX-25"; :>> verdict = "確認できない"; :>> actual = "エンジンの起動回数・運転時間の記録を取っていない"; }
    part <'VCS-15'> vcs_15 : ValidationCase { doc /* VEX-26 */ :>> expectationId = "VEX-26"; :>> verdict = "確認できない"; :>> actual = "費用の記録を取っていない"; }
    part <'VCS-16'> vcs_16 : ValidationCase { doc /* VEX-27 */ :>> expectationId = "VEX-27"; :>> verdict = "満たさなかった"; :>> actual = "1990年までの飛行は最大 44"; }
    part <'VCS-17'> vcs_17 : ValidationCase { doc /* VEX-28 */ :>> expectationId = "VEX-28"; :>> verdict = "確認できない"; :>> actual = "ペイロードの費用の記録を取っていない"; }
}
