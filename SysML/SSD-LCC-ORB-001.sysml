// SysML v2 テキスト：LCC 違反定義書（打上げのコミット基準の違反・免除の記録）
// SSD-LCC-ORB-001 LCC 違反定義書（打上げのコミット基準の違反・免除の記録） の表から生成（lib/build_docs_dd.py・rev_dd/lccdata.py）。根拠の頁は SSD-LCC-ORB-001 にある。
package SSD_LCC_ORB_001 {
    doc /* SSD-LCC-ORB-001 LCC 違反定義書（打上げのコミット基準の違反・免除の記録）。LCC の違反・免除の記録を part def LccEvent の使用として持つ。飛行・日付・項目・群・結果・免除・数え方・LAV の ID は属性。要求への関係（導出・充足・検証）は張らず、トレースの外に置く。 */
    private import ScalarValues::*;
    part def LccEvent {
        doc /* LCC（打上げのコミット基準）の違反・免除の記録。Mission Report 本文にある分で、LCC 違反の全数ではない。群・数え方は本書の判断（PLAN_DD） */
        attribute flight : String;
        attribute eventDate : String;
        attribute lccItem : String;
        attribute itemGroup : String;
        attribute eventOutcome : String;
        attribute isWaived : ScalarValues::Boolean;
        attribute isCounted : ScalarValues::Boolean;
        attribute lavId : String;
    }
    part <'LCC-001'> lcc_001 : LccEvent { doc /* STS-1 oxygen partial pressure in the Orbiter cabin (LCC redline) */ :>> flight = "STS-1"; :>> eventDate = "1981-04-10"; :>> lccItem = "oxygen partial pressure in the Orbiter cabin (LCC redline)"; :>> itemGroup = "機体・ET・SRB・SSME の計測"; :>> eventOutcome = "その他"; :>> isWaived = false; :>> isCounted = true; :>> lavId = ""; }
    part <'LCC-002'> lcc_002 : LccEvent { doc /* STS-1 cabin differential pressure/differential time (LCC redline) */ :>> flight = "STS-1"; :>> eventDate = "1981-04-12"; :>> lccItem = "cabin differential pressure/differential time (LCC redline)"; :>> itemGroup = "機体・ET・SRB・SSME の計測"; :>> eventOutcome = "その他"; :>> isWaived = false; :>> isCounted = true; :>> lavId = ""; }
    part <'LCC-003'> lcc_003 : LccEvent { doc /* STS-2 hydrogen concentration at the LH2 T-0 umbilical (redline) du */ :>> flight = "STS-2"; :>> eventDate = ""; :>> lccItem = "hydrogen concentration at the LH2 T-0 umbilical (redline) during tanking test"; :>> itemGroup = "推進系・ガス"; :>> eventOutcome = "その他"; :>> isWaived = false; :>> isCounted = false; :>> lavId = ""; }
    part <'LCC-004'> lcc_004 : LccEvent { doc /* STS-2 PRSD oxygen tank pressure at T-0 valve closure (T-2 min 35 s */ :>> flight = "STS-2"; :>> eventDate = ""; :>> lccItem = "PRSD oxygen tank pressure at T-0 valve closure (T-2 min 35 s)"; :>> itemGroup = "機体・ET・SRB・SSME の計測"; :>> eventOutcome = "スクラブ"; :>> isWaived = false; :>> isCounted = false; :>> lavId = "LAV-002"; }
    part <'LCC-005'> lcc_005 : LccEvent { doc /* STS-2 airlock-to-cargo bay differential pressure measurement (V64P */ :>> flight = "STS-2"; :>> eventDate = ""; :>> lccItem = "airlock-to-cargo bay differential pressure measurement (V64P0101A) LCC max redline"; :>> itemGroup = "機体・ET・SRB・SSME の計測"; :>> eventOutcome = "免除して打上げ"; :>> isWaived = true; :>> isCounted = true; :>> lavId = ""; }
    part <'LCC-006'> lcc_006 : LccEvent { doc /* STS-7 ET LH2 loading: T-zero umbilical leak (3.6 percent red line  */ :>> flight = "STS-7"; :>> eventDate = ""; :>> lccItem = "ET LH2 loading: T-zero umbilical leak (3.6 percent red line value)"; :>> itemGroup = "機体・ET・SRB・SSME の計測"; :>> eventOutcome = "保持"; :>> isWaived = false; :>> isCounted = false; :>> lavId = ""; }
    part <'LCC-007'> lcc_007 : LccEvent { doc /* STS-26 wing load indicators WLE-14R and WLE-14L redline limits */ :>> flight = "STS-26"; :>> eventDate = "1988-09-29"; :>> lccItem = "wing load indicators WLE-14R and WLE-14L redline limits"; :>> itemGroup = "機体・ET・SRB・SSME の計測"; :>> eventOutcome = "保持"; :>> isWaived = false; :>> isCounted = false; :>> lavId = ""; }
    part <'LCC-008'> lcc_008 : LccEvent { doc /* STS-26 dp/dt LCC redline */ :>> flight = "STS-26"; :>> eventDate = ""; :>> lccItem = "dp/dt LCC redline"; :>> itemGroup = "機体・ET・SRB・SSME の計測"; :>> eventOutcome = "免除して打上げ"; :>> isWaived = true; :>> isCounted = true; :>> lavId = ""; }
    part <'LCC-009'> lcc_009 : LccEvent { doc /* STS-27 wing A18 structural load limits with winds aloft */ :>> flight = "STS-27"; :>> eventDate = "1988-12-02"; :>> lccItem = "wing A18 structural load limits with winds aloft"; :>> itemGroup = "天候"; :>> eventOutcome = "免除して打上げ"; :>> isWaived = true; :>> isCounted = false; :>> lavId = ""; }
    part <'LCC-010'> lcc_010 : LccEvent { doc /* STS-27 water spray boiler 2 ready signal / steam vent temperature */ :>> flight = "STS-27"; :>> eventDate = "1988-12-02"; :>> lccItem = "water spray boiler 2 ready signal / steam vent temperature"; :>> itemGroup = "機体・ET・SRB・SSME の計測"; :>> eventOutcome = "免除して打上げ"; :>> isWaived = true; :>> isCounted = true; :>> lavId = ""; }
    part <'LCC-011'> lcc_011 : LccEvent { doc /* STS-27 ET nose-cone temperature */ :>> flight = "STS-27"; :>> eventDate = "1988-12-02"; :>> lccItem = "ET nose-cone temperature"; :>> itemGroup = "機体・ET・SRB・SSME の計測"; :>> eventOutcome = "免除して打上げ"; :>> isWaived = true; :>> isCounted = true; :>> lavId = ""; }
    part <'LCC-012'> lcc_012 : LccEvent { doc /* STS-28 hydrogen concentration in the Orbiter aft compartment (LCC l */ :>> flight = "STS-28"; :>> eventDate = ""; :>> lccItem = "hydrogen concentration in the Orbiter aft compartment (LCC limit 500 ppm), conditional raise to 600 "; :>> itemGroup = "推進系・ガス"; :>> eventOutcome = "その他"; :>> isWaived = true; :>> isCounted = false; :>> lavId = ""; }
    part <'LCC-013'> lcc_013 : LccEvent { doc /* STS-29 Orbiter wing leading edge loads vs green squatcheloid (winds */ :>> flight = "STS-29"; :>> eventDate = "1989-03-13"; :>> lccItem = "Orbiter wing leading edge loads vs green squatcheloid (winds aloft)"; :>> itemGroup = "天候"; :>> eventOutcome = "免除して打上げ"; :>> isWaived = true; :>> isCounted = true; :>> lavId = ""; }
    part <'LCC-014'> lcc_014 : LccEvent { doc /* STS-29 ET structure loads vs squatcheloid (L-1 hour balloon winds) */ :>> flight = "STS-29"; :>> eventDate = "1989-03-13"; :>> lccItem = "ET structure loads vs squatcheloid (L-1 hour balloon winds)"; :>> itemGroup = "天候"; :>> eventOutcome = "免除して打上げ"; :>> isWaived = true; :>> isCounted = true; :>> lavId = ""; }
    part <'LCC-015'> lcc_015 : LccEvent { doc /* STS-30 LCC engine-start box */ :>> flight = "STS-30"; :>> eventDate = "1989-04-28"; :>> lccItem = "LCC engine-start box"; :>> itemGroup = "機体・ET・SRB・SSME の計測"; :>> eventOutcome = "スクラブ"; :>> isWaived = false; :>> isCounted = true; :>> lavId = "LAV-006"; }
    part <'LCC-016'> lcc_016 : LccEvent { doc /* STS-30 water spray boiler 2 steam vent temperature LCC minimum */ :>> flight = "STS-30"; :>> eventDate = "1989-05-04"; :>> lccItem = "water spray boiler 2 steam vent temperature LCC minimum"; :>> itemGroup = "機体・ET・SRB・SSME の計測"; :>> eventOutcome = "その他"; :>> isWaived = false; :>> isCounted = false; :>> lavId = ""; }
    part <'LCC-017'> lcc_017 : LccEvent { doc /* STS-31 APU-1 chamber pressure (LCC) */ :>> flight = "STS-31"; :>> eventDate = "1990-04-10"; :>> lccItem = "APU-1 chamber pressure (LCC)"; :>> itemGroup = "機体・ET・SRB・SSME の計測"; :>> eventOutcome = "スクラブ"; :>> isWaived = false; :>> isCounted = true; :>> lavId = "LAV-007"; }
    part <'LCC-018'> lcc_018 : LccEvent { doc /* STS-31 APU-1 turbine speed (LCC) */ :>> flight = "STS-31"; :>> eventDate = "1990-04-10"; :>> lccItem = "APU-1 turbine speed (LCC)"; :>> itemGroup = "機体・ET・SRB・SSME の計測"; :>> eventOutcome = "スクラブ"; :>> isWaived = false; :>> isCounted = true; :>> lavId = "LAV-007"; }
    part <'LCC-019'> lcc_019 : LccEvent { doc /* STS-31 ice/frost on the ET/Orbiter 17-inch liquid hydrogen disconne */ :>> flight = "STS-31"; :>> eventDate = "1990-04-24"; :>> lccItem = "ice/frost on the ET/Orbiter 17-inch liquid hydrogen disconnect"; :>> itemGroup = "氷・デブリ・TPS"; :>> eventOutcome = "免除して打上げ"; :>> isWaived = true; :>> isCounted = true; :>> lavId = ""; }
    part <'LCC-020'> lcc_020 : LccEvent { doc /* STS-31 liquid oxygen outboard fill and drain valve closure at T-48  */ :>> flight = "STS-31"; :>> eventDate = "1990-04-24"; :>> lccItem = "liquid oxygen outboard fill and drain valve closure at T-48 seconds"; :>> itemGroup = "機体・ET・SRB・SSME の計測"; :>> eventOutcome = "保持"; :>> isWaived = false; :>> isCounted = true; :>> lavId = ""; }
    part <'LCC-021'> lcc_021 : LccEvent { doc /* STS-32 LCC paragraph 6.4-05 (right-hand OMS tank pressure different */ :>> flight = "STS-32"; :>> eventDate = "1990-01-08"; :>> lccItem = "LCC paragraph 6.4-05 (right-hand OMS tank pressure differential)"; :>> itemGroup = "機体・ET・SRB・SSME の計測"; :>> eventOutcome = "その他"; :>> isWaived = false; :>> isCounted = true; :>> lavId = ""; }
    part <'LCC-022'> lcc_022 : LccEvent { doc /* STS-33 APU 3 test line temperature 1 (V46T0183A) */ :>> flight = "STS-33"; :>> eventDate = ""; :>> lccItem = "APU 3 test line temperature 1 (V46T0183A)"; :>> itemGroup = "機体・ET・SRB・SSME の計測"; :>> eventOutcome = "その他"; :>> isWaived = false; :>> isCounted = true; :>> lavId = ""; }
    part <'LCC-023'> lcc_023 : LccEvent { doc /* STS-35 hydrogen concentration in the Orbiter aft compartment */ :>> flight = "STS-35"; :>> eventDate = "1990-05-29"; :>> lccItem = "hydrogen concentration in the Orbiter aft compartment"; :>> itemGroup = "推進系・ガス"; :>> eventOutcome = "スクラブ"; :>> isWaived = false; :>> isCounted = false; :>> lavId = "LAV-011"; }
    part <'LCC-024'> lcc_024 : LccEvent { doc /* STS-35 hydrogen concentration in the Orbiter aft compartment */ :>> flight = "STS-35"; :>> eventDate = "1990-09-05"; :>> lccItem = "hydrogen concentration in the Orbiter aft compartment"; :>> itemGroup = "推進系・ガス"; :>> eventOutcome = "スクラブ"; :>> isWaived = false; :>> isCounted = true; :>> lavId = "LAV-013"; }
    part <'LCC-025'> lcc_025 : LccEvent { doc /* STS-35 hydrogen concentration in the Orbiter aft compartment */ :>> flight = "STS-35"; :>> eventDate = "1990-09-17"; :>> lccItem = "hydrogen concentration in the Orbiter aft compartment"; :>> itemGroup = "推進系・ガス"; :>> eventOutcome = "スクラブ"; :>> isWaived = false; :>> isCounted = false; :>> lavId = "LAV-014"; }
    part <'LCC-026'> lcc_026 : LccEvent { doc /* STS-35 range safety minimum ceiling for launch area optical coverag */ :>> flight = "STS-35"; :>> eventDate = "1990-12-02"; :>> lccItem = "range safety minimum ceiling for launch area optical coverage"; :>> itemGroup = "天候"; :>> eventOutcome = "保持"; :>> isWaived = false; :>> isCounted = false; :>> lavId = ""; }
    part <'LCC-027'> lcc_027 : LccEvent { doc /* STS-35 Orbiter aft compartment helium concentration */ :>> flight = "STS-35"; :>> eventDate = "1990-12-02"; :>> lccItem = "Orbiter aft compartment helium concentration"; :>> itemGroup = "推進系・ガス"; :>> eventOutcome = "その他"; :>> isWaived = false; :>> isCounted = true; :>> lavId = ""; }
    part <'LCC-028'> lcc_028 : LccEvent { doc /* STS-36 SSME liquid oxygen engine inlet temperature, minimum limit d */ :>> flight = "STS-36"; :>> eventDate = "1990-02-25"; :>> lccItem = "SSME liquid oxygen engine inlet temperature, minimum limit during T-31 s hold"; :>> itemGroup = "機体・ET・SRB・SSME の計測"; :>> eventOutcome = "スクラブ"; :>> isWaived = false; :>> isCounted = true; :>> lavId = "LAV-018"; }
    part <'LCC-029'> lcc_029 : LccEvent { doc /* STS-36 fuel cell 2 hydrogen pump motor current (LCC maximum) */ :>> flight = "STS-36"; :>> eventDate = ""; :>> lccItem = "fuel cell 2 hydrogen pump motor current (LCC maximum)"; :>> itemGroup = "機体・ET・SRB・SSME の計測"; :>> eventOutcome = "その他"; :>> isWaived = false; :>> isCounted = true; :>> lavId = ""; }
    part <'LCC-030'> lcc_030 : LccEvent { doc /* STS-36 OMS right-hand helium isolation valve leak rate */ :>> flight = "STS-36"; :>> eventDate = ""; :>> lccItem = "OMS right-hand helium isolation valve leak rate"; :>> itemGroup = "機体・ET・SRB・SSME の計測"; :>> eventOutcome = "免除して打上げ"; :>> isWaived = true; :>> isCounted = false; :>> lavId = ""; }
    part <'LCC-031'> lcc_031 : LccEvent { doc /* STS-36 check valve between supply tanks A and B (leak above specifi */ :>> flight = "STS-36"; :>> eventDate = ""; :>> lccItem = "check valve between supply tanks A and B (leak above specification)"; :>> itemGroup = "機体・ET・SRB・SSME の計測"; :>> eventOutcome = "免除して打上げ"; :>> isWaived = true; :>> isCounted = false; :>> lavId = ""; }
    part <'LCC-032'> lcc_032 : LccEvent { doc /* STS-37 weather ceiling for RTLS abort (LCC) */ :>> flight = "STS-37"; :>> eventDate = "1991-04-05"; :>> lccItem = "weather ceiling for RTLS abort (LCC)"; :>> itemGroup = "天候"; :>> eventOutcome = "保持"; :>> isWaived = false; :>> isCounted = true; :>> lavId = ""; }
    part <'LCC-033'> lcc_033 : LccEvent { doc /* STS-37 weather (wind) effects on blast propagation (LCC) */ :>> flight = "STS-37"; :>> eventDate = "1991-04-05"; :>> lccItem = "weather (wind) effects on blast propagation (LCC)"; :>> itemGroup = "天候"; :>> eventOutcome = "保持"; :>> isWaived = false; :>> isCounted = false; :>> lavId = ""; }
    part <'LCC-034'> lcc_034 : LccEvent { doc /* STS-38 fuel cell 1 hydrogen pump motor voltage (LCC limit 0.75 V),  */ :>> flight = "STS-38"; :>> eventDate = ""; :>> lccItem = "fuel cell 1 hydrogen pump motor voltage (LCC limit 0.75 V), LCC change"; :>> itemGroup = "機体・ET・SRB・SSME の計測"; :>> eventOutcome = "その他"; :>> isWaived = false; :>> isCounted = false; :>> lavId = ""; }
    part <'LCC-035'> lcc_035 : LccEvent { doc /* STS-38 OMS left-hand gaseous nitrogen fill/vent valve leakage */ :>> flight = "STS-38"; :>> eventDate = ""; :>> lccItem = "OMS left-hand gaseous nitrogen fill/vent valve leakage"; :>> itemGroup = "機体・ET・SRB・SSME の計測"; :>> eventOutcome = "免除して打上げ"; :>> isWaived = true; :>> isCounted = false; :>> lavId = ""; }
    part <'LCC-036'> lcc_036 : LccEvent { doc /* STS-39 main engine 3 HPOTP secondary seal cavity pressure measureme */ :>> flight = "STS-39"; :>> eventDate = "1991-04-23"; :>> lccItem = "main engine 3 HPOTP secondary seal cavity pressure measurement (E2029) channel A"; :>> itemGroup = "機体・ET・SRB・SSME の計測"; :>> eventOutcome = "スクラブ"; :>> isWaived = false; :>> isCounted = true; :>> lavId = "LAV-020"; }
    part <'LCC-037'> lcc_037 : LccEvent { doc /* STS-39 helium concentration in Orbiter aft compartment */ :>> flight = "STS-39"; :>> eventDate = ""; :>> lccItem = "helium concentration in Orbiter aft compartment"; :>> itemGroup = "推進系・ガス"; :>> eventOutcome = "その他"; :>> isWaived = false; :>> isCounted = false; :>> lavId = ""; }
    part <'LCC-038'> lcc_038 : LccEvent { doc /* STS-41 hydraulic system 2 water spray boiler 'OK' indication (WSB s */ :>> flight = "STS-41"; :>> eventDate = "1990-10-06"; :>> lccItem = "hydraulic system 2 water spray boiler 'OK' indication (WSB steam vent duct temperature)"; :>> itemGroup = "機体・ET・SRB・SSME の計測"; :>> eventOutcome = "保持"; :>> isWaived = false; :>> isCounted = false; :>> lavId = ""; }
    part <'LCC-039'> lcc_039 : LccEvent { doc /* STS-42 fuel cell 2 hydrogen-pump motor condition */ :>> flight = "STS-42"; :>> eventDate = "1992-01-22"; :>> lccItem = "fuel cell 2 hydrogen-pump motor condition"; :>> itemGroup = "機体・ET・SRB・SSME の計測"; :>> eventOutcome = "保持"; :>> isWaived = true; :>> isCounted = true; :>> lavId = ""; }
    part <'LCC-040'> lcc_040 : LccEvent { doc /* STS-43 cabin vent valve closed indication (cabin pressure check) */ :>> flight = "STS-43"; :>> eventDate = "1991-08-01"; :>> lccItem = "cabin vent valve closed indication (cabin pressure check)"; :>> itemGroup = "機体・ET・SRB・SSME の計測"; :>> eventOutcome = "保持"; :>> isWaived = false; :>> isCounted = false; :>> lavId = ""; }
    part <'LCC-041'> lcc_041 : LccEvent { doc /* STS-45 LO2 concentration in the Orbiter aft compartment (LCC) */ :>> flight = "STS-45"; :>> eventDate = "1992-03-23"; :>> lccItem = "LO2 concentration in the Orbiter aft compartment (LCC)"; :>> itemGroup = "推進系・ガス"; :>> eventOutcome = "スクラブ"; :>> isWaived = false; :>> isCounted = true; :>> lavId = "LAV-029"; }
    part <'LCC-042'> lcc_042 : LccEvent { doc /* STS-45 LH2 concentration in the Orbiter aft compartment (LCC) */ :>> flight = "STS-45"; :>> eventDate = "1992-03-23"; :>> lccItem = "LH2 concentration in the Orbiter aft compartment (LCC)"; :>> itemGroup = "推進系・ガス"; :>> eventOutcome = "スクラブ"; :>> isWaived = false; :>> isCounted = true; :>> lavId = "LAV-029"; }
    part <'LCC-043'> lcc_043 : LccEvent { doc /* STS-45 LO2 concentration in the Orbiter aft compartment (LCC) */ :>> flight = "STS-45"; :>> eventDate = "1992-03-24"; :>> lccItem = "LO2 concentration in the Orbiter aft compartment (LCC)"; :>> itemGroup = "推進系・ガス"; :>> eventOutcome = "免除して打上げ"; :>> isWaived = true; :>> isCounted = true; :>> lavId = ""; }
    part <'LCC-044'> lcc_044 : LccEvent { doc /* STS-47 hydrogen concentration in aft compartment (LCC) */ :>> flight = "STS-47"; :>> eventDate = "1992-09-12"; :>> lccItem = "hydrogen concentration in aft compartment (LCC)"; :>> itemGroup = "推進系・ガス"; :>> eventOutcome = "免除して打上げ"; :>> isWaived = true; :>> isCounted = true; :>> lavId = ""; }
    part <'LCC-045'> lcc_045 : LccEvent { doc /* STS-47 IAPU 3 fuel test line temperature */ :>> flight = "STS-47"; :>> eventDate = "1992-09-12"; :>> lccItem = "IAPU 3 fuel test line temperature"; :>> itemGroup = "機体・ET・SRB・SSME の計測"; :>> eventOutcome = "免除して打上げ"; :>> isWaived = true; :>> isCounted = true; :>> lavId = ""; }
    part <'LCC-046'> lcc_046 : LccEvent { doc /* STS-49 APU 3 fuel test line temperature 2 (IAPU) */ :>> flight = "STS-49"; :>> eventDate = "1992-05-07"; :>> lccItem = "APU 3 fuel test line temperature 2 (IAPU)"; :>> itemGroup = "機体・ET・SRB・SSME の計測"; :>> eventOutcome = "免除して打上げ"; :>> isWaived = true; :>> isCounted = true; :>> lavId = ""; }
    part <'LCC-047'> lcc_047 : LccEvent { doc /* STS-51 right-hand SRB TVC tilt HPU turbine speed (underspeed) */ :>> flight = "STS-51"; :>> eventDate = "1993-07-24"; :>> lccItem = "right-hand SRB TVC tilt HPU turbine speed (underspeed)"; :>> itemGroup = "機体・ET・SRB・SSME の計測"; :>> eventOutcome = "スクラブ"; :>> isWaived = false; :>> isCounted = true; :>> lavId = "LAV-031"; }
    part <'LCC-048'> lcc_048 : LccEvent { doc /* STS-51 SSME 2 turbine fuel flow meter miscompare (channel A2) */ :>> flight = "STS-51"; :>> eventDate = "1993-08-12"; :>> lccItem = "SSME 2 turbine fuel flow meter miscompare (channel A2)"; :>> itemGroup = "機体・ET・SRB・SSME の計測"; :>> eventOutcome = "スクラブ"; :>> isWaived = false; :>> isCounted = true; :>> lavId = "LAV-033"; }
    part <'LCC-049'> lcc_049 : LccEvent { doc /* STS-52 hydrogen leak detectors 23 and 35 in GUCP cavity (LCC upper  */ :>> flight = "STS-52"; :>> eventDate = "1992-10-22"; :>> lccItem = "hydrogen leak detectors 23 and 35 in GUCP cavity (LCC upper redline)"; :>> itemGroup = "推進系・ガス"; :>> eventOutcome = "その他"; :>> isWaived = false; :>> isCounted = true; :>> lavId = ""; }
    part <'LCC-050'> lcc_050 : LccEvent { doc /* STS-53 wing load indicator A16L (predicted violation) */ :>> flight = "STS-53"; :>> eventDate = "1992-12-02"; :>> lccItem = "wing load indicator A16L (predicted violation)"; :>> itemGroup = "機体・ET・SRB・SSME の計測"; :>> eventOutcome = "保持"; :>> isWaived = true; :>> isCounted = false; :>> lavId = ""; }
    part <'LCC-051'> lcc_051 : LccEvent { doc /* STS-53 SSME 3A 750-psi helium regulator outlet pressure (also SSME  */ :>> flight = "STS-53"; :>> eventDate = "1992-12-02"; :>> lccItem = "SSME 3A 750-psi helium regulator outlet pressure (also SSME 1B)"; :>> itemGroup = "機体・ET・SRB・SSME の計測"; :>> eventOutcome = "免除して打上げ"; :>> isWaived = true; :>> isCounted = true; :>> lavId = ""; }
    part <'LCC-052'> lcc_052 : LccEvent { doc /* STS-53 ET acreage ice in the debris zone (1/16-inch thickness) */ :>> flight = "STS-53"; :>> eventDate = "1992-12-02"; :>> lccItem = "ET acreage ice in the debris zone (1/16-inch thickness)"; :>> itemGroup = "氷・デブリ・TPS"; :>> eventOutcome = "保持"; :>> isWaived = false; :>> isCounted = true; :>> lavId = ""; }
    part <'LCC-053'> lcc_053 : LccEvent { doc /* STS-55 SSME oxidizer preburner (OPB) purge pressure redline */ :>> flight = "STS-55"; :>> eventDate = "1993-03-22"; :>> lccItem = "SSME oxidizer preburner (OPB) purge pressure redline"; :>> itemGroup = "機体・ET・SRB・SSME の計測"; :>> eventOutcome = "スクラブ"; :>> isWaived = false; :>> isCounted = false; :>> lavId = "LAV-039"; }
    part <'LCC-054'> lcc_054 : LccEvent { doc /* STS-55 SSME 2 helium bottle pressure (LCC limit 4,500 psia) */ :>> flight = "STS-55"; :>> eventDate = "1993-03-22"; :>> lccItem = "SSME 2 helium bottle pressure (LCC limit 4,500 psia)"; :>> itemGroup = "機体・ET・SRB・SSME の計測"; :>> eventOutcome = "その他"; :>> isWaived = false; :>> isCounted = true; :>> lavId = ""; }
    part <'LCC-055'> lcc_055 : LccEvent { doc /* STS-56 MPS LH2 high-point bleed valve (PV22) closed position indica */ :>> flight = "STS-56"; :>> eventDate = "1993-04-06"; :>> lccItem = "MPS LH2 high-point bleed valve (PV22) closed position indication"; :>> itemGroup = "機体・ET・SRB・SSME の計測"; :>> eventOutcome = "スクラブ"; :>> isWaived = true; :>> isCounted = true; :>> lavId = "LAV-041"; }
    part <'LCC-056'> lcc_056 : LccEvent { doc /* STS-56 SSME 1 LO2 anti-flood valve skin temperature / GO2 interface */ :>> flight = "STS-56"; :>> eventDate = "1993-04-06"; :>> lccItem = "SSME 1 LO2 anti-flood valve skin temperature / GO2 interface temperature"; :>> itemGroup = "機体・ET・SRB・SSME の計測"; :>> eventOutcome = "保持"; :>> isWaived = true; :>> isCounted = false; :>> lavId = ""; }
    part <'LCC-057'> lcc_057 : LccEvent { doc /* STS-57 SSME 2 750-psi helium regulator B outlet pressure (LCC lower */ :>> flight = "STS-57"; :>> eventDate = "1993-06-20"; :>> lccItem = "SSME 2 750-psi helium regulator B outlet pressure (LCC lower limit), limit changed"; :>> itemGroup = "機体・ET・SRB・SSME の計測"; :>> eventOutcome = "その他"; :>> isWaived = true; :>> isCounted = false; :>> lavId = ""; }
    part <'LCC-058'> lcc_058 : LccEvent { doc /* STS-57 WSB 1 regulator outlet pressure */ :>> flight = "STS-57"; :>> eventDate = ""; :>> lccItem = "WSB 1 regulator outlet pressure"; :>> itemGroup = "機体・ET・SRB・SSME の計測"; :>> eventOutcome = "免除して打上げ"; :>> isWaived = true; :>> isCounted = false; :>> lavId = ""; }
    part <'LCC-059'> lcc_059 : LccEvent { doc /* STS-57 GSE GN2 purge pressures to LO2 disconnect umbilical cavity a */ :>> flight = "STS-57"; :>> eventDate = ""; :>> lccItem = "GSE GN2 purge pressures to LO2 disconnect umbilical cavity and LO2 T-0 umbilical (hardware maximum a"; :>> itemGroup = "地上設備・レンジ・その他"; :>> eventOutcome = "免除して打上げ"; :>> isWaived = true; :>> isCounted = false; :>> lavId = ""; }
    part <'LCC-060'> lcc_060 : LccEvent { doc /* STS-58 ET intertank oxygen concentration */ :>> flight = "STS-58"; :>> eventDate = "1993-10-14"; :>> lccItem = "ET intertank oxygen concentration"; :>> itemGroup = "推進系・ガス"; :>> eventOutcome = "免除して打上げ"; :>> isWaived = true; :>> isCounted = true; :>> lavId = ""; }
    part <'LCC-061'> lcc_061 : LccEvent { doc /* STS-58 Orbiter S-band transponder 2 */ :>> flight = "STS-58"; :>> eventDate = "1993-10-15"; :>> lccItem = "Orbiter S-band transponder 2"; :>> itemGroup = "地上設備・レンジ・その他"; :>> eventOutcome = "スクラブ"; :>> isWaived = false; :>> isCounted = true; :>> lavId = "LAV-044"; }
    part <'LCC-062'> lcc_062 : LccEvent { doc /* STS-58 ET Shuttle Range Safety System signal strength */ :>> flight = "STS-58"; :>> eventDate = "1993-10-15"; :>> lccItem = "ET Shuttle Range Safety System signal strength"; :>> itemGroup = "地上設備・レンジ・その他"; :>> eventOutcome = "その他"; :>> isWaived = false; :>> isCounted = true; :>> lavId = ""; }
    part <'LCC-063'> lcc_063 : LccEvent { doc /* STS-59 LO2 umbilical plate gap setup supply pressure */ :>> flight = "STS-59"; :>> eventDate = ""; :>> lccItem = "LO2 umbilical plate gap setup supply pressure"; :>> itemGroup = "機体・ET・SRB・SSME の計測"; :>> eventOutcome = "免除して打上げ"; :>> isWaived = true; :>> isCounted = false; :>> lavId = ""; }
    part <'LCC-064'> lcc_064 : LccEvent { doc /* STS-61C liquid-oxygen main-engine temperature (engine-start requirem */ :>> flight = "STS-61C"; :>> eventDate = "1986-01-06"; :>> lccItem = "liquid-oxygen main-engine temperature (engine-start requirement)"; :>> itemGroup = "機体・ET・SRB・SSME の計測"; :>> eventOutcome = "スクラブ"; :>> isWaived = false; :>> isCounted = false; :>> lavId = "LAV-050"; }
    part <'LCC-065'> lcc_065 : LccEvent { doc /* STS-67 fuel cells 2 and 3 voltage vs LCC minimum performance curve */ :>> flight = "STS-67"; :>> eventDate = "1995-03-02"; :>> lccItem = "fuel cells 2 and 3 voltage vs LCC minimum performance curve"; :>> itemGroup = "機体・ET・SRB・SSME の計測"; :>> eventOutcome = "その他"; :>> isWaived = false; :>> isCounted = true; :>> lavId = ""; }
    part <'LCC-066'> lcc_066 : LccEvent { doc /* STS-67 Freon coolant loop 2 accumulator quantity (LCC) */ :>> flight = "STS-67"; :>> eventDate = "1995-03-02"; :>> lccItem = "Freon coolant loop 2 accumulator quantity (LCC)"; :>> itemGroup = "機体・ET・SRB・SSME の計測"; :>> eventOutcome = "免除して打上げ"; :>> isWaived = true; :>> isCounted = false; :>> lavId = ""; }
    part <'LCC-067'> lcc_067 : LccEvent { doc /* STS-67 FES accumulator B feedline temperature (LCC limit 56 F) */ :>> flight = "STS-67"; :>> eventDate = "1995-03-02"; :>> lccItem = "FES accumulator B feedline temperature (LCC limit 56 F)"; :>> itemGroup = "機体・ET・SRB・SSME の計測"; :>> eventOutcome = "保持"; :>> isWaived = false; :>> isCounted = false; :>> lavId = ""; }
    part <'LCC-068'> lcc_068 : LccEvent { doc /* STS-68 SSME 3 HPOT discharge temperature A (LCC redline) */ :>> flight = "STS-68"; :>> eventDate = "1994-08-18"; :>> lccItem = "SSME 3 HPOT discharge temperature A (LCC redline)"; :>> itemGroup = "機体・ET・SRB・SSME の計測"; :>> eventOutcome = "スクラブ"; :>> isWaived = false; :>> isCounted = true; :>> lavId = "LAV-055"; }
    part <'LCC-069'> lcc_069 : LccEvent { doc /* STS-70 ET range safety system (RSS) receiver signal strength (LCC) */ :>> flight = "STS-70"; :>> eventDate = "1995-07-13"; :>> lccItem = "ET range safety system (RSS) receiver signal strength (LCC)"; :>> itemGroup = "地上設備・レンジ・その他"; :>> eventOutcome = "保持"; :>> isWaived = false; :>> isCounted = true; :>> lavId = ""; }
    part <'LCC-070'> lcc_070 : LccEvent { doc /* STS-73 fuel cell 3 substack 1 cell performance monitor (CPM) differ */ :>> flight = "STS-73"; :>> eventDate = ""; :>> lccItem = "fuel cell 3 substack 1 cell performance monitor (CPM) differential voltage measurement (constraint t"; :>> itemGroup = "機体・ET・SRB・SSME の計測"; :>> eventOutcome = "免除して打上げ"; :>> isWaived = true; :>> isCounted = false; :>> lavId = ""; }
    part <'LCC-071'> lcc_071 : LccEvent { doc /* STS-73 hydraulic system 1 air content (compressibility test) */ :>> flight = "STS-73"; :>> eventDate = ""; :>> lccItem = "hydraulic system 1 air content (compressibility test)"; :>> itemGroup = "機体・ET・SRB・SSME の計測"; :>> eventOutcome = "免除して打上げ"; :>> isWaived = true; :>> isCounted = false; :>> lavId = ""; }
    part <'LCC-072'> lcc_072 : LccEvent { doc /* STS-80 Orbiter aft compartment gaseous hydrogen concentration */ :>> flight = "STS-80"; :>> eventDate = "1996-11-19"; :>> lccItem = "Orbiter aft compartment gaseous hydrogen concentration"; :>> itemGroup = "推進系・ガス"; :>> eventOutcome = "保持"; :>> isWaived = false; :>> isCounted = true; :>> lavId = ""; }
    part <'LCC-073'> lcc_073 : LccEvent { doc /* STS-80 ET intertank GUCP hydrogen concentration */ :>> flight = "STS-80"; :>> eventDate = "1996-11-19"; :>> lccItem = "ET intertank GUCP hydrogen concentration"; :>> itemGroup = "推進系・ガス"; :>> eventOutcome = "保持"; :>> isWaived = false; :>> isCounted = false; :>> lavId = ""; }
    part <'LCC-074'> lcc_074 : LccEvent { doc /* STS-82 APU 1 injector temperature (LCC limit) */ :>> flight = "STS-82"; :>> eventDate = ""; :>> lccItem = "APU 1 injector temperature (LCC limit)"; :>> itemGroup = "機体・ET・SRB・SSME の計測"; :>> eventOutcome = "免除して打上げ"; :>> isWaived = true; :>> isCounted = true; :>> lavId = ""; }
    part <'LCC-075'> lcc_075 : LccEvent { doc /* STS-83 fuel cell 2 substack 3 cell performance monitor (CPM) differ */ :>> flight = "STS-83"; :>> eventDate = ""; :>> lccItem = "fuel cell 2 substack 3 cell performance monitor (CPM) differential voltage"; :>> itemGroup = "機体・ET・SRB・SSME の計測"; :>> eventOutcome = "免除して打上げ"; :>> isWaived = true; :>> isCounted = false; :>> lavId = ""; }
    part <'LCC-076'> lcc_076 : LccEvent { doc /* STS-88 hydraulic system 1 supply pressure B (master alarm LCC) */ :>> flight = "STS-88"; :>> eventDate = "1998-12-03"; :>> lccItem = "hydraulic system 1 supply pressure B (master alarm LCC)"; :>> itemGroup = "機体・ET・SRB・SSME の計測"; :>> eventOutcome = "スクラブ"; :>> isWaived = false; :>> isCounted = false; :>> lavId = "LAV-070"; }
    part <'LCC-077'> lcc_077 : LccEvent { doc /* STS-91 PRSD O2 tank 5 heater current-limit sensors (simultaneous tr */ :>> flight = "STS-91"; :>> eventDate = ""; :>> lccItem = "PRSD O2 tank 5 heater current-limit sensors (simultaneous trip), LCC waiver pre-approved"; :>> itemGroup = "機体・ET・SRB・SSME の計測"; :>> eventOutcome = "その他"; :>> isWaived = true; :>> isCounted = false; :>> lavId = ""; }
    part <'LCC-078'> lcc_078 : LccEvent { doc /* STS-93 Orbiter aft compartment hydrogen concentration */ :>> flight = "STS-93"; :>> eventDate = "1999-07-20"; :>> lccItem = "Orbiter aft compartment hydrogen concentration"; :>> itemGroup = "推進系・ガス"; :>> eventOutcome = "スクラブ"; :>> isWaived = false; :>> isCounted = true; :>> lavId = "LAV-074"; }
    part <'LCC-079'> lcc_079 : LccEvent { doc /* STS-93 lightning within 20 miles of the launch area (weather LCC) */ :>> flight = "STS-93"; :>> eventDate = "1999-07-22"; :>> lccItem = "lightning within 20 miles of the launch area (weather LCC)"; :>> itemGroup = "天候"; :>> eventOutcome = "スクラブ"; :>> isWaived = false; :>> isCounted = true; :>> lavId = "LAV-075"; }
    part <'LCC-080'> lcc_080 : LccEvent { doc /* STS-96 avionics bay 3A fan differential pressure */ :>> flight = "STS-96"; :>> eventDate = ""; :>> lccItem = "avionics bay 3A fan differential pressure"; :>> itemGroup = "機体・ET・SRB・SSME の計測"; :>> eventOutcome = "免除して打上げ"; :>> isWaived = true; :>> isCounted = true; :>> lavId = ""; }
    part <'LCC-081'> lcc_081 : LccEvent { doc /* STS-101 avionics-bay cooling-fan delta-P upper limit */ :>> flight = "STS-101"; :>> eventDate = ""; :>> lccItem = "avionics-bay cooling-fan delta-P upper limit"; :>> itemGroup = "機体・ET・SRB・SSME の計測"; :>> eventOutcome = "免除して打上げ"; :>> isWaived = true; :>> isCounted = false; :>> lavId = ""; }
    part <'LCC-082'> lcc_082 : LccEvent { doc /* STS-108 APU 2 service line temperature (lower LCC limit) */ :>> flight = "STS-108"; :>> eventDate = "2001-12-04"; :>> lccItem = "APU 2 service line temperature (lower LCC limit)"; :>> itemGroup = "機体・ET・SRB・SSME の計測"; :>> eventOutcome = "免除して打上げ"; :>> isWaived = true; :>> isCounted = false; :>> lavId = ""; }
    part <'LCC-083'> lcc_083 : LccEvent { doc /* STS-110 right RCS fuel system helium regulators leakage */ :>> flight = "STS-110"; :>> eventDate = ""; :>> lccItem = "right RCS fuel system helium regulators leakage"; :>> itemGroup = "機体・ET・SRB・SSME の計測"; :>> eventOutcome = "免除して打上げ"; :>> isWaived = true; :>> isCounted = false; :>> lavId = ""; }
    part <'LCC-084'> lcc_084 : LccEvent { doc /* STS-113 payload bay (midbody) oxygen concentration (LCC: any increas */ :>> flight = "STS-113"; :>> eventDate = "2002-11-10"; :>> lccItem = "payload bay (midbody) oxygen concentration (LCC: any increase above background requires evaluation)"; :>> itemGroup = "推進系・ガス"; :>> eventOutcome = "スクラブ"; :>> isWaived = false; :>> isCounted = true; :>> lavId = "LAV-090"; }
    part <'LCC-085'> lcc_085 : LccEvent { doc /* STS-113 cryogenic helium contamination (PRSD) */ :>> flight = "STS-113"; :>> eventDate = ""; :>> lccItem = "cryogenic helium contamination (PRSD)"; :>> itemGroup = "機体・ET・SRB・SSME の計測"; :>> eventOutcome = "免除して打上げ"; :>> isWaived = true; :>> isCounted = false; :>> lavId = ""; }
    part <'LCC-086'> lcc_086 : LccEvent { doc /* STS-113 fuel cell water relief nozzle temperature */ :>> flight = "STS-113"; :>> eventDate = ""; :>> lccItem = "fuel cell water relief nozzle temperature"; :>> itemGroup = "機体・ET・SRB・SSME の計測"; :>> eventOutcome = "免除して打上げ"; :>> isWaived = true; :>> isCounted = false; :>> lavId = ""; }
    part <'LCC-087'> lcc_087 : LccEvent { doc /* STS-114 ET LH2 ECO sensor 2 indication (LCC MPS-22) */ :>> flight = "STS-114"; :>> eventDate = "2005-07-13"; :>> lccItem = "ET LH2 ECO sensor 2 indication (LCC MPS-22)"; :>> itemGroup = "機体・ET・SRB・SSME の計測"; :>> eventOutcome = "スクラブ"; :>> isWaived = true; :>> isCounted = true; :>> lavId = "LAV-093"; }
    part <'LCC-088'> lcc_088 : LccEvent { doc /* STS-115 ET LH2 ECO sensor 3 (LCC MPS-22) */ :>> flight = "STS-115"; :>> eventDate = "2006-09-08"; :>> lccItem = "ET LH2 ECO sensor 3 (LCC MPS-22)"; :>> itemGroup = "機体・ET・SRB・SSME の計測"; :>> eventOutcome = "スクラブ"; :>> isWaived = false; :>> isCounted = true; :>> lavId = "LAV-097"; }
    part <'LCC-089'> lcc_089 : LccEvent { doc /* STS-116 fuel cell 2 substack 3 cell performance monitor (CPM) sensit */ :>> flight = "STS-116"; :>> eventDate = ""; :>> lccItem = "fuel cell 2 substack 3 cell performance monitor (CPM) sensitivity limit"; :>> itemGroup = "機体・ET・SRB・SSME の計測"; :>> eventOutcome = "免除して打上げ"; :>> isWaived = true; :>> isCounted = false; :>> lavId = ""; }
    part <'LCC-090'> lcc_090 : LccEvent { doc /* STS-117 APU 3 fuel pump drain line temperature 2 */ :>> flight = "STS-117"; :>> eventDate = "2007-06-08"; :>> lccItem = "APU 3 fuel pump drain line temperature 2"; :>> itemGroup = "機体・ET・SRB・SSME の計測"; :>> eventOutcome = "その他"; :>> isWaived = false; :>> isCounted = false; :>> lavId = ""; }
    part <'LCC-091'> lcc_091 : LccEvent { doc /* STS-117 helium injection (bubbling) secondary differential pressure  */ :>> flight = "STS-117"; :>> eventDate = "2007-06-08"; :>> lccItem = "helium injection (bubbling) secondary differential pressure (one of three LCC parameters)"; :>> itemGroup = "機体・ET・SRB・SSME の計測"; :>> eventOutcome = "その他"; :>> isWaived = false; :>> isCounted = false; :>> lavId = ""; }
    part <'LCC-092'> lcc_092 : LccEvent { doc /* STS-118 ICE-01 (TPS crack at Xt 1973 on LO2 feedline inboard base cl */ :>> flight = "STS-118"; :>> eventDate = ""; :>> lccItem = "ICE-01 (TPS crack at Xt 1973 on LO2 feedline inboard base closeout)"; :>> itemGroup = "氷・デブリ・TPS"; :>> eventOutcome = "免除して打上げ"; :>> isWaived = true; :>> isCounted = true; :>> lavId = ""; }
    part <'LCC-093'> lcc_093 : LccEvent { doc /* STS-119 HAZ-09 LH2 leakage at the GUCP (leak detectors LD23 and LD25 */ :>> flight = "STS-119"; :>> eventDate = "2009-03-11"; :>> lccItem = "HAZ-09 LH2 leakage at the GUCP (leak detectors LD23 and LD25)"; :>> itemGroup = "推進系・ガス"; :>> eventOutcome = "スクラブ"; :>> isWaived = false; :>> isCounted = false; :>> lavId = "LAV-102"; }
    part <'LCC-094'> lcc_094 : LccEvent { doc /* STS-119 MPS LH2 ET/Orbiter plate-gap differential pressure (LCC mini */ :>> flight = "STS-119"; :>> eventDate = "2009-03-15"; :>> lccItem = "MPS LH2 ET/Orbiter plate-gap differential pressure (LCC minimum 0.026 psid)"; :>> itemGroup = "機体・ET・SRB・SSME の計測"; :>> eventOutcome = "免除して打上げ"; :>> isWaived = true; :>> isCounted = true; :>> lavId = ""; }
    part <'LCC-095'> lcc_095 : LccEvent { doc /* STS-119 LCC ICE-01 (debris: bat on the ET LH2 tank acreage foam) */ :>> flight = "STS-119"; :>> eventDate = ""; :>> lccItem = "LCC ICE-01 (debris: bat on the ET LH2 tank acreage foam)"; :>> itemGroup = "氷・デブリ・TPS"; :>> eventOutcome = "免除して打上げ"; :>> isWaived = true; :>> isCounted = true; :>> lavId = ""; }
    part <'LCC-096'> lcc_096 : LccEvent { doc /* STS-120 ice at the LH2 umbilical pyrotechnic canister closeout (LCC  */ :>> flight = "STS-120"; :>> eventDate = "2007-10-23"; :>> lccItem = "ice at the LH2 umbilical pyrotechnic canister closeout (LCC ICE-01)"; :>> itemGroup = "氷・デブリ・TPS"; :>> eventOutcome = "免除して打上げ"; :>> isWaived = true; :>> isCounted = true; :>> lavId = ""; }
    part <'LCC-097'> lcc_097 : LccEvent { doc /* STS-121 ET TPS tear at the gap between the fairing and the ET/-Y SRB */ :>> flight = "STS-121"; :>> eventDate = "2006-07-04"; :>> lccItem = "ET TPS tear at the gap between the fairing and the ET/-Y SRB cable tray"; :>> itemGroup = "氷・デブリ・TPS"; :>> eventOutcome = "免除して打上げ"; :>> isWaived = true; :>> isCounted = true; :>> lavId = ""; }
    part <'LCC-098'> lcc_098 : LccEvent { doc /* STS-125 LH2 T-0 umbilical ice/frost (LCC ICE criteria) */ :>> flight = "STS-125"; :>> eventDate = "2009-05-11"; :>> lccItem = "LH2 T-0 umbilical ice/frost (LCC ICE criteria)"; :>> itemGroup = "氷・デブリ・TPS"; :>> eventOutcome = "免除して打上げ"; :>> isWaived = true; :>> isCounted = true; :>> lavId = ""; }
    part <'LCC-099'> lcc_099 : LccEvent { doc /* STS-127 LH2 leakage in the area of the GUCP (40,000 ppm) */ :>> flight = "STS-127"; :>> eventDate = "2009-06-13"; :>> lccItem = "LH2 leakage in the area of the GUCP (40,000 ppm)"; :>> itemGroup = "推進系・ガス"; :>> eventOutcome = "スクラブ"; :>> isWaived = false; :>> isCounted = false; :>> lavId = "LAV-108"; }
    part <'LCC-100'> lcc_100 : LccEvent { doc /* STS-127 LH2 leakage in the area of the GUCP (LCC Haz-09 40,000 ppm p */ :>> flight = "STS-127"; :>> eventDate = "2009-06-17"; :>> lccItem = "LH2 leakage in the area of the GUCP (LCC Haz-09 40,000 ppm per appendix)"; :>> itemGroup = "推進系・ガス"; :>> eventOutcome = "スクラブ"; :>> isWaived = false; :>> isCounted = false; :>> lavId = "LAV-109"; }
    part <'LCC-101'> lcc_101 : LccEvent { doc /* STS-127 FRCS thruster F1D Tyvek rain cover partially debonded */ :>> flight = "STS-127"; :>> eventDate = "2009-07-12"; :>> lccItem = "FRCS thruster F1D Tyvek rain cover partially debonded"; :>> itemGroup = "氷・デブリ・TPS"; :>> eventOutcome = "免除して打上げ"; :>> isWaived = true; :>> isCounted = false; :>> lavId = ""; }
    part <'LCC-102'> lcc_102 : LccEvent { doc /* STS-128 ice at the LH2 T-0 umbilical (LCC ICE-01) */ :>> flight = "STS-128"; :>> eventDate = "2009-08-25"; :>> lccItem = "ice at the LH2 T-0 umbilical (LCC ICE-01)"; :>> itemGroup = "氷・デブリ・TPS"; :>> eventOutcome = "免除して打上げ"; :>> isWaived = true; :>> isCounted = true; :>> lavId = ""; }
    part <'LCC-103'> lcc_103 : LccEvent { doc /* STS-128 LH2 inboard fill-and-drain valve (PV12) closed indication (L */ :>> flight = "STS-128"; :>> eventDate = "2009-08-26"; :>> lccItem = "LH2 inboard fill-and-drain valve (PV12) closed indication (LCC MPS-04)"; :>> itemGroup = "機体・ET・SRB・SSME の計測"; :>> eventOutcome = "スクラブ"; :>> isWaived = false; :>> isCounted = true; :>> lavId = "LAV-115"; }
    part <'LCC-104'> lcc_104 : LccEvent { doc /* STS-128 ice at the LH2 T-0 umbilical (LCC ICE-01) */ :>> flight = "STS-128"; :>> eventDate = "2009-08-28"; :>> lccItem = "ice at the LH2 T-0 umbilical (LCC ICE-01)"; :>> itemGroup = "氷・デブリ・TPS"; :>> eventOutcome = "免除して打上げ"; :>> isWaived = true; :>> isCounted = true; :>> lavId = ""; }
    part <'LCC-105'> lcc_105 : LccEvent { doc /* STS-130 FRCS thruster Tyvek covers (F1D partially debonded, F3D libe */ :>> flight = "STS-130"; :>> eventDate = "2010-02-07"; :>> lccItem = "FRCS thruster Tyvek covers (F1D partially debonded, F3D liberated)"; :>> itemGroup = "氷・デブリ・TPS"; :>> eventOutcome = "免除して打上げ"; :>> isWaived = true; :>> isCounted = false; :>> lavId = ""; }
    part <'LCC-106'> lcc_106 : LccEvent { doc /* STS-130 Ice Detector equipment glass gauge-face fragments on pad lev */ :>> flight = "STS-130"; :>> eventDate = "2010-02-07"; :>> lccItem = "Ice Detector equipment glass gauge-face fragments on pad levels"; :>> itemGroup = "氷・デブリ・TPS"; :>> eventOutcome = "免除して打上げ"; :>> isWaived = true; :>> isCounted = false; :>> lavId = ""; }
    part <'LCC-107'> lcc_107 : LccEvent { doc /* STS-132 LCC ICE-01 (LH2 diagonal strut base closeout TPS crack) */ :>> flight = "STS-132"; :>> eventDate = "2010-05-14"; :>> lccItem = "LCC ICE-01 (LH2 diagonal strut base closeout TPS crack)"; :>> itemGroup = "氷・デブリ・TPS"; :>> eventOutcome = "免除して打上げ"; :>> isWaived = true; :>> isCounted = true; :>> lavId = ""; }
    part <'LCC-108'> lcc_108 : LccEvent { doc /* STS-133 GH2 leakage at the ET/GUCP interface (LCC limit 40,000 ppm) */ :>> flight = "STS-133"; :>> eventDate = "2010-11-05"; :>> lccItem = "GH2 leakage at the ET/GUCP interface (LCC limit 40,000 ppm)"; :>> itemGroup = "推進系・ガス"; :>> eventOutcome = "スクラブ"; :>> isWaived = false; :>> isCounted = false; :>> lavId = "LAV-121"; }
    part <'LCC-109'> lcc_109 : LccEvent { doc /* STS-133 right RCS fuel primary helium regulators internal leakage (S */ :>> flight = "STS-133"; :>> eventDate = "2011-02-22"; :>> lccItem = "right RCS fuel primary helium regulators internal leakage (SODB acceptable limit)"; :>> itemGroup = "機体・ET・SRB・SSME の計測"; :>> eventOutcome = "免除して打上げ"; :>> isWaived = true; :>> isCounted = false; :>> lavId = ""; }
    part <'LCC-110'> lcc_110 : LccEvent { doc /* STS-134 APU 1 Fuel Test Line temperature (APU-14 LCC minimum) */ :>> flight = "STS-134"; :>> eventDate = "2011-04-29"; :>> lccItem = "APU 1 Fuel Test Line temperature (APU-14 LCC minimum)"; :>> itemGroup = "機体・ET・SRB・SSME の計測"; :>> eventOutcome = "スクラブ"; :>> isWaived = false; :>> isCounted = true; :>> lavId = "LAV-124"; }
    part <'LCC-111'> lcc_111 : LccEvent { doc /* STS-134 LCC ICE-01 (RTV debris item on the ET crossbeam) */ :>> flight = "STS-134"; :>> eventDate = ""; :>> lccItem = "LCC ICE-01 (RTV debris item on the ET crossbeam)"; :>> itemGroup = "氷・デブリ・TPS"; :>> eventOutcome = "免除して打上げ"; :>> isWaived = true; :>> isCounted = true; :>> lavId = ""; }
    part <'LCC-112'> lcc_112 : LccEvent { doc /* STS-134 FRCS thruster Tyvek rain covers (F4D and F3F detached, F2D m */ :>> flight = "STS-134"; :>> eventDate = ""; :>> lccItem = "FRCS thruster Tyvek rain covers (F4D and F3F detached, F2D mostly debonded)"; :>> itemGroup = "氷・デブリ・TPS"; :>> eventOutcome = "免除して打上げ"; :>> isWaived = true; :>> isCounted = false; :>> lavId = ""; }
}
