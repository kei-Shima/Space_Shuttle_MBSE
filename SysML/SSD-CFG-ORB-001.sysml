// SysML v2 テキスト：構成の変遷定義書（機体・機器・ソフトウェア・手順の初飛行と改修の記録）
// SSD-CFG-ORB-001 構成の変遷定義書（機体・機器・ソフトウェア・手順の初飛行と改修の記録） の表から生成（lib/build_docs_cw.py・rev_cw/cwdata.py）。根拠の頁は SSD-CFG-ORB-001 にある。
package SSD_CFG_ORB_001 {
    doc /* SSD-CFG-ORB-001 構成の変遷定義書（機体・機器・ソフトウェア・手順の初飛行と改修の記録）。初飛行・改修の記録を part def ConfigChange の使用として持つ。飛行・打上げ日・機能ブロック・種別・対象は文字列の属性で、パッケージへの矢印は張らない。要求への関係（導出・充足・検証）は張らず、トレースの外に置く。 */
    private import ScalarValues::*;
    part def ConfigChange {
        doc /* 機体・機器・ソフトウェア・手順の初飛行・改修の記録。Mission Report 本文にある分で、全数ではない。機能ブロック・種別は本書の判断（PLAN_CW） */
        attribute flight : String;
        attribute launchDate : String;
        attribute block : String;
        attribute kind : String;
        attribute changedPart : String;
    }
    part <'CFG-001'> cfg_001 : ConfigChange { doc /* STS-2 */ :>> flight = "STS-2"; :>> launchDate = "1981-11-12"; :>> block = "EPS"; :>> kind = "新型ハードウェア"; :>> changedPart = "bus tie operation (fuel cell 1 loss)"; }
    part <'CFG-002'> cfg_002 : ConfigChange { doc /* STS-2 */ :>> flight = "STS-2"; :>> launchDate = "1981-11-12"; :>> block = "CT"; :>> kind = "新型ハードウェア"; :>> changedPart = "wireless crew communications systems"; }
    part <'CFG-003'> cfg_003 : ConfigChange { doc /* STS-3 */ :>> flight = "STS-3"; :>> launchDate = "1982-03-22"; :>> block = "ECLSS"; :>> kind = "新型ハードウェア"; :>> changedPart = "full interchanger water flow for cabin temperature control"; }
    part <'CFG-004'> cfg_004 : ConfigChange { doc /* STS-3 */ :>> flight = "STS-3"; :>> launchDate = "1982-03-22"; :>> block = "CT"; :>> kind = "新型ハードウェア"; :>> changedPart = "new interior film (crew camera film)"; }
    part <'CFG-005'> cfg_005 : ConfigChange { doc /* STS-4 */ :>> flight = "STS-4"; :>> launchDate = "1982-06-27"; :>> block = "EPS"; :>> kind = "新型ハードウェア"; :>> changedPart = "PRSD tanks depleted to residual quantities"; }
    part <'CFG-006'> cfg_006 : ConfigChange { doc /* STS-4 */ :>> flight = "STS-4"; :>> launchDate = "1982-06-27"; :>> block = "CREW"; :>> kind = "新型ハードウェア"; :>> changedPart = "large jettison bag"; }
    part <'CFG-007'> cfg_007 : ConfigChange { doc /* STS-4 */ :>> flight = "STS-4"; :>> launchDate = "1982-06-27"; :>> block = "CT"; :>> kind = "改修"; :>> changedPart = "UHF frequency change on orbit"; }
    part <'CFG-008'> cfg_008 : ConfigChange { doc /* STS-4 */ :>> flight = "STS-4"; :>> launchDate = "1982-06-27"; :>> block = "CREW"; :>> kind = "新型ハードウェア"; :>> changedPart = "food freezer"; }
    part <'CFG-009'> cfg_009 : ConfigChange { doc /* STS-4 */ :>> flight = "STS-4"; :>> launchDate = "1982-06-27"; :>> block = "PLS"; :>> kind = "新型ハードウェア"; :>> changedPart = "payload bay liner"; }
    part <'CFG-010'> cfg_010 : ConfigChange { doc /* STS-5 */ :>> flight = "STS-5"; :>> launchDate = "1982-11-11"; :>> block = "ET"; :>> kind = "新型ハードウェア"; :>> changedPart = "External Tank without an antigeyser line"; }
    part <'CFG-011'> cfg_011 : ConfigChange { doc /* STS-5 */ :>> flight = "STS-5"; :>> launchDate = "1982-11-11"; :>> block = "GNC"; :>> kind = "新型ハードウェア"; :>> changedPart = "OTT (optional TAEM targeting) TAEM guidance"; }
    part <'CFG-012'> cfg_012 : ConfigChange { doc /* STS-6 */ :>> flight = "STS-6"; :>> launchDate = "1983-04-04"; :>> block = "MECH"; :>> kind = "新型ハードウェア"; :>> changedPart = "vehicle OV-099 (Challenger)"; }
    part <'CFG-013'> cfg_013 : ConfigChange { doc /* STS-9 */ :>> flight = "STS-9"; :>> launchDate = "1983-11-28"; :>> block = "EPS"; :>> kind = "新型ハードウェア"; :>> changedPart = "3 substack fuel cells"; }
    part <'CFG-014'> cfg_014 : ConfigChange { doc /* STS-26 */ :>> flight = "STS-26"; :>> launchDate = "1988-09-29"; :>> block = "EPS"; :>> kind = "改修"; :>> changedPart = "improved fuel cell (FCP 2)"; }
    part <'CFG-015'> cfg_015 : ConfigChange { doc /* STS-26 */ :>> flight = "STS-26"; :>> launchDate = "1988-09-29"; :>> block = "ECLSS"; :>> kind = "新型ハードウェア"; :>> changedPart = "alternate water removal system"; }
    part <'CFG-016'> cfg_016 : ConfigChange { doc /* STS-27 */ :>> flight = "STS-27"; :>> launchDate = "1988-12-02"; :>> block = "TCS"; :>> kind = "新型ハードウェア"; :>> changedPart = "revised B-leg keel web heater thermostat"; }
    part <'CFG-017'> cfg_017 : ConfigChange { doc /* STS-28 */ :>> flight = "STS-28"; :>> launchDate = "1989-08-08"; :>> block = "MPS"; :>> kind = "新型ハードウェア"; :>> changedPart = "crossfeed-line pressure transducers"; }
    part <'CFG-018'> cfg_018 : ConfigChange { doc /* STS-29 */ :>> flight = "STS-29"; :>> launchDate = "1989-03-13"; :>> block = "CT"; :>> kind = "新型ハードウェア"; :>> changedPart = "TDRS coverage through the entry blackout period"; }
    part <'CFG-019'> cfg_019 : ConfigChange { doc /* STS-31 */ :>> flight = "STS-31"; :>> launchDate = "1990-04-24"; :>> block = "MPS"; :>> kind = "新型ハードウェア"; :>> changedPart = "strain gages on SSME high pressure oxidizer turbopumps"; }
    part <'CFG-020'> cfg_020 : ConfigChange { doc /* STS-35 */ :>> flight = "STS-35"; :>> launchDate = "1990-12-02"; :>> block = "ECLSS"; :>> kind = "改修"; :>> changedPart = "improved waste collection system"; }
    part <'CFG-021'> cfg_021 : ConfigChange { doc /* STS-38 */ :>> flight = "STS-38"; :>> launchDate = "1990-11-15"; :>> block = "MPS"; :>> kind = "新型ハードウェア"; :>> changedPart = "step 2 gaseous oxygen fixed-orifice flow control valve"; }
    part <'CFG-022'> cfg_022 : ConfigChange { doc /* STS-40 */ :>> flight = "STS-40"; :>> launchDate = "1991-06-05"; :>> block = "MPS"; :>> kind = "新型ハードウェア"; :>> changedPart = "gaseous oxygen flow control valves fixed in one position"; }
    part <'CFG-023'> cfg_023 : ConfigChange { doc /* STS-41 */ :>> flight = "STS-41"; :>> launchDate = ""; :>> block = "MPS"; :>> kind = "新型ハードウェア"; :>> changedPart = "step-1 gaseous oxygen fixed orifice/flow control valve"; }
    part <'CFG-024'> cfg_024 : ConfigChange { doc /* STS-41 */ :>> flight = "STS-41"; :>> launchDate = ""; :>> block = "MPS"; :>> kind = "運用・手順"; :>> changedPart = "direct insertion +X RCS settling maneuver at MPS dump start (deleted)"; }
    part <'CFG-025'> cfg_025 : ConfigChange { doc /* STS-41B */ :>> flight = "STS-41B"; :>> launchDate = "1984-02-03"; :>> block = "EVA"; :>> kind = "運用・手順"; :>> changedPart = "MMU (manned maneuvering unit) untethered EVA"; }
    part <'CFG-026'> cfg_026 : ConfigChange { doc /* STS-43 */ :>> flight = "STS-43"; :>> launchDate = "1991-08-02"; :>> block = "MPS"; :>> kind = "新型ハードウェア"; :>> changedPart = "gaseous oxygen fixed-orifice flow control valve (shimmed to 78 percent flow area"; }
    part <'CFG-027'> cfg_027 : ConfigChange { doc /* STS-44 */ :>> flight = "STS-44"; :>> launchDate = "1991-11-24"; :>> block = "ECLSS"; :>> kind = "新型ハードウェア"; :>> changedPart = "water coolant loop bypass valve temperature controller (automatic position)"; }
    part <'CFG-028'> cfg_028 : ConfigChange { doc /* STS-44 */ :>> flight = "STS-44"; :>> launchDate = "1991-11-24"; :>> block = "CT"; :>> kind = "新型ハードウェア"; :>> changedPart = "color television (TV) monitor 2"; }
    part <'CFG-029'> cfg_029 : ConfigChange { doc /* STS-44 */ :>> flight = "STS-44"; :>> launchDate = "1991-11-24"; :>> block = "DPS"; :>> kind = "新型ハードウェア"; :>> changedPart = "display driver unit (DDU) filter cleaning tool"; }
    part <'CFG-030'> cfg_030 : ConfigChange { doc /* STS-46 */ :>> flight = "STS-46"; :>> launchDate = "1992-07-31"; :>> block = "CREW"; :>> kind = "改修"; :>> changedPart = "redesigned flight deck speaker"; }
    part <'CFG-031'> cfg_031 : ConfigChange { doc /* STS-48 */ :>> flight = "STS-48"; :>> launchDate = "1991-09-12"; :>> block = "MPS"; :>> kind = "新型ハードウェア"; :>> changedPart = "gaseous oxygen fixed-orifice configuration flow control valves on OV-103"; }
    part <'CFG-032'> cfg_032 : ConfigChange { doc /* STS-48 */ :>> flight = "STS-48"; :>> launchDate = "1991-09-12"; :>> block = "DPS"; :>> kind = "改修"; :>> changedPart = "redesigned manipulator controller interface unit (MCIU)"; }
    part <'CFG-033'> cfg_033 : ConfigChange { doc /* STS-48 */ :>> flight = "STS-48"; :>> launchDate = "1991-09-12"; :>> block = "DPS"; :>> kind = "ソフトウェア"; :>> changedPart = "RMS with OI-20 software"; }
    part <'CFG-034'> cfg_034 : ConfigChange { doc /* STS-49 */ :>> flight = "STS-49"; :>> launchDate = "1992-05-07"; :>> block = "MPS"; :>> kind = "新型ハードウェア"; :>> changedPart = "-0006 750-psi helium regulators"; }
    part <'CFG-035'> cfg_035 : ConfigChange { doc /* STS-49 */ :>> flight = "STS-49"; :>> launchDate = "1992-05-07"; :>> block = "MPS"; :>> kind = "新型ハードウェア"; :>> changedPart = "-0006 850-psi helium relief valves"; }
    part <'CFG-036'> cfg_036 : ConfigChange { doc /* STS-49 */ :>> flight = "STS-49"; :>> launchDate = "1992-05-07"; :>> block = "ET"; :>> kind = "改修"; :>> changedPart = "liquid hydrogen ET/Orbiter umbilical spacer modification"; }
    part <'CFG-037'> cfg_037 : ConfigChange { doc /* STS-49 */ :>> flight = "STS-49"; :>> launchDate = "1992-05-07"; :>> block = "ECLSS"; :>> kind = "運用・手順"; :>> changedPart = "simultaneous dump of supply water and waste water (DTO 325)"; }
    part <'CFG-038'> cfg_038 : ConfigChange { doc /* STS-49 */ :>> flight = "STS-49"; :>> launchDate = "1992-05-07"; :>> block = "GNC"; :>> kind = "新型ハードウェア"; :>> changedPart = "TACANs manufactured by Collins"; }
    part <'CFG-039'> cfg_039 : ConfigChange { doc /* STS-50 */ :>> flight = "STS-50"; :>> launchDate = "1992-06-25"; :>> block = "ECLSS"; :>> kind = "新型ハードウェア"; :>> changedPart = "regenerable CO2 removal subsystem (RCRS)"; }
    part <'CFG-040'> cfg_040 : ConfigChange { doc /* STS-50 */ :>> flight = "STS-50"; :>> launchDate = "1992-06-25"; :>> block = "PLS"; :>> kind = "新型ハードウェア"; :>> changedPart = "Extended Duration Orbiter (EDO) cryogenics pallet"; }
    part <'CFG-041'> cfg_041 : ConfigChange { doc /* STS-50 */ :>> flight = "STS-50"; :>> launchDate = "1992-06-25"; :>> block = "APU"; :>> kind = "改修"; :>> changedPart = "improved auxiliary power unit (IAPU)"; }
    part <'CFG-042'> cfg_042 : ConfigChange { doc /* STS-50 */ :>> flight = "STS-50"; :>> launchDate = "1992-06-25"; :>> block = "MECH"; :>> kind = "新型ハードウェア"; :>> changedPart = "drag chute"; }
    part <'CFG-043'> cfg_043 : ConfigChange { doc /* STS-51 */ :>> flight = "STS-51"; :>> launchDate = "1993-09-12"; :>> block = "TCS"; :>> kind = "新型ハードウェア"; :>> changedPart = "ammonia boiler system A secondary controller"; }
    part <'CFG-044'> cfg_044 : ConfigChange { doc /* STS-51D */ :>> flight = "STS-51D"; :>> launchDate = "1985-04-12"; :>> block = "PLS"; :>> kind = "新型ハードウェア"; :>> changedPart = "contingency EVA (flyswatter devices attached to RMS end effector)"; }
    part <'CFG-045'> cfg_045 : ConfigChange { doc /* STS-52 */ :>> flight = "STS-52"; :>> launchDate = "1992-10-22"; :>> block = "SRB"; :>> kind = "新型ハードウェア"; :>> changedPart = "MSFC-developed booster trowelable ablator"; }
    part <'CFG-046'> cfg_046 : ConfigChange { doc /* STS-52 */ :>> flight = "STS-52"; :>> launchDate = "1992-10-22"; :>> block = "OMS"; :>> kind = "運用・手順"; :>> changedPart = "RMS left uncradled during an OMS maneuver"; }
    part <'CFG-047'> cfg_047 : ConfigChange { doc /* STS-54 */ :>> flight = "STS-54"; :>> launchDate = "1993-01-13"; :>> block = "ECLSS"; :>> kind = "新型ハードウェア"; :>> changedPart = "Extended Duration Orbiter (EDO) waste collection system"; }
    part <'CFG-048'> cfg_048 : ConfigChange { doc /* STS-55 */ :>> flight = "STS-55"; :>> launchDate = "1993-04-26"; :>> block = "TCS"; :>> kind = "新型ハードウェア"; :>> changedPart = "system A ammonia boiler"; }
    part <'CFG-049'> cfg_049 : ConfigChange { doc /* STS-56 */ :>> flight = "STS-56"; :>> launchDate = "1993-04-08"; :>> block = "ECLSS"; :>> kind = "改修"; :>> changedPart = "phase I fan separator design modifications"; }
    part <'CFG-050'> cfg_050 : ConfigChange { doc /* STS-56 */ :>> flight = "STS-56"; :>> launchDate = "1993-04-08"; :>> block = "PLS"; :>> kind = "新型ハードウェア"; :>> changedPart = "RMS end effector serial number 403"; }
    part <'CFG-051'> cfg_051 : ConfigChange { doc /* STS-57 */ :>> flight = "STS-57"; :>> launchDate = "1993-06-21"; :>> block = "APU"; :>> kind = "改修"; :>> changedPart = "improved APU controller"; }
    part <'CFG-052'> cfg_052 : ConfigChange { doc /* STS-57 */ :>> flight = "STS-57"; :>> launchDate = "1993-06-21"; :>> block = "MECH"; :>> kind = "新型ハードウェア"; :>> changedPart = "tunnel adapter C hatch used for an EVA"; }
    part <'CFG-053'> cfg_053 : ConfigChange { doc /* STS-58 */ :>> flight = "STS-58"; :>> launchDate = "1993-10-18"; :>> block = "TCS"; :>> kind = "新型ハードウェア"; :>> changedPart = "ammonia boiler system secondary A controller"; }
    part <'CFG-054'> cfg_054 : ConfigChange { doc /* STS-59 */ :>> flight = "STS-59"; :>> launchDate = "1994-04-09"; :>> block = "GNC"; :>> kind = "新型ハードウェア"; :>> changedPart = "beep / RHC trim derotation commands"; }
    part <'CFG-055'> cfg_055 : ConfigChange { doc /* STS-59 */ :>> flight = "STS-59"; :>> launchDate = "1994-04-09"; :>> block = "TPS"; :>> kind = "新型ハードウェア"; :>> changedPart = "toughened unipiece fibrous insulation (TUFI) tiles"; }
    part <'CFG-056'> cfg_056 : ConfigChange { doc /* STS-60 */ :>> flight = "STS-60"; :>> launchDate = "1994-02-03"; :>> block = "MPS"; :>> kind = "改修"; :>> changedPart = "MPS liquid oxygen bleed check valves (redesigned)"; }
    part <'CFG-057'> cfg_057 : ConfigChange { doc /* STS-60 */ :>> flight = "STS-60"; :>> launchDate = "1994-02-03"; :>> block = "MPS"; :>> kind = "新型ハードウェア"; :>> changedPart = "actual 750-psi regulator calibrations"; }
    part <'CFG-058'> cfg_058 : ConfigChange { doc /* STS-61 */ :>> flight = "STS-61"; :>> launchDate = "1993-12-02"; :>> block = "MPS"; :>> kind = "改修"; :>> changedPart = "MPS LO2 bleed check valves (redesigned)"; }
    part <'CFG-059'> cfg_059 : ConfigChange { doc /* STS-61 */ :>> flight = "STS-61"; :>> launchDate = "1993-12-02"; :>> block = "EPS"; :>> kind = "新型ハードウェア"; :>> changedPart = "fifth PRSD tank set"; }
    part <'CFG-060'> cfg_060 : ConfigChange { doc /* STS-61 */ :>> flight = "STS-61"; :>> launchDate = "1993-12-02"; :>> block = "APU"; :>> kind = "運用・手順"; :>> changedPart = "crew procedure change moving APU water system heater activation to just after AP"; }
    part <'CFG-061'> cfg_061 : ConfigChange { doc /* STS-61 */ :>> flight = "STS-61"; :>> launchDate = "1993-12-02"; :>> block = "ECLSS"; :>> kind = "新型ハードウェア"; :>> changedPart = "ammonia boiler system (ABS) unit after heat exchanger replacement"; }
    part <'CFG-062'> cfg_062 : ConfigChange { doc /* STS-61 */ :>> flight = "STS-61"; :>> launchDate = "1993-12-02"; :>> block = "GNC"; :>> kind = "新型ハードウェア"; :>> changedPart = "High Accuracy Inertial Navigation System (HAINS) IMUs"; }
    part <'CFG-063'> cfg_063 : ConfigChange { doc /* STS-61 */ :>> flight = "STS-61"; :>> launchDate = "1993-12-02"; :>> block = "PLS"; :>> kind = "新型ハードウェア"; :>> changedPart = "note in the Flight Data File on RMS arm deselection messages"; }
    part <'CFG-064'> cfg_064 : ConfigChange { doc /* STS-61B */ :>> flight = "STS-61B"; :>> launchDate = "1986-11-27"; :>> block = "SRB"; :>> kind = "改修"; :>> changedPart = "reconfigured waste nozzle (redesigned nozzles)"; }
    part <'CFG-065'> cfg_065 : ConfigChange { doc /* STS-63 */ :>> flight = "STS-63"; :>> launchDate = "1995-02-03"; :>> block = "DPS"; :>> kind = "ソフトウェア"; :>> changedPart = "dump patch to the OI-23 software"; }
    part <'CFG-066'> cfg_066 : ConfigChange { doc /* STS-63 */ :>> flight = "STS-63"; :>> launchDate = "1995-02-03"; :>> block = "ECLSS"; :>> kind = "新型ハードウェア"; :>> changedPart = "ammonia system A controller (adjusted)"; }
    part <'CFG-067'> cfg_067 : ConfigChange { doc /* STS-64 */ :>> flight = "STS-64"; :>> launchDate = ""; :>> block = "APU"; :>> kind = "新型ハードウェア"; :>> changedPart = "titanium thermal isolator sleeve (APU gear box / fuel pump)"; }
    part <'CFG-068'> cfg_068 : ConfigChange { doc /* STS-64 */ :>> flight = "STS-64"; :>> launchDate = ""; :>> block = "ECLSS"; :>> kind = "新型ハードウェア"; :>> changedPart = "supply water dump line purge assembly (SWDLPA)"; }
    part <'CFG-069'> cfg_069 : ConfigChange { doc /* STS-64 */ :>> flight = "STS-64"; :>> launchDate = ""; :>> block = "DPS"; :>> kind = "ソフトウェア"; :>> changedPart = "OI-23 software (RMS position orientation hold select mode)"; }
    part <'CFG-070'> cfg_070 : ConfigChange { doc /* STS-65 */ :>> flight = "STS-65"; :>> launchDate = "1994-07-08"; :>> block = "MPS"; :>> kind = "ソフトウェア"; :>> changedPart = "OI-23 software (automated MPS vacuum inerting)"; }
    part <'CFG-071'> cfg_071 : ConfigChange { doc /* STS-65 */ :>> flight = "STS-65"; :>> launchDate = "1994-07-08"; :>> block = "MPS"; :>> kind = "ソフトウェア"; :>> changedPart = "MPS dump and vacuum inerting procedures developed for OI-23"; }
    part <'CFG-072'> cfg_072 : ConfigChange { doc /* STS-65 */ :>> flight = "STS-65"; :>> launchDate = "1994-07-08"; :>> block = "MPS"; :>> kind = "ソフトウェア"; :>> changedPart = "automated MPS helium system entry configuration (OI-23)"; }
    part <'CFG-073'> cfg_073 : ConfigChange { doc /* STS-66 */ :>> flight = "STS-66"; :>> launchDate = "1994-11-03"; :>> block = "PLS"; :>> kind = "新型ハードウェア"; :>> changedPart = "remote manipulator system arm S/N 202"; }
    part <'CFG-074'> cfg_074 : ConfigChange { doc /* STS-67 */ :>> flight = "STS-67"; :>> launchDate = "1995-03-02"; :>> block = "MPS"; :>> kind = "新型ハードウェア"; :>> changedPart = "new LO2 replenish valve"; }
    part <'CFG-075'> cfg_075 : ConfigChange { doc /* STS-67 */ :>> flight = "STS-67"; :>> launchDate = "1995-03-02"; :>> block = "PLS"; :>> kind = "新型ハードウェア"; :>> changedPart = "EDO pallet on a vehicle other than OV-102"; }
    part <'CFG-076'> cfg_076 : ConfigChange { doc /* STS-67 */ :>> flight = "STS-67"; :>> launchDate = "1995-03-02"; :>> block = "EPS"; :>> kind = "新型ハードウェア"; :>> changedPart = "nine-tank-set (PRSD) configuration"; }
    part <'CFG-077'> cfg_077 : ConfigChange { doc /* STS-68 */ :>> flight = "STS-68"; :>> launchDate = "1994-09-30"; :>> block = "APU"; :>> kind = "新型ハードウェア"; :>> changedPart = "new water valves (APU water spray boiler)"; }
    part <'CFG-078'> cfg_078 : ConfigChange { doc /* STS-69 */ :>> flight = "STS-69"; :>> launchDate = "1995-09-07"; :>> block = "APU"; :>> kind = "改修"; :>> changedPart = "WSB electric-heater modification"; }
    part <'CFG-079'> cfg_079 : ConfigChange { doc /* STS-69 */ :>> flight = "STS-69"; :>> launchDate = "1995-09-07"; :>> block = "GNC"; :>> kind = "運用・手順"; :>> changedPart = "ground-commanded Orbiter maneuvers during crew sleep"; }
    part <'CFG-080'> cfg_080 : ConfigChange { doc /* STS-69 */ :>> flight = "STS-69"; :>> launchDate = "1995-09-07"; :>> block = "SRB"; :>> kind = "新型ハードウェア"; :>> changedPart = "RSRM set (48) made from propellant of the new M-314 propellant premix facility"; }
    part <'CFG-081'> cfg_081 : ConfigChange { doc /* STS-69 */ :>> flight = "STS-69"; :>> launchDate = "1995-09-07"; :>> block = "MPS"; :>> kind = "新型ハードウェア"; :>> changedPart = "re-oriented GH2 flow control valve manifold assembly"; }
    part <'CFG-082'> cfg_082 : ConfigChange { doc /* STS-70 */ :>> flight = "STS-70"; :>> launchDate = ""; :>> block = "STR"; :>> kind = "新型ハードウェア"; :>> changedPart = "W6 window"; }
    part <'CFG-083'> cfg_083 : ConfigChange { doc /* STS-70 */ :>> flight = "STS-70"; :>> launchDate = ""; :>> block = "MPS"; :>> kind = "改修"; :>> changedPart = "SSME vent modification"; }
    part <'CFG-084'> cfg_084 : ConfigChange { doc /* STS-70 */ :>> flight = "STS-70"; :>> launchDate = ""; :>> block = "MPS"; :>> kind = "新型ハードウェア"; :>> changedPart = "Block 1 engine (SSME)"; }
    part <'CFG-085'> cfg_085 : ConfigChange { doc /* STS-70 */ :>> flight = "STS-70"; :>> launchDate = ""; :>> block = "DPS"; :>> kind = "新型ハードウェア"; :>> changedPart = "day of launch I-loads-II (DOLILU II)"; }
    part <'CFG-086'> cfg_086 : ConfigChange { doc /* STS-70 */ :>> flight = "STS-70"; :>> launchDate = ""; :>> block = "MPS"; :>> kind = "新型ハードウェア"; :>> changedPart = "-6 degree turnaround position for SSME pitch"; }
    part <'CFG-087'> cfg_087 : ConfigChange { doc /* STS-71 */ :>> flight = "STS-71"; :>> launchDate = "1995-06-27"; :>> block = "PLS"; :>> kind = "新型ハードウェア"; :>> changedPart = "APDS (androgynous peripheral docking system) on the Orbiter"; }
    part <'CFG-088'> cfg_088 : ConfigChange { doc /* STS-71 */ :>> flight = "STS-71"; :>> launchDate = "1995-06-27"; :>> block = "APU"; :>> kind = "新型ハードウェア"; :>> changedPart = "relocated main case drain temperature sensors on hydraulic systems 1 and 2"; }
    part <'CFG-089'> cfg_089 : ConfigChange { doc /* STS-71 */ :>> flight = "STS-71"; :>> launchDate = "1995-06-27"; :>> block = "CREW"; :>> kind = "新型ハードウェア"; :>> changedPart = "recumbent seat system"; }
    part <'CFG-090'> cfg_090 : ConfigChange { doc /* STS-72 */ :>> flight = "STS-72"; :>> launchDate = "1996-01-11"; :>> block = "MPS"; :>> kind = "新型ハードウェア"; :>> changedPart = "water spray boiler (WSB) water feedline electric heaters"; }
    part <'CFG-091'> cfg_091 : ConfigChange { doc /* STS-73 */ :>> flight = "STS-73"; :>> launchDate = "1995-10-20"; :>> block = "MPS"; :>> kind = "新型ハードウェア"; :>> changedPart = "two Block 1 SSMEs"; }
    part <'CFG-092'> cfg_092 : ConfigChange { doc /* STS-73 */ :>> flight = "STS-73"; :>> launchDate = "1995-10-20"; :>> block = "MPS"; :>> kind = "改修"; :>> changedPart = "GH2 pressurization system modifications"; }
    part <'CFG-093'> cfg_093 : ConfigChange { doc /* STS-73 */ :>> flight = "STS-73"; :>> launchDate = "1995-10-20"; :>> block = "ET"; :>> kind = "新型ハードウェア"; :>> changedPart = "ET door thermal barriers"; }
    part <'CFG-094'> cfg_094 : ConfigChange { doc /* STS-74 */ :>> flight = "STS-74"; :>> launchDate = "1995-11-12"; :>> block = "MPS"; :>> kind = "改修"; :>> changedPart = "gaseous helium pressurization system modifications"; }
    part <'CFG-095'> cfg_095 : ConfigChange { doc /* STS-74 */ :>> flight = "STS-74"; :>> launchDate = "1995-11-12"; :>> block = "RCS"; :>> kind = "新型ハードウェア"; :>> changedPart = "minimum-angle thruster-selection algorithm"; }
    part <'CFG-096'> cfg_096 : ConfigChange { doc /* STS-76 */ :>> flight = "STS-76"; :>> launchDate = "1996-03-22"; :>> block = "MPS"; :>> kind = "改修"; :>> changedPart = "GH2 pressurization system modifications"; }
    part <'CFG-097'> cfg_097 : ConfigChange { doc /* STS-76 */ :>> flight = "STS-76"; :>> launchDate = "1996-03-22"; :>> block = "EVA"; :>> kind = "新型ハードウェア"; :>> changedPart = "oxygen transfer system (Orbiter/Mir)"; }
    part <'CFG-098'> cfg_098 : ConfigChange { doc /* STS-76 */ :>> flight = "STS-76"; :>> launchDate = "1996-03-22"; :>> block = "APU"; :>> kind = "新型ハードウェア"; :>> changedPart = "hydraulic system 1 circulation pump start (option exercised because of an anomal"; }
    part <'CFG-099'> cfg_099 : ConfigChange { doc /* STS-77 */ :>> flight = "STS-77"; :>> launchDate = "1996-05-19"; :>> block = "MPS"; :>> kind = "新型ハードウェア"; :>> changedPart = "cluster of three Block 1 SSMEs"; }
    part <'CFG-100'> cfg_100 : ConfigChange { doc /* STS-77 */ :>> flight = "STS-77"; :>> launchDate = "1996-05-19"; :>> block = "APU"; :>> kind = "運用・手順"; :>> changedPart = "DTO 416 WSB Quick Restart"; }
    part <'CFG-101'> cfg_101 : ConfigChange { doc /* STS-78 */ :>> flight = "STS-78"; :>> launchDate = "1996-06-20"; :>> block = "MPS"; :>> kind = "改修"; :>> changedPart = "GHe pressurization system modifications and filters (OV-102)"; }
    part <'CFG-102'> cfg_102 : ConfigChange { doc /* STS-80 */ :>> flight = "STS-80"; :>> launchDate = "1996-11-19"; :>> block = "MPS"; :>> kind = "新型ハードウェア"; :>> changedPart = "reshimmed -1301 configuration of the GH2 flow control valves"; }
    part <'CFG-103'> cfg_103 : ConfigChange { doc /* STS-81 */ :>> flight = "STS-81"; :>> launchDate = "1997-01-12"; :>> block = "PLS"; :>> kind = "新型ハードウェア"; :>> changedPart = "targets mounted on the Orbiter bulkheads (payload bay camera aiming)"; }
    part <'CFG-104'> cfg_104 : ConfigChange { doc /* STS-81 */ :>> flight = "STS-81"; :>> launchDate = "1997-01-12"; :>> block = "GNC"; :>> kind = "運用・手順"; :>> changedPart = "GPS/INS (DTO 700-12, LN-100G)"; }
    part <'CFG-105'> cfg_105 : ConfigChange { doc /* STS-82 */ :>> flight = "STS-82"; :>> launchDate = "1997-02-11"; :>> block = "MPS"; :>> kind = "新型ハードウェア"; :>> changedPart = "reshimmed GH2 flow control valves (OV-103)"; }
    part <'CFG-106'> cfg_106 : ConfigChange { doc /* STS-82 */ :>> flight = "STS-82"; :>> launchDate = "1997-02-11"; :>> block = "EVA"; :>> kind = "新型ハードウェア"; :>> changedPart = "on-orbit resizing of the EMU (EVA suits)"; }
    part <'CFG-107'> cfg_107 : ConfigChange { doc /* STS-83 */ :>> flight = "STS-83"; :>> launchDate = "1997-04-04"; :>> block = "MECH"; :>> kind = "新型ハードウェア"; :>> changedPart = "recoverable pilot parachutes"; }
    part <'CFG-108'> cfg_108 : ConfigChange { doc /* STS-83 */ :>> flight = "STS-83"; :>> launchDate = "1997-04-04"; :>> block = "MECH"; :>> kind = "新型ハードウェア"; :>> changedPart = "drogue parachute deployment bags"; }
    part <'CFG-109'> cfg_109 : ConfigChange { doc /* STS-84 */ :>> flight = "STS-84"; :>> launchDate = "1997-05-15"; :>> block = "PLS"; :>> kind = "改修"; :>> changedPart = "lightweight seat and internal airlock"; }
    part <'CFG-110'> cfg_110 : ConfigChange { doc /* STS-84 */ :>> flight = "STS-84"; :>> launchDate = "1997-05-15"; :>> block = "MPS"; :>> kind = "新型ハードウェア"; :>> changedPart = "new liquid hydrogen (LH2) tank sidewall TPS (NCFI 24-184)"; }
    part <'CFG-111'> cfg_111 : ConfigChange { doc /* STS-85 */ :>> flight = "STS-85"; :>> launchDate = "1997-08-07"; :>> block = "ECLSS"; :>> kind = "新型ハードウェア"; :>> changedPart = "vapor-deposit transducer (new)"; }
    part <'CFG-112'> cfg_112 : ConfigChange { doc /* STS-86 */ :>> flight = "STS-86"; :>> launchDate = "1997-09-25"; :>> block = "ET"; :>> kind = "新型ハードウェア"; :>> changedPart = "composite nose cone (ET)"; }
    part <'CFG-113'> cfg_113 : ConfigChange { doc /* STS-86 */ :>> flight = "STS-86"; :>> launchDate = "1997-09-25"; :>> block = "CT"; :>> kind = "運用・手順"; :>> changedPart = "S-band Sequential Still Video (SSV) system (DTO 700-16)"; }
    part <'CFG-114'> cfg_114 : ConfigChange { doc /* STS-87 */ :>> flight = "STS-87"; :>> launchDate = "1997-11-19"; :>> block = "EPS"; :>> kind = "新型ハードウェア"; :>> changedPart = "fuel cell monitoring system (FCMS)"; }
    part <'CFG-115'> cfg_115 : ConfigChange { doc /* STS-87 */ :>> flight = "STS-87"; :>> launchDate = "1997-11-19"; :>> block = "ECLSS"; :>> kind = "新型ハードウェア"; :>> changedPart = "infrared carbon dioxide sensors"; }
    part <'CFG-116'> cfg_116 : ConfigChange { doc /* STS-88 */ :>> flight = "STS-88"; :>> launchDate = "1998-12-04"; :>> block = "APU"; :>> kind = "改修"; :>> changedPart = "burst disk added between APU drain line pressure measurements and relief valve"; }
    part <'CFG-117'> cfg_117 : ConfigChange { doc /* STS-89 */ :>> flight = "STS-89"; :>> launchDate = "1998-01-22"; :>> block = "MPS"; :>> kind = "新型ハードウェア"; :>> changedPart = "Block IIA Space Shuttle main engines (SSMEs)"; }
    part <'CFG-118'> cfg_118 : ConfigChange { doc /* STS-89 */ :>> flight = "STS-89"; :>> launchDate = "1998-01-22"; :>> block = "EPS"; :>> kind = "新型ハードウェア"; :>> changedPart = "fuel cell monitoring system (FCMS)"; }
    part <'CFG-119'> cfg_119 : ConfigChange { doc /* STS-90 */ :>> flight = "STS-90"; :>> launchDate = ""; :>> block = "OMS"; :>> kind = "運用・手順"; :>> changedPart = "OMS assist maneuver during second stage of ascent"; }
    part <'CFG-120'> cfg_120 : ConfigChange { doc /* STS-91 */ :>> flight = "STS-91"; :>> launchDate = ""; :>> block = "PLS"; :>> kind = "新型ハードウェア"; :>> changedPart = "ISS Androgynous Peripheral Attachment System (APAS) docking mechanism"; }
    part <'CFG-121'> cfg_121 : ConfigChange { doc /* STS-91 */ :>> flight = "STS-91"; :>> launchDate = ""; :>> block = "ET"; :>> kind = "改修"; :>> changedPart = "super lightweight tank (SLWT) ET-96"; }
    part <'CFG-122'> cfg_122 : ConfigChange { doc /* STS-91 */ :>> flight = "STS-91"; :>> launchDate = ""; :>> block = "MPS"; :>> kind = "新型ハードウェア"; :>> changedPart = "transducer (MPS, cryogenic compensating)"; }
    part <'CFG-123'> cfg_123 : ConfigChange { doc /* STS-91 */ :>> flight = "STS-91"; :>> launchDate = ""; :>> block = "EPS"; :>> kind = "新型ハードウェア"; :>> changedPart = "fuel cell monitoring system (FCMS) on OV-103"; }
    part <'CFG-124'> cfg_124 : ConfigChange { doc /* STS-91 */ :>> flight = "STS-91"; :>> launchDate = ""; :>> block = "DPS"; :>> kind = "ソフトウェア"; :>> changedPart = "OI-26B flight software"; }
    part <'CFG-125'> cfg_125 : ConfigChange { doc /* STS-91 */ :>> flight = "STS-91"; :>> launchDate = ""; :>> block = "GNC"; :>> kind = "新型ハードウェア"; :>> changedPart = "single-string Global Positioning System (GPS) capability"; }
    part <'CFG-126'> cfg_126 : ConfigChange { doc /* STS-91 */ :>> flight = "STS-91"; :>> launchDate = ""; :>> block = "TPS"; :>> kind = "新型ハードウェア"; :>> changedPart = "upper body tiles in the plume impingement area"; }
    part <'CFG-127'> cfg_127 : ConfigChange { doc /* STS-91 */ :>> flight = "STS-91"; :>> launchDate = ""; :>> block = "CT"; :>> kind = "新型ハードウェア"; :>> changedPart = "umbilical well cameras (OV-103)"; }
    part <'CFG-128'> cfg_128 : ConfigChange { doc /* STS-94 */ :>> flight = "STS-94"; :>> launchDate = ""; :>> block = "MPS"; :>> kind = "新型ハードウェア"; :>> changedPart = "SSME continuous fuel system purge"; }
    part <'CFG-129'> cfg_129 : ConfigChange { doc /* STS-94 */ :>> flight = "STS-94"; :>> launchDate = ""; :>> block = "MPS"; :>> kind = "新型ハードウェア"; :>> changedPart = "NCFI 24-124 thermal protection system material on LO2 tank barrel and ogive"; }
    part <'CFG-130'> cfg_130 : ConfigChange { doc /* STS-95 */ :>> flight = "STS-95"; :>> launchDate = "1998-10-29"; :>> block = "SRB"; :>> kind = "新型ハードウェア"; :>> changedPart = "aft skirt doubler brackets"; }
    part <'CFG-131'> cfg_131 : ConfigChange { doc /* STS-95 */ :>> flight = "STS-95"; :>> launchDate = "1998-10-29"; :>> block = "ECLSS"; :>> kind = "新型ハードウェア"; :>> changedPart = "sea water activated release (SWAR) links on all main parachutes"; }
    part <'CFG-132'> cfg_132 : ConfigChange { doc /* STS-95 */ :>> flight = "STS-95"; :>> launchDate = "1998-10-29"; :>> block = "DPS"; :>> kind = "新型ハードウェア"; :>> changedPart = "Integrated Vehicle Health Monitoring (IVHM) system"; }
    part <'CFG-133'> cfg_133 : ConfigChange { doc /* STS-95 */ :>> flight = "STS-95"; :>> launchDate = "1998-10-29"; :>> block = "PLS"; :>> kind = "新型ハードウェア"; :>> changedPart = "Orbiter Space Vision System (OSVS) with RMS operations"; }
    part <'CFG-134'> cfg_134 : ConfigChange { doc /* STS-95 */ :>> flight = "STS-95"; :>> launchDate = "1998-10-29"; :>> block = "DPS"; :>> kind = "ソフトウェア"; :>> changedPart = "GPS receiver firmware and PGSC software simulating SIGI"; }
    part <'CFG-135'> cfg_135 : ConfigChange { doc /* STS-96 */ :>> flight = "STS-96"; :>> launchDate = "1999-05-27"; :>> block = "RCS"; :>> kind = "新型ハードウェア"; :>> changedPart = "forward RCS vernier thruster 18-watt heaters"; }
    part <'CFG-136'> cfg_136 : ConfigChange { doc /* STS-96 */ :>> flight = "STS-96"; :>> launchDate = "1999-05-27"; :>> block = "MPS"; :>> kind = "改修"; :>> changedPart = "modified hazardous gas detection system (HGDS)"; }
    part <'CFG-137'> cfg_137 : ConfigChange { doc /* STS-96 */ :>> flight = "STS-96"; :>> launchDate = "1999-05-27"; :>> block = "PLS"; :>> kind = "新型ハードウェア"; :>> changedPart = "docking (rather than berthing) with the ISS"; }
    part <'CFG-138'> cfg_138 : ConfigChange { doc /* STS-97 */ :>> flight = "STS-97"; :>> launchDate = "2000-11-30"; :>> block = "CREW"; :>> kind = "新型ハードウェア"; :>> changedPart = "Shuttle Urine Pretreat Assembly (SUPA)"; }
    part <'CFG-139'> cfg_139 : ConfigChange { doc /* STS-97 */ :>> flight = "STS-97"; :>> launchDate = "2000-11-30"; :>> block = "ECLSS"; :>> kind = "新型ハードウェア"; :>> changedPart = "Orbiter Condensate Separation hardware (adapter hose assembly and Water Dispense"; }
    part <'CFG-140'> cfg_140 : ConfigChange { doc /* STS-98 */ :>> flight = "STS-98"; :>> launchDate = "2001-02-07"; :>> block = "DPS"; :>> kind = "ソフトウェア"; :>> changedPart = "OI-28 software (automated firing of forward primary RCS up-firing thrusters)"; }
    part <'CFG-141'> cfg_141 : ConfigChange { doc /* STS-98 */ :>> flight = "STS-98"; :>> launchDate = "2001-02-07"; :>> block = "DPS"; :>> kind = "ソフトウェア"; :>> changedPart = "automated reboost software"; }
    part <'CFG-142'> cfg_142 : ConfigChange { doc /* STS-98 */ :>> flight = "STS-98"; :>> launchDate = "2001-02-07"; :>> block = "RCS"; :>> kind = "新型ハードウェア"; :>> changedPart = "RCS-to-RCS crossfeed using the master crossfeed switch"; }
    part <'CFG-143'> cfg_143 : ConfigChange { doc /* STS-98 */ :>> flight = "STS-98"; :>> launchDate = "2001-02-07"; :>> block = "RCS"; :>> kind = "新型ハードウェア"; :>> changedPart = "forward up-firing RCS thruster plumes to prevent BSM particulate impingement on "; }
    part <'CFG-144'> cfg_144 : ConfigChange { doc /* STS-98 */ :>> flight = "STS-98"; :>> launchDate = "2001-02-07"; :>> block = "ECLSS"; :>> kind = "改修"; :>> changedPart = "redesigned gas sample bottles (four of six)"; }
    part <'CFG-145'> cfg_145 : ConfigChange { doc /* STS-99 */ :>> flight = "STS-99"; :>> launchDate = "2000-02-11"; :>> block = "OMS"; :>> kind = "新型ハードウェア"; :>> changedPart = "OMS engine S/N 105 refurbished by WSTF"; }
    part <'CFG-146'> cfg_146 : ConfigChange { doc /* STS-100 */ :>> flight = "STS-100"; :>> launchDate = "2001-04-19"; :>> block = "CT"; :>> kind = "新型ハードウェア"; :>> changedPart = "Space-to-Space Orbiter Radio (SSOR) and SSSR during undocking/separation"; }
    part <'CFG-147'> cfg_147 : ConfigChange { doc /* STS-100 */ :>> flight = "STS-100"; :>> launchDate = "2001-04-19"; :>> block = "SRB"; :>> kind = "新型ハードウェア"; :>> changedPart = "C-Band Controller system (SRB)"; }
    part <'CFG-148'> cfg_148 : ConfigChange { doc /* STS-100 */ :>> flight = "STS-100"; :>> launchDate = "2001-04-19"; :>> block = "EPS"; :>> kind = "新型ハードウェア"; :>> changedPart = "fuel cells with drip-fill process cells"; }
    part <'CFG-149'> cfg_149 : ConfigChange { doc /* STS-101 */ :>> flight = "STS-101"; :>> launchDate = "2000-05-19"; :>> block = "OMS"; :>> kind = "新型ハードウェア"; :>> changedPart = "left OMS engine (rebuilt at WSTF)"; }
    part <'CFG-150'> cfg_150 : ConfigChange { doc /* STS-101 */ :>> flight = "STS-101"; :>> launchDate = "2000-05-19"; :>> block = "APU"; :>> kind = "新型ハードウェア"; :>> changedPart = "bellows accumulators (hydraulic)"; }
    part <'CFG-151'> cfg_151 : ConfigChange { doc /* STS-101 */ :>> flight = "STS-101"; :>> launchDate = "2000-05-19"; :>> block = "APU"; :>> kind = "新型ハードウェア"; :>> changedPart = "Propylene Glycol Monomethyl Ether (PGME) water spray boiler additive"; }
    part <'CFG-152'> cfg_152 : ConfigChange { doc /* STS-101 */ :>> flight = "STS-101"; :>> launchDate = "2000-05-19"; :>> block = "DPS"; :>> kind = "新型ハードウェア"; :>> changedPart = "Multifunction Electronic Display System (MEDS)"; }
    part <'CFG-153'> cfg_153 : ConfigChange { doc /* STS-101 */ :>> flight = "STS-101"; :>> launchDate = "2000-05-19"; :>> block = "GNC"; :>> kind = "新型ハードウェア"; :>> changedPart = "-Y solid-state star tracker"; }
    part <'CFG-154'> cfg_154 : ConfigChange { doc /* STS-101 */ :>> flight = "STS-101"; :>> launchDate = "2000-05-19"; :>> block = "APU"; :>> kind = "新型ハードウェア"; :>> changedPart = "hydraulic circulation pump temperature control limits (all three systems reduced"; }
    part <'CFG-155'> cfg_155 : ConfigChange { doc /* STS-102 */ :>> flight = "STS-102"; :>> launchDate = "2001-03-08"; :>> block = "APU"; :>> kind = "新型ハードウェア"; :>> changedPart = "water spray boiler additive (PGME) in all three WSB cores"; }
    part <'CFG-156'> cfg_156 : ConfigChange { doc /* STS-102 */ :>> flight = "STS-102"; :>> launchDate = "2001-03-08"; :>> block = "RCS"; :>> kind = "新型ハードウェア"; :>> changedPart = "vernier/vernier automatic ISS reboost"; }
    part <'CFG-157'> cfg_157 : ConfigChange { doc /* STS-102 */ :>> flight = "STS-102"; :>> launchDate = "2001-03-08"; :>> block = "ECLSS"; :>> kind = "新型ハードウェア"; :>> changedPart = "Orbiter Condensate Separation hardware (adapter hose assembly and water dispense"; }
    part <'CFG-158'> cfg_158 : ConfigChange { doc /* STS-104 */ :>> flight = "STS-104"; :>> launchDate = "2001-07-12"; :>> block = "MPS"; :>> kind = "新型ハードウェア"; :>> changedPart = "Block II SSME"; }
    part <'CFG-159'> cfg_159 : ConfigChange { doc /* STS-104 */ :>> flight = "STS-104"; :>> launchDate = "2001-07-12"; :>> block = "CT"; :>> kind = "新型ハードウェア"; :>> changedPart = "Space-to-Space Communication System (SSCS)"; }
    part <'CFG-160'> cfg_160 : ConfigChange { doc /* STS-105 */ :>> flight = "STS-105"; :>> launchDate = "2001-08-10"; :>> block = "OMS"; :>> kind = "新型ハードウェア"; :>> changedPart = "single-mission fuel isolation valve (SMFIV)"; }
    part <'CFG-161'> cfg_161 : ConfigChange { doc /* STS-106 */ :>> flight = "STS-106"; :>> launchDate = "2000-09-08"; :>> block = "ECLSS"; :>> kind = "新型ハードウェア"; :>> changedPart = "oxygen sensor relocated from the quick-disconnect panel"; }
    part <'CFG-162'> cfg_162 : ConfigChange { doc /* STS-107 */ :>> flight = "STS-107"; :>> launchDate = "2003-01-16"; :>> block = "PLS"; :>> kind = "新型ハードウェア"; :>> changedPart = "Spacehab Research Double Module (RDM)"; }
    part <'CFG-163'> cfg_163 : ConfigChange { doc /* STS-108 */ :>> flight = "STS-108"; :>> launchDate = "2001-12-05"; :>> block = "SRB"; :>> kind = "新型ハードウェア"; :>> changedPart = "dumping of payload water reservoirs (PWRs) through the wastewater dump nozzle"; }
    part <'CFG-164'> cfg_164 : ConfigChange { doc /* STS-109 */ :>> flight = "STS-109"; :>> launchDate = "2002-03-01"; :>> block = "CREW"; :>> kind = "新型ハードウェア"; :>> changedPart = "sternal harness with the disposable electrodes"; }
    part <'CFG-165'> cfg_165 : ConfigChange { doc /* STS-109 */ :>> flight = "STS-109"; :>> launchDate = "2002-03-01"; :>> block = "MPS"; :>> kind = "新型ハードウェア"; :>> changedPart = "hazardous gas detection system (HGDS) Haz Gas 2000"; }
    part <'CFG-166'> cfg_166 : ConfigChange { doc /* STS-109 */ :>> flight = "STS-109"; :>> launchDate = "2002-03-01"; :>> block = "APU"; :>> kind = "新型ハードウェア"; :>> changedPart = "water additive PGME in all three water spray boilers (OV-102)"; }
    part <'CFG-167'> cfg_167 : ConfigChange { doc /* STS-110 */ :>> flight = "STS-110"; :>> launchDate = "2002-04-08"; :>> block = "PLS"; :>> kind = "運用・手順"; :>> changedPart = "modified docking ring retraction procedure"; }
    part <'CFG-168'> cfg_168 : ConfigChange { doc /* STS-110 */ :>> flight = "STS-110"; :>> launchDate = "2002-04-08"; :>> block = "CT"; :>> kind = "新型ハードウェア"; :>> changedPart = "digital television (DTV) system"; }
    part <'CFG-169'> cfg_169 : ConfigChange { doc /* STS-110 */ :>> flight = "STS-110"; :>> launchDate = "2002-04-08"; :>> block = "PLS"; :>> kind = "新型ハードウェア"; :>> changedPart = "all four EVAs originating from the ISS airlock"; }
    part <'CFG-170'> cfg_170 : ConfigChange { doc /* STS-110 */ :>> flight = "STS-110"; :>> launchDate = "2002-04-08"; :>> block = "MPS"; :>> kind = "新型ハードウェア"; :>> changedPart = "full cluster of three Block II SSMEs"; }
    part <'CFG-171'> cfg_171 : ConfigChange { doc /* STS-110 */ :>> flight = "STS-110"; :>> launchDate = "2002-04-08"; :>> block = "APU"; :>> kind = "新型ハードウェア"; :>> changedPart = "water additive (PGME) in all three WSBs on OV-104"; }
    part <'CFG-172'> cfg_172 : ConfigChange { doc /* STS-110 */ :>> flight = "STS-110"; :>> launchDate = "2002-04-08"; :>> block = "DPS"; :>> kind = "ソフトウェア"; :>> changedPart = "OI-29 software (lower circulation pump thermal limits)"; }
    part <'CFG-173'> cfg_173 : ConfigChange { doc /* STS-110 */ :>> flight = "STS-110"; :>> launchDate = "2002-04-08"; :>> block = "PLS"; :>> kind = "新型ハードウェア"; :>> changedPart = "oxygen transfer from the Orbiter to the ISS"; }
    part <'CFG-174'> cfg_174 : ConfigChange { doc /* STS-112 */ :>> flight = "STS-112"; :>> launchDate = "2002-10-07"; :>> block = "CT"; :>> kind = "新型ハードウェア"; :>> changedPart = "Shuttle Observation Camera System"; }
    part <'CFG-175'> cfg_175 : ConfigChange { doc /* STS-112 */ :>> flight = "STS-112"; :>> launchDate = "2002-10-07"; :>> block = "ECLSS"; :>> kind = "新型ハードウェア"; :>> changedPart = "cabin CO2 control by ISS CDRA and Vozdukh hardware"; }
    part <'CFG-176'> cfg_176 : ConfigChange { doc /* STS-112 */ :>> flight = "STS-112"; :>> launchDate = "2002-10-07"; :>> block = "PLS"; :>> kind = "新型ハードウェア"; :>> changedPart = "docking with the RMS out of the cradle position"; }
    part <'CFG-177'> cfg_177 : ConfigChange { doc /* STS-113 */ :>> flight = "STS-113"; :>> launchDate = "2002-11-23"; :>> block = "PLS"; :>> kind = "新型ハードウェア"; :>> changedPart = "RMS S/N 201 arm (refurbished)"; }
    part <'CFG-178'> cfg_178 : ConfigChange { doc /* STS-114 */ :>> flight = "STS-114"; :>> launchDate = "2005-07-26"; :>> block = "PLS"; :>> kind = "新型ハードウェア"; :>> changedPart = "Orbiter Boom Sensor System (OBSS)"; }
    part <'CFG-179'> cfg_179 : ConfigChange { doc /* STS-114 */ :>> flight = "STS-114"; :>> launchDate = "2005-07-26"; :>> block = "PLS"; :>> kind = "新型ハードウェア"; :>> changedPart = "pan tilt unit (PTU) of the OBSS"; }
    part <'CFG-180'> cfg_180 : ConfigChange { doc /* STS-114 */ :>> flight = "STS-114"; :>> launchDate = "2005-07-26"; :>> block = "SRB"; :>> kind = "改修"; :>> changedPart = "SRB/ET forward attachment bolt catcher"; }
    part <'CFG-181'> cfg_181 : ConfigChange { doc /* STS-114 */ :>> flight = "STS-114"; :>> launchDate = "2005-07-26"; :>> block = "SRB"; :>> kind = "改修"; :>> changedPart = "NASA Standard Initiator (NSI) pressure cartridge retention device"; }
    part <'CFG-182'> cfg_182 : ConfigChange { doc /* STS-114 */ :>> flight = "STS-114"; :>> launchDate = "2005-07-26"; :>> block = "SRB"; :>> kind = "改修"; :>> changedPart = "booster separation motor (BSM) igniter"; }
    part <'CFG-183'> cfg_183 : ConfigChange { doc /* STS-114 */ :>> flight = "STS-114"; :>> launchDate = "2005-07-26"; :>> block = "ECLSS"; :>> kind = "新型ハードウェア"; :>> changedPart = "new system for analyzing the gas sample bottle contents"; }
    part <'CFG-184'> cfg_184 : ConfigChange { doc /* STS-115 */ :>> flight = "STS-115"; :>> launchDate = "2006-09-09"; :>> block = "PLS"; :>> kind = "新型ハードウェア"; :>> changedPart = "ISS Airlock Campout Protocol for EVA prebreathe"; }
    part <'CFG-185'> cfg_185 : ConfigChange { doc /* STS-115 */ :>> flight = "STS-115"; :>> launchDate = "2006-09-09"; :>> block = "ET"; :>> kind = "改修"; :>> changedPart = "External Tank Attach ring material (4340 steel)"; }
    part <'CFG-186'> cfg_186 : ConfigChange { doc /* STS-115 */ :>> flight = "STS-115"; :>> launchDate = "2006-09-09"; :>> block = "TPS"; :>> kind = "改修"; :>> changedPart = "Aft Skirt BSM Triple Mount TPS modification"; }
    part <'CFG-187'> cfg_187 : ConfigChange { doc /* STS-115 */ :>> flight = "STS-115"; :>> launchDate = "2006-09-09"; :>> block = "SRB"; :>> kind = "改修"; :>> changedPart = "new adhesive (TIGA 321) for entire nozzle"; }
    part <'CFG-188'> cfg_188 : ConfigChange { doc /* STS-115 */ :>> flight = "STS-115"; :>> launchDate = "2006-09-09"; :>> block = "SRB"; :>> kind = "改修"; :>> changedPart = "RSRM instrumentation change (igniter joints, field joints, nozzle-to-case joints"; }
    part <'CFG-189'> cfg_189 : ConfigChange { doc /* STS-115 */ :>> flight = "STS-115"; :>> launchDate = "2006-09-09"; :>> block = "MPS"; :>> kind = "新型ハードウェア"; :>> changedPart = "HPFTP single-piece speed sensors"; }
    part <'CFG-190'> cfg_190 : ConfigChange { doc /* STS-115 */ :>> flight = "STS-115"; :>> launchDate = "2006-09-09"; :>> block = "MPS"; :>> kind = "改修"; :>> changedPart = "fastener modification to small line clamping (SSME)"; }
    part <'CFG-191'> cfg_191 : ConfigChange { doc /* STS-115 */ :>> flight = "STS-115"; :>> launchDate = "2006-09-09"; :>> block = "APU"; :>> kind = "新型ハードウェア"; :>> changedPart = "Propylene Glycol Monomethyl Ether (PGME) water additive in WSB"; }
    part <'CFG-192'> cfg_192 : ConfigChange { doc /* STS-115 */ :>> flight = "STS-115"; :>> launchDate = "2006-09-09"; :>> block = "GNC"; :>> kind = "新型ハードウェア"; :>> changedPart = "GPS firmware Link 007"; }
    part <'CFG-193'> cfg_193 : ConfigChange { doc /* STS-116 */ :>> flight = "STS-116"; :>> launchDate = "2006-12-09"; :>> block = "PLS"; :>> kind = "新型ハードウェア"; :>> changedPart = "docking and handing over the payload to the ISS on the docking day"; }
    part <'CFG-194'> cfg_194 : ConfigChange { doc /* STS-116 */ :>> flight = "STS-116"; :>> launchDate = "2006-12-09"; :>> block = "PLS"; :>> kind = "新型ハードウェア"; :>> changedPart = "ISS airlock for four EVAs and campout"; }
    part <'CFG-195'> cfg_195 : ConfigChange { doc /* STS-116 */ :>> flight = "STS-116"; :>> launchDate = "2006-12-09"; :>> block = "DPS"; :>> kind = "運用・手順"; :>> changedPart = "Advanced Health Monitoring System (AHMS) Controller, monitor mode only"; }
    part <'CFG-196'> cfg_196 : ConfigChange { doc /* STS-116 */ :>> flight = "STS-116"; :>> launchDate = "2006-12-09"; :>> block = "MPS"; :>> kind = "改修"; :>> changedPart = "Non-Integral Spark Igniter System (NISIS)"; }
    part <'CFG-197'> cfg_197 : ConfigChange { doc /* STS-116 */ :>> flight = "STS-116"; :>> launchDate = "2006-12-09"; :>> block = "MPS"; :>> kind = "改修"; :>> changedPart = "Low Pressure Fuel Duct (LPFD) Kevlar Insulation System"; }
    part <'CFG-198'> cfg_198 : ConfigChange { doc /* STS-116 */ :>> flight = "STS-116"; :>> launchDate = "2006-12-09"; :>> block = "MPS"; :>> kind = "改修"; :>> changedPart = "seal modification (LH2 T-0 carrier cavity)"; }
    part <'CFG-199'> cfg_199 : ConfigChange { doc /* STS-116 */ :>> flight = "STS-116"; :>> launchDate = "2006-12-09"; :>> block = "RCS"; :>> kind = "改修"; :>> changedPart = "redesigned Forward Reaction Control system (FRCS) Tyvek weather covers"; }
    part <'CFG-200'> cfg_200 : ConfigChange { doc /* STS-116 */ :>> flight = "STS-116"; :>> launchDate = "2006-12-09"; :>> block = "APU"; :>> kind = "新型ハードウェア"; :>> changedPart = "APU 3 gas generator with double-wall spring clip"; }
    part <'CFG-201'> cfg_201 : ConfigChange { doc /* STS-116 */ :>> flight = "STS-116"; :>> launchDate = "2006-12-09"; :>> block = "APU"; :>> kind = "新型ハードウェア"; :>> changedPart = "PGME water additive in all WSB system water tanks"; }
    part <'CFG-202'> cfg_202 : ConfigChange { doc /* STS-117 */ :>> flight = "STS-117"; :>> launchDate = "2007-06-08"; :>> block = "MPS"; :>> kind = "改修"; :>> changedPart = "redesigned Low Pressure Fuel Turbopump (LPFTP) duct no. 8 flow-meter (SSME 2059)"; }
    part <'CFG-203'> cfg_203 : ConfigChange { doc /* STS-117 */ :>> flight = "STS-117"; :>> launchDate = "2007-06-08"; :>> block = "DPS"; :>> kind = "新型ハードウェア"; :>> changedPart = "Advanced Health Management System (AHMS) controllers"; }
    part <'CFG-204'> cfg_204 : ConfigChange { doc /* STS-117 */ :>> flight = "STS-117"; :>> launchDate = "2007-06-08"; :>> block = "MPS"; :>> kind = "新型ハードウェア"; :>> changedPart = "SSME 2059"; }
    part <'CFG-205'> cfg_205 : ConfigChange { doc /* STS-117 */ :>> flight = "STS-117"; :>> launchDate = "2007-06-08"; :>> block = "MPS"; :>> kind = "新型ハードウェア"; :>> changedPart = "Engine Cut-off (ECO) Sensor System Instrumentation for measuring SSME voltage"; }
    part <'CFG-206'> cfg_206 : ConfigChange { doc /* STS-117 */ :>> flight = "STS-117"; :>> launchDate = "2007-06-08"; :>> block = "MPS"; :>> kind = "改修"; :>> changedPart = "ET LO2 feedline camera system electronics package (new)"; }
    part <'CFG-207'> cfg_207 : ConfigChange { doc /* STS-117 */ :>> flight = "STS-117"; :>> launchDate = "2007-06-08"; :>> block = "MPS"; :>> kind = "改修"; :>> changedPart = "BX-265 on LH2 tank cover plate (internal to Intertank)"; }
    part <'CFG-208'> cfg_208 : ConfigChange { doc /* STS-117 */ :>> flight = "STS-117"; :>> launchDate = "2007-06-08"; :>> block = "TPS"; :>> kind = "改修"; :>> changedPart = "Low Pressure Oxidizer Turbo Pump (LPOTP) Inducer, Leading Edge Cutback Design"; }
    part <'CFG-209'> cfg_209 : ConfigChange { doc /* STS-118 */ :>> flight = "STS-118"; :>> launchDate = "2007-08-08"; :>> block = "GNC"; :>> kind = "新型ハードウェア"; :>> changedPart = "flight without the three TACANs (replaced by GPS)"; }
    part <'CFG-210'> cfg_210 : ConfigChange { doc /* STS-118 */ :>> flight = "STS-118"; :>> launchDate = "2007-08-08"; :>> block = "DPS"; :>> kind = "改修"; :>> changedPart = "Day-of-Launch I-Load Update system on the LINUX platform"; }
    part <'CFG-211'> cfg_211 : ConfigChange { doc /* STS-118 */ :>> flight = "STS-118"; :>> launchDate = "2007-08-08"; :>> block = "SRB"; :>> kind = "新型ハードウェア"; :>> changedPart = "SRB Command Receiver Decoder (CRD)"; }
    part <'CFG-212'> cfg_212 : ConfigChange { doc /* STS-118 */ :>> flight = "STS-118"; :>> launchDate = "2007-08-08"; :>> block = "MPS"; :>> kind = "運用・手順"; :>> changedPart = "Advanced Health Monitoring System (AHMS) SSME controller in redline active mode"; }
    part <'CFG-213'> cfg_213 : ConfigChange { doc /* STS-118 */ :>> flight = "STS-118"; :>> launchDate = "2007-08-08"; :>> block = "MPS"; :>> kind = "改修"; :>> changedPart = "ECO Point Sensor system measurements (design change)"; }
    part <'CFG-214'> cfg_214 : ConfigChange { doc /* STS-118 */ :>> flight = "STS-118"; :>> launchDate = "2007-08-08"; :>> block = "EPS"; :>> kind = "新型ハードウェア"; :>> changedPart = "Station-to-Shuttle Power Transfer System (SSPTS)"; }
    part <'CFG-215'> cfg_215 : ConfigChange { doc /* STS-118 */ :>> flight = "STS-118"; :>> launchDate = "2007-08-08"; :>> block = "GNC"; :>> kind = "新型ハードウェア"; :>> changedPart = "3-string GPS navigation"; }
    part <'CFG-216'> cfg_216 : ConfigChange { doc /* STS-118 */ :>> flight = "STS-118"; :>> launchDate = "2007-08-08"; :>> block = "MECH"; :>> kind = "改修"; :>> changedPart = "new improved main landing gear tires (OV-105)"; }
    part <'CFG-217'> cfg_217 : ConfigChange { doc /* STS-120 */ :>> flight = "STS-120"; :>> launchDate = "2007-10-23"; :>> block = "MPS"; :>> kind = "改修"; :>> changedPart = "SSME High Pressure Oxidizer Turbopump (HPOTP) with redesigned knife-edge seals"; }
    part <'CFG-218'> cfg_218 : ConfigChange { doc /* STS-120 */ :>> flight = "STS-120"; :>> launchDate = "2007-10-23"; :>> block = "MPS"; :>> kind = "新型ハードウェア"; :>> changedPart = "Low Pressure Oxidizer Turbopump (LPOTP) Joint 05 corrosion inhibitor"; }
    part <'CFG-219'> cfg_219 : ConfigChange { doc /* STS-120 */ :>> flight = "STS-120"; :>> launchDate = "2007-10-23"; :>> block = "DPS"; :>> kind = "ソフトウェア"; :>> changedPart = "OI-32 flight software"; }
    part <'CFG-220'> cfg_220 : ConfigChange { doc /* STS-120 */ :>> flight = "STS-120"; :>> launchDate = "2007-10-23"; :>> block = "DPS"; :>> kind = "新型ハードウェア"; :>> changedPart = "A31P Payload and General Support Computers (PGSCs)"; }
    part <'CFG-221'> cfg_221 : ConfigChange { doc /* STS-120 */ :>> flight = "STS-120"; :>> launchDate = "2007-10-23"; :>> block = "EPS"; :>> kind = "新型ハードウェア"; :>> changedPart = "Station-to-Shuttle Power Transfer System (SSPTS) on OV-103"; }
    part <'CFG-222'> cfg_222 : ConfigChange { doc /* STS-120 */ :>> flight = "STS-120"; :>> launchDate = "2007-10-23"; :>> block = "TPS"; :>> kind = "運用・手順"; :>> changedPart = "T-RAD/STA-54 tile repair material (DTO-848)"; }
    part <'CFG-223'> cfg_223 : ConfigChange { doc /* STS-120 */ :>> flight = "STS-120"; :>> launchDate = "2007-10-23"; :>> block = "PLS"; :>> kind = "新型ハードウェア"; :>> changedPart = "Orbiter Boom Sensor System (OBSS) with EVA on the SSRMS"; }
    part <'CFG-224'> cfg_224 : ConfigChange { doc /* STS-120 */ :>> flight = "STS-120"; :>> launchDate = "2007-10-23"; :>> block = "ECLSS"; :>> kind = "改修"; :>> changedPart = "Air Data Transducer Assemblies (ADTA) retrofitted with newly built power supply "; }
    part <'CFG-225'> cfg_225 : ConfigChange { doc /* STS-121 */ :>> flight = "STS-121"; :>> launchDate = "2006-07-04"; :>> block = "CT"; :>> kind = "改修"; :>> changedPart = "vehicle modification to downlink low-rate Modular Auxiliary Data System (MADS) d"; }
    part <'CFG-226'> cfg_226 : ConfigChange { doc /* STS-121 */ :>> flight = "STS-121"; :>> launchDate = "2006-07-04"; :>> block = "PLS"; :>> kind = "新型ハードウェア"; :>> changedPart = "Recharge Oxygen Orifice Bypass Assembly (ROOBA)"; }
    part <'CFG-227'> cfg_227 : ConfigChange { doc /* STS-121 */ :>> flight = "STS-121"; :>> launchDate = "2006-07-04"; :>> block = "CT"; :>> kind = "新型ハードウェア"; :>> changedPart = "Integrated Sensor Inspection System (ISIS) Digital Camera (IDC)"; }
    part <'CFG-228'> cfg_228 : ConfigChange { doc /* STS-121 */ :>> flight = "STS-121"; :>> launchDate = "2006-07-04"; :>> block = "SRB"; :>> kind = "改修"; :>> changedPart = "Nozzle Structural Adhesive System (SRB, left-hand forward nozzle assembly)"; }
    part <'CFG-229'> cfg_229 : ConfigChange { doc /* STS-121 */ :>> flight = "STS-121"; :>> launchDate = "2006-07-04"; :>> block = "SRB"; :>> kind = "改修"; :>> changedPart = "SRB Camera System (SCS), forward skirt aft-looking camera"; }
    part <'CFG-230'> cfg_230 : ConfigChange { doc /* STS-121 */ :>> flight = "STS-121"; :>> launchDate = "2006-07-04"; :>> block = "SRB"; :>> kind = "改修"; :>> changedPart = "External Tank Attach (ETA) Ring Camera (SRB)"; }
    part <'CFG-231'> cfg_231 : ConfigChange { doc /* STS-121 */ :>> flight = "STS-121"; :>> launchDate = "2006-07-04"; :>> block = "ET"; :>> kind = "改修"; :>> changedPart = "redesign removing the Protuberance Air Load (PAL) ramps (ET cable trays)"; }
    part <'CFG-232'> cfg_232 : ConfigChange { doc /* STS-121 */ :>> flight = "STS-121"; :>> launchDate = "2006-07-04"; :>> block = "ET"; :>> kind = "改修"; :>> changedPart = "bipod heater zinc chromate paste application"; }
    part <'CFG-233'> cfg_233 : ConfigChange { doc /* STS-121 */ :>> flight = "STS-121"; :>> launchDate = "2006-07-04"; :>> block = "ET"; :>> kind = "改修"; :>> changedPart = "bipod wire cryogenic-ingestion mitigation"; }
    part <'CFG-234'> cfg_234 : ConfigChange { doc /* STS-121 */ :>> flight = "STS-121"; :>> launchDate = "2006-07-04"; :>> block = "ET"; :>> kind = "改修"; :>> changedPart = "bipod-to-tank fastener length"; }
    part <'CFG-235'> cfg_235 : ConfigChange { doc /* STS-121 */ :>> flight = "STS-121"; :>> launchDate = "2006-07-04"; :>> block = "ET"; :>> kind = "改修"; :>> changedPart = "bipod strut fastener hardware"; }
    part <'CFG-236'> cfg_236 : ConfigChange { doc /* STS-121 */ :>> flight = "STS-121"; :>> launchDate = "2006-07-04"; :>> block = "MPS"; :>> kind = "改修"; :>> changedPart = "nozzle ablative removal redesign (SSME)"; }
    part <'CFG-237'> cfg_237 : ConfigChange { doc /* STS-121 */ :>> flight = "STS-121"; :>> launchDate = "2006-07-04"; :>> block = "RCS"; :>> kind = "改修"; :>> changedPart = "redesigned Forward Reaction Control System (FRCS) Tyvek weather covers"; }
    part <'CFG-238'> cfg_238 : ConfigChange { doc /* STS-121 */ :>> flight = "STS-121"; :>> launchDate = "2006-07-04"; :>> block = "ET"; :>> kind = "新型ハードウェア"; :>> changedPart = "yellow paint striping on ET door perimeter corner tiles"; }
    part <'CFG-239'> cfg_239 : ConfigChange { doc /* STS-121 */ :>> flight = "STS-121"; :>> launchDate = "2006-07-04"; :>> block = "MECH"; :>> kind = "改修"; :>> changedPart = "improved Main Landing Gear (MLG) tires with higher launch pressure (425 psia vs."; }
    part <'CFG-240'> cfg_240 : ConfigChange { doc /* STS-121 */ :>> flight = "STS-121"; :>> launchDate = "2006-07-04"; :>> block = "TPS"; :>> kind = "新型ハードウェア"; :>> changedPart = "RCC inspection late in the flight for MMOD impacts (LDRI)"; }
    part <'CFG-241'> cfg_241 : ConfigChange { doc /* STS-122 */ :>> flight = "STS-122"; :>> launchDate = "2008-02-07"; :>> block = "PLS"; :>> kind = "新型ハードウェア"; :>> changedPart = "Shuttle docking to the Node 2/PMA 2 configuration"; }
    part <'CFG-242'> cfg_242 : ConfigChange { doc /* STS-122 */ :>> flight = "STS-122"; :>> launchDate = "2008-02-07"; :>> block = "PLS"; :>> kind = "改修"; :>> changedPart = "Integrated Cargo Carrier Lightweight (ICC-L)"; }
    part <'CFG-243'> cfg_243 : ConfigChange { doc /* STS-122 */ :>> flight = "STS-122"; :>> launchDate = "2008-02-07"; :>> block = "ECLSS"; :>> kind = "新型ハードウェア"; :>> changedPart = "N2/O2 Control Panel Mass Flow sensor design"; }
    part <'CFG-244'> cfg_244 : ConfigChange { doc /* STS-122 */ :>> flight = "STS-122"; :>> launchDate = "2008-02-07"; :>> block = "APU"; :>> kind = "改修"; :>> changedPart = "Gas Generator Valve Module (GGVM) heater modification on all three APUs"; }
    part <'CFG-245'> cfg_245 : ConfigChange { doc /* STS-122 */ :>> flight = "STS-122"; :>> launchDate = "2008-02-07"; :>> block = "MPS"; :>> kind = "改修"; :>> changedPart = "High Pressure Oxidizer Turbopumps with redesigned knife-edge seals (all three SS"; }
    part <'CFG-246'> cfg_246 : ConfigChange { doc /* STS-122 */ :>> flight = "STS-122"; :>> launchDate = "2008-02-07"; :>> block = "MPS"; :>> kind = "改修"; :>> changedPart = "Low Pressure Oxidizer Turbopump (LPOTP) oversized inserts with corrosion inhibit"; }
    part <'CFG-247'> cfg_247 : ConfigChange { doc /* STS-122 */ :>> flight = "STS-122"; :>> launchDate = "2008-02-07"; :>> block = "ECLSS"; :>> kind = "改修"; :>> changedPart = "redesigned Orbiter aft fuselage gas sampler bottles"; }
    part <'CFG-248'> cfg_248 : ConfigChange { doc /* STS-123 */ :>> flight = "STS-123"; :>> launchDate = "2008-03-11"; :>> block = "DPS"; :>> kind = "新型ハードウェア"; :>> changedPart = "new on-board Shuttle Ethernet Local Area Network (LAN) configuration"; }
    part <'CFG-249'> cfg_249 : ConfigChange { doc /* STS-123 */ :>> flight = "STS-123"; :>> launchDate = "2008-03-11"; :>> block = "ECLSS"; :>> kind = "新型ハードウェア"; :>> changedPart = "Extended Range Ammonia Detection Kit"; }
    part <'CFG-250'> cfg_250 : ConfigChange { doc /* STS-123 */ :>> flight = "STS-123"; :>> launchDate = "2008-03-11"; :>> block = "ET"; :>> kind = "新型ハードウェア"; :>> changedPart = "ET camera flash units in the left-hand ET/Orbiter umbilical"; }
    part <'CFG-251'> cfg_251 : ConfigChange { doc /* STS-124 */ :>> flight = "STS-124"; :>> launchDate = "2008-05-31"; :>> block = "MECH"; :>> kind = "新型ハードウェア"; :>> changedPart = "nose landing gear tire set"; }
    part <'CFG-252'> cfg_252 : ConfigChange { doc /* STS-124 */ :>> flight = "STS-124"; :>> launchDate = "2008-05-31"; :>> block = "APU"; :>> kind = "改修"; :>> changedPart = "APU Gas Generator Valve Module (GGVM) line heater modification on all three APUs"; }
    part <'CFG-253'> cfg_253 : ConfigChange { doc /* STS-125 */ :>> flight = "STS-125"; :>> launchDate = "2009-05-11"; :>> block = "SRB"; :>> kind = "新型ハードウェア"; :>> changedPart = "low-temperature material O-rings in the RSRM field joints"; }
    part <'CFG-254'> cfg_254 : ConfigChange { doc /* STS-125 */ :>> flight = "STS-125"; :>> launchDate = "2009-05-11"; :>> block = "MPS"; :>> kind = "運用・手順"; :>> changedPart = "in-flight pressure equalization of the NPRV cap (procedure)"; }
    part <'CFG-255'> cfg_255 : ConfigChange { doc /* STS-125 */ :>> flight = "STS-125"; :>> launchDate = "2009-05-11"; :>> block = "MECH"; :>> kind = "新型ハードウェア"; :>> changedPart = "nose landing gear tires"; }
    part <'CFG-256'> cfg_256 : ConfigChange { doc /* STS-125 */ :>> flight = "STS-125"; :>> launchDate = "2009-05-11"; :>> block = "TCS"; :>> kind = "新型ハードウェア"; :>> changedPart = "thermostat (lower FDA limit 43 to 40 F, sensor range increased)"; }
    part <'CFG-257'> cfg_257 : ConfigChange { doc /* STS-126 */ :>> flight = "STS-126"; :>> launchDate = "2008-11-14"; :>> block = "DPS"; :>> kind = "ソフトウェア"; :>> changedPart = "OI-33 software"; }
    part <'CFG-258'> cfg_258 : ConfigChange { doc /* STS-126 */ :>> flight = "STS-126"; :>> launchDate = "2008-11-14"; :>> block = "CT"; :>> kind = "新型ハードウェア"; :>> changedPart = "High Definition video system"; }
    part <'CFG-259'> cfg_259 : ConfigChange { doc /* STS-126 */ :>> flight = "STS-126"; :>> launchDate = "2008-11-14"; :>> block = "SRB"; :>> kind = "改修"; :>> changedPart = "SRB forward propellant segment grain geometry redesign (transition region)"; }
    part <'CFG-260'> cfg_260 : ConfigChange { doc /* STS-126 */ :>> flight = "STS-126"; :>> launchDate = "2008-11-14"; :>> block = "SRB"; :>> kind = "改修"; :>> changedPart = "Intelligent Pressure Transducer (IPT) on the SRB"; }
    part <'CFG-261'> cfg_261 : ConfigChange { doc /* STS-126 */ :>> flight = "STS-126"; :>> launchDate = "2008-11-14"; :>> block = "SRB"; :>> kind = "改修"; :>> changedPart = "ATK Booster Separation Motor (BSM)"; }
    part <'CFG-262'> cfg_262 : ConfigChange { doc /* STS-126 */ :>> flight = "STS-126"; :>> launchDate = "2008-11-14"; :>> block = "SRB"; :>> kind = "改修"; :>> changedPart = "Enhanced Data Acquisition System (EDAS) units on the SRB forward skirt"; }
    part <'CFG-263'> cfg_263 : ConfigChange { doc /* STS-126 */ :>> flight = "STS-126"; :>> launchDate = "2008-11-14"; :>> block = "SRB"; :>> kind = "改修"; :>> changedPart = "Frangible Nut Crossover System (FNCS) on the hold-down posts"; }
    part <'CFG-264'> cfg_264 : ConfigChange { doc /* STS-126 */ :>> flight = "STS-126"; :>> launchDate = "2008-11-14"; :>> block = "MPS"; :>> kind = "改修"; :>> changedPart = "ET TPS process changes (LO2 Ice Frost Ramp and Longeron Foam)"; }
    part <'CFG-265'> cfg_265 : ConfigChange { doc /* STS-126 */ :>> flight = "STS-126"; :>> launchDate = "2008-11-14"; :>> block = "MPS"; :>> kind = "改修"; :>> changedPart = "ET LO2 feedline camera"; }
    part <'CFG-266'> cfg_266 : ConfigChange { doc /* STS-126 */ :>> flight = "STS-126"; :>> launchDate = "2008-11-14"; :>> block = "MECH"; :>> kind = "新型ハードウェア"; :>> changedPart = "nose landing gear tires"; }
    part <'CFG-267'> cfg_267 : ConfigChange { doc /* STS-127 */ :>> flight = "STS-127"; :>> launchDate = "2009-07-15"; :>> block = "ECLSS"; :>> kind = "新型ハードウェア"; :>> changedPart = "Contingency Water Container Iodine (CWCI) bags"; }
    part <'CFG-268'> cfg_268 : ConfigChange { doc /* STS-127 */ :>> flight = "STS-127"; :>> launchDate = "2009-07-15"; :>> block = "MPS"; :>> kind = "改修"; :>> changedPart = "Norbar Ultrasonic Extensometer (SSME engine joint bolt stretch)"; }
    part <'CFG-269'> cfg_269 : ConfigChange { doc /* STS-127 */ :>> flight = "STS-127"; :>> launchDate = "2009-07-15"; :>> block = "MPS"; :>> kind = "改修"; :>> changedPart = "Kevlar Insulation System on rigid fuel bleed duct (engine 2060)"; }
    part <'CFG-270'> cfg_270 : ConfigChange { doc /* STS-127 */ :>> flight = "STS-127"; :>> launchDate = "2009-07-15"; :>> block = "CT"; :>> kind = "新型ハードウェア"; :>> changedPart = "-507 CTVC camera configuration"; }
    part <'CFG-271'> cfg_271 : ConfigChange { doc /* STS-128 */ :>> flight = "STS-128"; :>> launchDate = "2009-08-28"; :>> block = "PLS"; :>> kind = "新型ハードウェア"; :>> changedPart = "rendezvous and docking using PRCS"; }
    part <'CFG-272'> cfg_272 : ConfigChange { doc /* STS-128 */ :>> flight = "STS-128"; :>> launchDate = "2009-08-28"; :>> block = "DPS"; :>> kind = "ソフトウェア"; :>> changedPart = "Operational Increment (OI) -34 software"; }
    part <'CFG-273'> cfg_273 : ConfigChange { doc /* STS-128 */ :>> flight = "STS-128"; :>> launchDate = "2009-08-28"; :>> block = "APU"; :>> kind = "改修"; :>> changedPart = "APU 3 fuel tank GN2 fill quick disconnect heater modification"; }
    part <'CFG-274'> cfg_274 : ConfigChange { doc /* STS-128 */ :>> flight = "STS-128"; :>> launchDate = "2009-08-28"; :>> block = "MECH"; :>> kind = "新型ハードウェア"; :>> changedPart = "nose landing gear tires"; }
    part <'CFG-275'> cfg_275 : ConfigChange { doc /* STS-129 */ :>> flight = "STS-129"; :>> launchDate = "2009-11-16"; :>> block = "CT"; :>> kind = "新型ハードウェア"; :>> changedPart = "no-communication abort boundaries delivered for the in-plane time"; }
    part <'CFG-276'> cfg_276 : ConfigChange { doc /* STS-130 */ :>> flight = "STS-130"; :>> launchDate = "2010-02-08"; :>> block = "SRB"; :>> kind = "改修"; :>> changedPart = "low-temperature O-ring in RSRM Nozzle-Joint 1"; }
    part <'CFG-277'> cfg_277 : ConfigChange { doc /* STS-132 */ :>> flight = "STS-132"; :>> launchDate = "2010-05-14"; :>> block = "SRB"; :>> kind = "新型ハードウェア"; :>> changedPart = "nozzle Flow Recirculation Inhibitor (FRI)"; }
    part <'CFG-278'> cfg_278 : ConfigChange { doc /* STS-132 */ :>> flight = "STS-132"; :>> launchDate = "2010-05-14"; :>> block = "MECH"; :>> kind = "新型ハードウェア"; :>> changedPart = "nose landing gear tires"; }
    part <'CFG-279'> cfg_279 : ConfigChange { doc /* STS-133 */ :>> flight = "STS-133"; :>> launchDate = "2011-02-24"; :>> block = "APU"; :>> kind = "新型ハードウェア"; :>> changedPart = "Phase II Fuel Pump (APU)"; }
    part <'CFG-280'> cfg_280 : ConfigChange { doc /* STS-133 */ :>> flight = "STS-133"; :>> launchDate = "2011-02-24"; :>> block = "MECH"; :>> kind = "新型ハードウェア"; :>> changedPart = "nose landing gear tires"; }
    part <'CFG-281'> cfg_281 : ConfigChange { doc /* STS-134 */ :>> flight = "STS-134"; :>> launchDate = "2011-05-16"; :>> block = "EVA"; :>> kind = "新型ハードウェア"; :>> changedPart = "In-Suit Light Exercise (ISLE) pre-breathe protocol"; }
    part <'CFG-282'> cfg_282 : ConfigChange { doc /* STS-134 */ :>> flight = "STS-134"; :>> launchDate = "2011-05-16"; :>> block = "SRB"; :>> kind = "新型ハードウェア"; :>> changedPart = "RSRB Phase II fuel pumps (all four APU positions)"; }
    part <'CFG-283'> cfg_283 : ConfigChange { doc /* STS-134 */ :>> flight = "STS-134"; :>> launchDate = "2011-05-16"; :>> block = "SRB"; :>> kind = "改修"; :>> changedPart = "low-temperature O-ring material in RSRM nozzle joint 3"; }
    part <'CFG-284'> cfg_284 : ConfigChange { doc /* STS-134 */ :>> flight = "STS-134"; :>> launchDate = "2011-05-16"; :>> block = "MECH"; :>> kind = "新型ハードウェア"; :>> changedPart = "nose landing gear tires"; }
}
