// SysML v2 テキスト：設計の決定の記録定義書（決定・代替案・理由・時期。NASA SP-4221 の記述による）
// SSD-DCN-ORB-001 設計の決定の記録定義書（決定・代替案・理由・時期。NASA SP-4221 の記述による） の表から生成（lib/build_docs_cx.py・rev_cx/cxdata.py）。根拠の頁は SSD-DCN-ORB-001 にある。
package SSD_DCN_ORB_001 {
    doc /* SSD-DCN-ORB-001 設計の決定の記録定義書（決定・代替案・理由・時期。NASA SP-4221 の記述による）。設計の決定を part def DesignDecision の使用として持つ。決定・代替案・理由・時期・機能ブロックは文字列の属性で、パッケージへの矢印は張らない。要求への関係（導出・充足・検証）は張らず、トレースの外に置く。 */
    private import ScalarValues::*;
    part def DesignDecision {
        doc /* 設計の決定の記録。NASA SP-4221（歴史書）の本文による。代替案・理由は本文の語。機能ブロックは本書の判断（PLAN_CX） */
        attribute decision : String;
        attribute alternatives : String;
        attribute reason : String;
        attribute year : String;
        attribute block : String;
    }
    part <'DCN-001'> dcn_001 : DesignDecision { doc /* reentry mode (thermal protection) */ :>> decision = "a no-lift entry"; :>> alternatives = "a lifting entry"; :>> reason = "easier to do a no-lift entry than a lifting entry, from the standpoint of heat protection"; :>> year = "1969"; :>> block = "TPS"; }
    part <'DCN-002'> dcn_002 : DesignDecision { doc /* booster */ :>> decision = "ruled out expendable boosters for a reusable shuttle"; :>> alternatives = "expendable boosters"; :>> reason = "such boosters were found to exceed the Saturn V in size"; :>> year = "1969"; :>> block = "SRB"; }
    part <'DCN-003'> dcn_003 : DesignDecision { doc /* orbiter configuration (wing vs lifting body) */ :>> decision = "turned to winged orbiters resembling those of Faget"; :>> alternatives = "lifting-body orbiters"; :>> reason = "having found no advantage in its lifting-body orbiters"; :>> year = "1969"; :>> block = "STR"; }
    part <'DCN-004'> dcn_004 : DesignDecision { doc /* two-stage fully-reusable configuration */ :>> decision = "eliminated the Triamese configurations"; :>> alternatives = "The initial concept, the FR-1"; :>> reason = "It had proven difficult, however, to have one shape serve both as booster and orbiter"; :>> year = "1969"; :>> block = "ORB"; }
    part <'DCN-005'> dcn_005 : DesignDecision { doc /* two-stage fully-reusable configuration */ :>> decision = "the FR-3 configuration was the forer~mner"; :>> alternatives = "FR-5"; :>> reason = "the problem of center-of-gravity shift was not so severe as to call for the design innovations of this class of concepts"; :>> year = "1969"; :>> block = "ORB"; }
    part <'DCN-006'> dcn_006 : DesignDecision { doc /* main engine nozzle type */ :>> decision = "to use the bell type only"; :>> alternatives = "the aerospike"; :>> reason = "had no real experience with the aerospike, though they had plenty with the bell"; :>> year = "1969"; :>> block = "MPS"; }
    part <'DCN-007'> dcn_007 : DesignDecision { doc /* orbiter primary structure material */ :>> decision = "the merits of titanium encouraged its use during NASA’s design work of 1970 and 1971"; :>> alternatives = "aluminum"; :>> reason = "the advantages of titanium promised a complete orbiter, including thermal protection, that would weigh some fifteen percent less than a counterpart built of alu"; :>> year = "1970"; :>> block = "STR"; }
    part <'DCN-008'> dcn_008 : DesignDecision { doc /* orbiter propellant tankage (external tank) */ :>> decision = "place the orbiter’s liquid hydrogen within expendable tankage"; :>> alternatives = "their fullyreusable configurations"; :>> reason = "Liquid hydrogen is bulky, having only one-fourteenth the density of water"; :>> year = "1971"; :>> block = "ET"; }
    part <'DCN-009'> dcn_009 : DesignDecision { doc /* booster thermal protection */ :>> decision = "it would use its structure as a heat sink"; :>> alternatives = "tiles; exotic metals"; :>> reason = "the lower staging velocity virtually eliminated the need for thermal protection"; :>> year = "1971"; :>> block = "TPS"; }
    part <'DCN-010'> dcn_010 : DesignDecision { doc /* orbiter wing */ :>> decision = "Donlan favored the delta wing"; :>> alternatives = "the straight-wing orbiter"; :>> reason = "the straight-wing orbiter would experience unsteady flow and buffeting, making it harder to fly"; :>> year = "1971"; :>> block = "STR"; }
    part <'DCN-011'> dcn_011 : DesignDecision { doc /* orbiter structure and thermal protection */ :>> decision = "the orbiter indeed would take shape as an aircraft built largely of this metal"; :>> alternatives = "hot structures"; :>> reason = "hot structures now looked like an open invitation to a cost overrun, everyone knew how to build an aluminum airplane"; :>> year = "1972"; :>> block = "TPS"; }
    part <'DCN-012'> dcn_012 : DesignDecision { doc /* orbiter main engines */ :>> decision = "replaced them with three SSMEs"; :>> alternatives = "four J-2s engines"; :>> reason = "NASA now was free to build an honest orbiter, one that would be right the first time"; :>> year = "1972"; :>> block = "MPS"; }
    part <'DCN-013'> dcn_013 : DesignDecision { doc /* orbiter size (payload bay) */ :>> decision = "NASA would get the full-size version that it wanted"; :>> alternatives = "the smaller orbiter"; :>> reason = "contractor studies found no advantage in the smaller orbiter, no offset to its compromise of NASA’s ability to carry DoD payloads"; :>> year = "1972"; :>> block = "STR"; }
    part <'DCN-014'> dcn_014 : DesignDecision { doc /* booster propulsion (solid rocket motor) */ :>> decision = "choosing the solid motor"; :>> alternatives = "the pressure-fed option; the less costly pump-fed booster"; :>> reason = "the projected costs for the solids drew on Air Force experience and were both low and firm, estimates for either of the liquid-fueled options were dodgy and lik"; :>> year = "1972"; :>> block = "SRB"; }
    part <'DCN-015'> dcn_015 : DesignDecision { doc /* first-stage propulsion */ :>> decision = "rocket engines were preferable to airbreathers for first-stage propulsion"; :>> alternatives = "airbreathers"; :>> reason = "the economic advantage for the rocket engine was always about the same as the developmental cost of the airbreathing engine"; :>> year = ""; :>> block = "SRB"; }
    part <'DCN-016'> dcn_016 : DesignDecision { doc /* launch mode */ :>> decision = "vertical takeoff proved to offer an advantage over horizontal launch"; :>> alternatives = "horizontal launch"; :>> reason = "the cost of developing a rocket sled was not offset by lower weight and cost in the flight vehicle"; :>> year = ""; :>> block = "ORB"; }
    part <'DCN-017'> dcn_017 : DesignDecision { doc /* main engine */ :>> decision = "an entirely new rocket motor, the Space Shuttle Main Engine (SSME)"; :>> alternatives = "the XLR-129"; :>> reason = "that engine promised 250,000 pounds of thrust and NASA wanted 415,000, to reduce the number and weight of the engines in the Shuttle’s booster"; :>> year = ""; :>> block = "MPS"; }
    part <'DCN-018'> dcn_018 : DesignDecision { doc /* booster */ :>> decision = "drop it entirely"; :>> alternatives = "this damn big reusable booster; ablative stuff"; :>> reason = "You cannot get the pilots away, the metallic heat shield is going to give you all kinds of problems, to do it with ablative stuff makes it too heavy"; :>> year = ""; :>> block = "SRB"; }
    part <'DCN-019'> dcn_019 : DesignDecision { doc /* booster */ :>> decision = "the pressure-fed reusable booster"; :>> alternatives = "The winged S-IC"; :>> reason = "it appeared more costly than the pressure-fed reusable booster"; :>> year = ""; :>> block = "SRB"; }
}
