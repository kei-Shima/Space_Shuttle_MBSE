// SysML v2 テキスト：プログラム組織と飛行準備の認証定義書（Level・審査のゲート・判断の事例・MOD の CoFR）
// SSD-ORG-ORB-001 プログラム組織と飛行準備の認証定義書（Level・審査のゲート・判断の事例・MOD の CoFR） の表から生成（lib/build_docs_da.py・rev_da/dadata.py）。根拠の頁は SSD-ORG-ORB-001 にある。
package SSD_ORG_ORB_001 {
    doc /* SSD-ORG-ORB-001 プログラム組織と飛行準備の認証定義書（Level・審査のゲート・判断の事例・MOD の CoFR）。組織を part def OrgUnit、認証のゲートを ReviewGate、判断の事例を LaunchDecision、CoFR の表を CofrTable の使用として持つ。名称・年・区分は文字列の属性で、パッケージへの矢印は張らない。要求への関係（導出・充足・検証）は張らず、トレースの外に置く。 */
    private import ScalarValues::*;
    part def OrgUnit {
        doc /* プログラム組織の記録（報告書・資料の本文）。資料の年と本文の年は別 */
        attribute name : String;
        attribute level : String;
        attribute docYear : String;
        attribute textYear : String;
        attribute orgKind : String;
    }
    part def ReviewGate {
        doc /* 認証のゲート（審査・会議）の記録 */
        attribute name : String;
        attribute owner : String;
        attribute nextGate : String;
        attribute docYear : String;
    }
    part def LaunchDecision {
        doc /* 当時その場で下された判断の事例（委員会の所見は含めない） */
        attribute decisionDate : String;
        attribute forum : String;
        attribute scope : String;
        attribute docYear : String;
    }
    part def CofrTable {
        doc /* MOD の CoFR の状況の表（20要求×10担当）。プログラム全体の CoFR ではない */
        attribute flight : String;
        attribute greenCount : ScalarValues::Integer;
        attribute naCount : ScalarValues::Integer;
    }
    part <'ORG-001'> org_001 : OrgUnit { doc /* Johnson Space Center */ :>> name = "Johnson Space Center"; :>> level = ""; :>> docYear = "1986"; :>> textYear = ""; :>> orgKind = "センター"; }
    part <'ORG-002'> org_002 : OrgUnit { doc /* Marshall Space Flight Center */ :>> name = "Marshall Space Flight Center"; :>> level = ""; :>> docYear = "1986"; :>> textYear = ""; :>> orgKind = "センター"; }
    part <'ORG-003'> org_003 : OrgUnit { doc /* Kennedy Space Center */ :>> name = "Kennedy Space Center"; :>> level = ""; :>> docYear = "1986"; :>> textYear = ""; :>> orgKind = "センター"; }
    part <'ORG-004'> org_004 : OrgUnit { doc /* Rockwell International, Space Transportation Syste */ :>> name = "Rockwell International, Space Transportation Systems Division (Orbiter contractor)"; :>> level = ""; :>> docYear = "1986"; :>> textYear = "1972"; :>> orgKind = "契約者"; }
    part <'ORG-005'> org_005 : OrgUnit { doc /* Martin Marietta Denver Aerospace (External Tank co */ :>> name = "Martin Marietta Denver Aerospace (External Tank contractor)"; :>> level = ""; :>> docYear = "1986"; :>> textYear = "1972"; :>> orgKind = "契約者"; }
    part <'ORG-006'> org_006 : OrgUnit { doc /* Morton Thiokol Corporation (Solid Rocket Booster c */ :>> name = "Morton Thiokol Corporation (Solid Rocket Booster contractor)"; :>> level = ""; :>> docYear = "1986"; :>> textYear = "1972"; :>> orgKind = "契約者"; }
    part <'ORG-007'> org_007 : OrgUnit { doc /* Rocketdyne (Rockwell division; Orbiter main engine */ :>> name = "Rocketdyne (Rockwell division; Orbiter main engine contractor)"; :>> level = ""; :>> docYear = "1986"; :>> textYear = "1972"; :>> orgKind = "契約者"; }
    part <'ORG-008'> org_008 : OrgUnit { doc /* Mission Management Team */ :>> name = "Mission Management Team"; :>> level = ""; :>> docYear = "1986"; :>> textYear = ""; :>> orgKind = "会議・委員会"; }
    part <'ORG-009'> org_009 : OrgUnit { doc /* Shuttle Projects Office (Marshall) */ :>> name = "Shuttle Projects Office (Marshall)"; :>> level = ""; :>> docYear = "1986"; :>> textYear = ""; :>> orgKind = "センター"; }
    part <'ORG-010'> org_010 : OrgUnit { doc /* Solid Rocket Booster project (Marshall) */ :>> name = "Solid Rocket Booster project (Marshall)"; :>> level = "Level III"; :>> docYear = "1986"; :>> textYear = ""; :>> orgKind = "センター"; }
    part <'ORG-011'> org_011 : OrgUnit { doc /* Launch decision chain (SRB project manager upward) */ :>> name = "Launch decision chain (SRB project manager upward)"; :>> level = ""; :>> docYear = "1986"; :>> textYear = ""; :>> orgKind = "その他"; }
    part <'ORG-012'> org_012 : OrgUnit { doc /* Marshall center director (institutional manager) */ :>> name = "Marshall center director (institutional manager)"; :>> level = ""; :>> docYear = "1986"; :>> textYear = ""; :>> orgKind = "センター"; }
    part <'ORG-013'> org_013 : OrgUnit { doc /* Level I */ :>> name = "Level I"; :>> level = "Level I"; :>> docYear = "1986"; :>> textYear = ""; :>> orgKind = "Level（階層）"; }
    part <'ORG-014'> org_014 : OrgUnit { doc /* Level II (National Space Transportation Program Ma */ :>> name = "Level II (National Space Transportation Program Manager)"; :>> level = "Level II"; :>> docYear = "1986"; :>> textYear = ""; :>> orgKind = "Level（階層）"; }
    part <'ORG-015'> org_015 : OrgUnit { doc /* Level III (program managers for Orbiter, SRB, ET,  */ :>> name = "Level III (program managers for Orbiter, SRB, ET, SSME)"; :>> level = "Level III"; :>> docYear = "1986"; :>> textYear = ""; :>> orgKind = "Level（階層）"; }
    part <'ORG-016'> org_016 : OrgUnit { doc /* Level IV (contractors for Shuttle elements) */ :>> name = "Level IV (contractors for Shuttle elements)"; :>> level = "Level IV"; :>> docYear = "1986"; :>> textYear = ""; :>> orgKind = "Level（階層）"; }
    part <'ORG-017'> org_017 : OrgUnit { doc /* NASA Chief Engineer at Headquarters */ :>> name = "NASA Chief Engineer at Headquarters"; :>> level = ""; :>> docYear = "1986"; :>> textYear = ""; :>> orgKind = "センター"; }
    part <'ORG-018'> org_018 : OrgUnit { doc /* Safety, reliability and quality assurance at Johns */ :>> name = "Safety, reliability and quality assurance at Johnson (Level II)"; :>> level = "Level II"; :>> docYear = "1986"; :>> textYear = ""; :>> orgKind = "安全・品質"; }
    part <'ORG-019'> org_019 : OrgUnit { doc /* Safety, reliability and quality assurance at Kenne */ :>> name = "Safety, reliability and quality assurance at Kennedy"; :>> level = ""; :>> docYear = "1986"; :>> textYear = ""; :>> orgKind = "安全・品質"; }
    part <'ORG-020'> org_020 : OrgUnit { doc /* Reliability and Quality Assurance at Marshall */ :>> name = "Reliability and Quality Assurance at Marshall"; :>> level = ""; :>> docYear = "1986"; :>> textYear = ""; :>> orgKind = "安全・品質"; }
    part <'ORG-021'> org_021 : OrgUnit { doc /* Level III problem reporting to Level II (1983 revi */ :>> name = "Level III problem reporting to Level II (1983 revision)"; :>> level = "Level III"; :>> docYear = "1986"; :>> textYear = "1983"; :>> orgKind = "Level（階層）"; }
    part <'ORG-022'> org_022 : OrgUnit { doc /* Level III problem reporting to Level II (before 19 */ :>> name = "Level III problem reporting to Level II (before 1983)"; :>> level = "Level III"; :>> docYear = "1986"; :>> textYear = ""; :>> orgKind = "Level（階層）"; }
    part <'ORG-023'> org_023 : OrgUnit { doc /* Aerospace Safety Advisory Panel */ :>> name = "Aerospace Safety Advisory Panel"; :>> level = ""; :>> docYear = "1986"; :>> textYear = "1967"; :>> orgKind = "安全・品質"; }
    part <'ORG-024'> org_024 : OrgUnit { doc /* Space Shuttle Program Crew Safety Panel */ :>> name = "Space Shuttle Program Crew Safety Panel"; :>> level = ""; :>> docYear = "1986"; :>> textYear = "1971"; :>> orgKind = "安全・品質"; }
    part <'ORG-025'> org_025 : OrgUnit { doc /* Director, NSTS */ :>> name = "Director, NSTS"; :>> level = ""; :>> docYear = "1987"; :>> textYear = "1986"; :>> orgKind = "その他"; }
    part <'ORG-026'> org_026 : OrgUnit { doc /* Deputy Director, NSTS Program (JSC) */ :>> name = "Deputy Director, NSTS Program (JSC)"; :>> level = ""; :>> docYear = "1987"; :>> textYear = "1986"; :>> orgKind = "センター"; }
    part <'ORG-027'> org_027 : OrgUnit { doc /* Deputy Director, NSTS Operations (KSC) */ :>> name = "Deputy Director, NSTS Operations (KSC)"; :>> level = ""; :>> docYear = "1987"; :>> textYear = ""; :>> orgKind = "センター"; }
    part <'ORG-028'> org_028 : OrgUnit { doc /* Operations integration offices at JSC, KSC, and MS */ :>> name = "Operations integration offices at JSC, KSC, and MSFC"; :>> level = ""; :>> docYear = "1987"; :>> textYear = ""; :>> orgKind = "センター"; }
    part <'ORG-029'> org_029 : OrgUnit { doc /* Manager of Shuttle Projects at MSFC */ :>> name = "Manager of Shuttle Projects at MSFC"; :>> level = ""; :>> docYear = "1987"; :>> textYear = ""; :>> orgKind = "センター"; }
    part <'ORG-030'> org_030 : OrgUnit { doc /* SR&QA element of the NSTS Program Office */ :>> name = "SR&QA element of the NSTS Program Office"; :>> level = ""; :>> docYear = "1987"; :>> textYear = ""; :>> orgKind = "安全・品質"; }
    part <'ORG-031'> org_031 : OrgUnit { doc /* JSC Flight Crew Operations, Mission Operations, an */ :>> name = "JSC Flight Crew Operations, Mission Operations, and Mission Support offices"; :>> level = ""; :>> docYear = "1987"; :>> textYear = ""; :>> orgKind = "センター"; }
    part <'ORG-032'> org_032 : OrgUnit { doc /* KSC Director of STS Management and Operations */ :>> name = "KSC Director of STS Management and Operations"; :>> level = ""; :>> docYear = "1987"; :>> textYear = ""; :>> orgKind = "センター"; }
    part <'ORG-033'> org_033 : OrgUnit { doc /* Office of Space Flight Management Council */ :>> name = "Office of Space Flight Management Council"; :>> level = ""; :>> docYear = "1987"; :>> textYear = ""; :>> orgKind = "会議・委員会"; }
    part <'ORG-034'> org_034 : OrgUnit { doc /* NASA Space Flight Safety Panel */ :>> name = "NASA Space Flight Safety Panel"; :>> level = ""; :>> docYear = "1987"; :>> textYear = "1987"; :>> orgKind = "安全・品質"; }
    part <'ORG-035'> org_035 : OrgUnit { doc /* Level I/II/III program management concept */ :>> name = "Level I/II/III program management concept"; :>> level = "Level I/Il/Ill"; :>> docYear = "1987"; :>> textYear = "1986"; :>> orgKind = "Level（階層）"; }
    part <'ORG-036'> org_036 : OrgUnit { doc /* NSTS element project offices (SRB, ET, SSME, Orbit */ :>> name = "NSTS element project offices (SRB, ET, SSME, Orbiter, GFE, Spacelab, KSC, VLS)"; :>> level = "Level III"; :>> docYear = "1987"; :>> textYear = "1986"; :>> orgKind = "センター"; }
    part <'ORG-037'> org_037 : OrgUnit { doc /* Level II Overview Group */ :>> name = "Level II Overview Group"; :>> level = "Level II"; :>> docYear = "1987"; :>> textYear = "1986"; :>> orgKind = "Level（階層）"; }
    part <'ORG-038'> org_038 : OrgUnit { doc /* NASA Office of Safety, Reliability, and Quality As */ :>> name = "NASA Office of Safety, Reliability, and Quality Assurance (SR&QA)"; :>> level = ""; :>> docYear = "1987"; :>> textYear = ""; :>> orgKind = "安全・品質"; }
    part <'ORG-039'> org_039 : OrgUnit { doc /* NASA Headquarters */ :>> name = "NASA Headquarters"; :>> level = ""; :>> docYear = "2003"; :>> textYear = ""; :>> orgKind = "センター"; }
    part <'ORG-040'> org_040 : OrgUnit { doc /* Kennedy Space Center */ :>> name = "Kennedy Space Center"; :>> level = ""; :>> docYear = "2003"; :>> textYear = ""; :>> orgKind = "センター"; }
    part <'ORG-041'> org_041 : OrgUnit { doc /* Space Shuttle Program Office (Johnson Space Center */ :>> name = "Space Shuttle Program Office (Johnson Space Center)"; :>> level = ""; :>> docYear = "2003"; :>> textYear = ""; :>> orgKind = "センター"; }
    part <'ORG-042'> org_042 : OrgUnit { doc /* Space Shuttle Projects Office (Marshall Space Flig */ :>> name = "Space Shuttle Projects Office (Marshall Space Flight Center)"; :>> level = ""; :>> docYear = "2003"; :>> textYear = ""; :>> orgKind = "センター"; }
    part <'ORG-043'> org_043 : OrgUnit { doc /* United Space Alliance */ :>> name = "United Space Alliance"; :>> level = ""; :>> docYear = "2003"; :>> textYear = "1996"; :>> orgKind = "契約者"; }
    part <'ORG-044'> org_044 : OrgUnit { doc /* Boeing（NASA Systems） */ :>> name = "Boeing（NASA Systems）"; :>> level = ""; :>> docYear = "2003"; :>> textYear = ""; :>> orgKind = "契約者"; }
    part <'ORG-045'> org_045 : OrgUnit { doc /* Boeing Rocketdyne Propulsion & Power */ :>> name = "Boeing Rocketdyne Propulsion & Power"; :>> level = ""; :>> docYear = "2003"; :>> textYear = ""; :>> orgKind = "契約者"; }
    part <'ORG-046'> org_046 : OrgUnit { doc /* ATK Thiokol Propulsion */ :>> name = "ATK Thiokol Propulsion"; :>> level = ""; :>> docYear = "2003"; :>> textYear = ""; :>> orgKind = "契約者"; }
    part <'ORG-047'> org_047 : OrgUnit { doc /* Lockheed Martin Space Systems, Michoud Operations */ :>> name = "Lockheed Martin Space Systems, Michoud Operations"; :>> level = ""; :>> docYear = "2003"; :>> textYear = ""; :>> orgKind = "契約者"; }
    part <'ORG-048'> org_048 : OrgUnit { doc /* Mission Management Team (MMT) */ :>> name = "Mission Management Team (MMT)"; :>> level = ""; :>> docYear = "2003"; :>> textYear = ""; :>> orgKind = "会議・委員会"; }
    part <'ORG-049'> org_049 : OrgUnit { doc /* Mission Evaluation Room (MER) */ :>> name = "Mission Evaluation Room (MER)"; :>> level = ""; :>> docYear = "2003"; :>> textYear = ""; :>> orgKind = "その他"; }
    part <'ORG-050'> org_050 : OrgUnit { doc /* Flight Director (Johnson Space Center) */ :>> name = "Flight Director (Johnson Space Center)"; :>> level = ""; :>> docYear = "2003"; :>> textYear = ""; :>> orgKind = "センター"; }
    part <'ORG-051'> org_051 : OrgUnit { doc /* Launch Integration Manager (Kennedy Space Center) */ :>> name = "Launch Integration Manager (Kennedy Space Center)"; :>> level = ""; :>> docYear = "2003"; :>> textYear = ""; :>> orgKind = "センター"; }
    part <'ORG-052'> org_052 : OrgUnit { doc /* Intercenter Photo Working Group */ :>> name = "Intercenter Photo Working Group"; :>> level = ""; :>> docYear = "2003"; :>> textYear = "2003"; :>> orgKind = "会議・委員会"; }
    part <'ORG-053'> org_053 : OrgUnit { doc /* Johnson Space Center（Space Shuttle Program の lead  */ :>> name = "Johnson Space Center（Space Shuttle Program の lead center）"; :>> level = ""; :>> docYear = "2003"; :>> textYear = "1996"; :>> orgKind = "センター"; }
    part <'ORG-054'> org_054 : OrgUnit { doc /* United Space Alliance（SFOC の下の責任） */ :>> name = "United Space Alliance（SFOC の下の責任）"; :>> level = ""; :>> docYear = "2003"; :>> textYear = ""; :>> orgKind = "契約者"; }
    part <'ORG-055'> org_055 : OrgUnit { doc /* NASA（SFOC の下の責任） */ :>> name = "NASA（SFOC の下の責任）"; :>> level = ""; :>> docYear = "2003"; :>> textYear = ""; :>> orgKind = "契約者"; }
    part <'ORG-056'> org_056 : OrgUnit { doc /* External Tank Project (Marshall Space Flight Cente */ :>> name = "External Tank Project (Marshall Space Flight Center)"; :>> level = ""; :>> docYear = "2003"; :>> textYear = "1992"; :>> orgKind = "センター"; }
    part <'ORG-057'> org_057 : OrgUnit { doc /* Space Shuttle Integration Office (Johnson Space Ce */ :>> name = "Space Shuttle Integration Office (Johnson Space Center)"; :>> level = ""; :>> docYear = "2003"; :>> textYear = "1992"; :>> orgKind = "センター"; }
    part <'ORG-058'> org_058 : OrgUnit { doc /* Debris Assessment Team (DAT) */ :>> name = "Debris Assessment Team (DAT)"; :>> level = ""; :>> docYear = "2003"; :>> textYear = "2003"; :>> orgKind = "会議・委員会"; }
    part <'ORG-059'> org_059 : OrgUnit { doc /* Headquarters Office of Safety, Reliability, and Qu */ :>> name = "Headquarters Office of Safety, Reliability, and Quality Assurance"; :>> level = ""; :>> docYear = "2003"; :>> textYear = "1986"; :>> orgKind = "安全・品質"; }
    part <'ORG-060'> org_060 : OrgUnit { doc /* Aerospace Safety Advisory Panel (ASAP) */ :>> name = "Aerospace Safety Advisory Panel (ASAP)"; :>> level = ""; :>> docYear = "2003"; :>> textYear = "1967"; :>> orgKind = "安全・品質"; }
    part <'ORG-061'> org_061 : OrgUnit { doc /* Shuttle Independent Assessment Team */ :>> name = "Shuttle Independent Assessment Team"; :>> level = ""; :>> docYear = "2003"; :>> textYear = "1999"; :>> orgKind = "会議・委員会"; }
    part <'ORG-062'> org_062 : OrgUnit { doc /* Office of Safety and Mission Assurance (NASA Headq */ :>> name = "Office of Safety and Mission Assurance (NASA Headquarters)"; :>> level = ""; :>> docYear = "2003"; :>> textYear = ""; :>> orgKind = "安全・品質"; }
    part <'ORG-063'> org_063 : OrgUnit { doc /* Johnson Space Shuttle Safety, Reliability and Qual */ :>> name = "Johnson Space Shuttle Safety, Reliability and Quality Assurance Division Chief"; :>> level = ""; :>> docYear = "2003"; :>> textYear = ""; :>> orgKind = "安全・品質"; }
    part <'ORG-064'> org_064 : OrgUnit { doc /* Shuttle Program Safety and Mission Assurance Manag */ :>> name = "Shuttle Program Safety and Mission Assurance Manager (Johnson)"; :>> level = ""; :>> docYear = "2003"; :>> textYear = ""; :>> orgKind = "安全・品質"; }
    part <'ORG-065'> org_065 : OrgUnit { doc /* Shuttle Program Manager（安全の責任） */ :>> name = "Shuttle Program Manager（安全の責任）"; :>> level = ""; :>> docYear = "2003"; :>> textYear = ""; :>> orgKind = "その他"; }
    part <'ORG-066'> org_066 : OrgUnit { doc /* NASA Engineering and Safety Center (NESC) */ :>> name = "NASA Engineering and Safety Center (NESC)"; :>> level = ""; :>> docYear = "2005"; :>> textYear = ""; :>> orgKind = "安全・品質"; }
    part <'ORG-067'> org_067 : OrgUnit { doc /* Mission Management Team (MMT) as defined in NSTS 0 */ :>> name = "Mission Management Team (MMT) as defined in NSTS 07700 Vol. VIII (background)"; :>> level = ""; :>> docYear = "2005"; :>> textYear = ""; :>> orgKind = "会議・委員会"; }
    part <'ORG-068'> org_068 : OrgUnit { doc /* Mission Management Team (MMT) after the changes */ :>> name = "Mission Management Team (MMT) after the changes"; :>> level = ""; :>> docYear = "2005"; :>> textYear = ""; :>> orgKind = "会議・委員会"; }
    part <'ORG-069'> org_069 : OrgUnit { doc /* Independent Technical Authority (NASA Chief Engine */ :>> name = "Independent Technical Authority (NASA Chief Engineer)"; :>> level = ""; :>> docYear = "2005"; :>> textYear = "2004"; :>> orgKind = "その他"; }
    part <'ORG-070'> org_070 : OrgUnit { doc /* Technical Warrant Holders */ :>> name = "Technical Warrant Holders"; :>> level = ""; :>> docYear = "2005"; :>> textYear = "2004"; :>> orgKind = "その他"; }
    part <'ORG-071'> org_071 : OrgUnit { doc /* Chief Safety and Mission Assurance Officer / Offic */ :>> name = "Chief Safety and Mission Assurance Officer / Office of Safety and Mission Assurance (OSMA)"; :>> level = ""; :>> docYear = "2005"; :>> textYear = ""; :>> orgKind = "安全・品質"; }
    part <'ORG-072'> org_072 : OrgUnit { doc /* Space Shuttle Program SMA Manager / program SMA Of */ :>> name = "Space Shuttle Program SMA Manager / program SMA Office"; :>> level = ""; :>> docYear = "2005"; :>> textYear = ""; :>> orgKind = "安全・品質"; }
    part <'ORG-073'> org_073 : OrgUnit { doc /* Engineering Risk Review Panels (ERRP) */ :>> name = "Engineering Risk Review Panels (ERRP)"; :>> level = "Level II (Program) and Level III (Project/Element)"; :>> docYear = "2005"; :>> textYear = ""; :>> orgKind = "会議・委員会"; }
    part <'ORG-074'> org_074 : OrgUnit { doc /* Level II ERRP Panel */ :>> name = "Level II ERRP Panel"; :>> level = "Level II"; :>> docYear = "2005"; :>> textYear = ""; :>> orgKind = "Level（階層）"; }
    part <'ORG-075'> org_075 : OrgUnit { doc /* Level III ERRPs (JSC Panel, MSFC Panel, KSC Panel) */ :>> name = "Level III ERRPs (JSC Panel, MSFC Panel, KSC Panel)"; :>> level = "Level III"; :>> docYear = "2005"; :>> textYear = ""; :>> orgKind = "Level（階層）"; }
    part <'ORG-076'> org_076 : OrgUnit { doc /* Space Shuttle Systems Engineering and Integration  */ :>> name = "Space Shuttle Systems Engineering and Integration Office (SEIO)"; :>> level = ""; :>> docYear = "2005"; :>> textYear = ""; :>> orgKind = "その他"; }
    part <'ORG-077'> org_077 : OrgUnit { doc /* Orbiter Project Office (formerly Space Shuttle Veh */ :>> name = "Orbiter Project Office (formerly Space Shuttle Vehicle Engineering Office)"; :>> level = ""; :>> docYear = "2005"; :>> textYear = ""; :>> orgKind = "その他"; }
    part <'ORG-078'> org_078 : OrgUnit { doc /* Integration Control Board */ :>> name = "Integration Control Board"; :>> level = ""; :>> docYear = "2005"; :>> textYear = ""; :>> orgKind = "会議・委員会"; }
    part <'ORG-079'> org_079 : OrgUnit { doc /* Center SMA organizations */ :>> name = "Center SMA organizations"; :>> level = ""; :>> docYear = "2005"; :>> textYear = ""; :>> orgKind = "安全・品質"; }
    part <'GAT-001'> gat_001 : ReviewGate { doc /* Cargo integration review */ :>> name = "Cargo integration review"; :>> owner = ""; :>> nextGate = ""; :>> docYear = "1986"; }
    part <'GAT-002'> gat_002 : ReviewGate { doc /* Flight Planning and Stowage Review (launch minus f */ :>> name = "Flight Planning and Stowage Review (launch minus five months)"; :>> owner = ""; :>> nextGate = ""; :>> docYear = "1986"; }
    part <'GAT-003'> gat_003 : ReviewGate { doc /* Level IV contractor certification of flight readin */ :>> name = "Level IV contractor certification of flight readiness"; :>> owner = "contractors for the elements (Level IV)"; :>> nextGate = "Level III NASA project managers at Johnson and Marshall (certification is made to them)"; :>> docYear = "1986"; }
    part <'GAT-004'> gat_004 : ReviewGate { doc /* Level III review at Marshall */ :>> name = "Level III review at Marshall"; :>> owner = "Marshall project managers (Level III) and Center Director"; :>> nextGate = "Certification of Flight Readiness to the Level II Program Manager at Johnson"; :>> docYear = "1986"; }
    part <'GAT-005'> gat_005 : ReviewGate { doc /* Level III review at Kennedy */ :>> name = "Level III review at Kennedy"; :>> owner = "Center Director (chair)"; :>> nextGate = "Certification of Flight Readiness to the Level II Program Manager at Johnson"; :>> docYear = "1986"; }
    part <'GAT-006'> gat_006 : ReviewGate { doc /* Certification of Flight Readiness to the Level II  */ :>> name = "Certification of Flight Readiness to the Level II Program Manager"; :>> owner = "Level II Program Manager at Johnson"; :>> nextGate = "Level I Flight Readiness Review (the process culminates in the Level I review)"; :>> docYear = "1986"; }
    part <'GAT-007'> gat_007 : ReviewGate { doc /* Level I Flight Readiness Review */ :>> name = "Level I Flight Readiness Review"; :>> owner = "NASA Associate Administrator for Space Flight (chair); supported by NASA Chief Engineer, Program Man"; :>> nextGate = "L-1 Mission Management Team meeting (FRR action items to be closed out at L-1)"; :>> docYear = "1986"; }
    part <'GAT-008'> gat_008 : ReviewGate { doc /* L-1 Mission Management Team meeting */ :>> name = "L-1 Mission Management Team meeting"; :>> owner = "Mission Management Team (supports Associate Administrator for Space Flight and Program Manager)"; :>> nextGate = ""; :>> docYear = "1986"; }
    part <'GAT-009'> gat_009 : ReviewGate { doc /* Shuttle Projects Flight Readiness Review */ :>> name = "Shuttle Projects Flight Readiness Review"; :>> owner = ""; :>> nextGate = "Level I Flight Readiness Review (intermediate review between Level III and Level I)"; :>> docYear = "1986"; }
    part <'GAT-010'> gat_010 : ReviewGate { doc /* Program Requirements Change Board (Noon Special PR */ :>> name = "Program Requirements Change Board (Noon Special PRCB) flight anomaly closeout"; :>> owner = "Manager of the National Space Transportation System (Level II)"; :>> nextGate = ""; :>> docYear = "1986"; }
    part <'GAT-011'> gat_011 : ReviewGate { doc /* Level II Program Requirements Control Board */ :>> name = "Level II Program Requirements Control Board"; :>> owner = "chaired by the project manager"; :>> nextGate = ""; :>> docYear = "1986"; }
    part <'GAT-012'> gat_012 : ReviewGate { doc /* Flight Readiness Review (FRR) */ :>> name = "Flight Readiness Review (FRR)"; :>> owner = "Associate Administrator for Space Flight (chair); Deputy Director, NSTS Operations presents it (p115"; :>> nextGate = "mission management team (MMT) meeting at L-1: each project element and contractor signs an endorseme"; :>> docYear = "1987"; }
    part <'GAT-013'> gat_013 : ReviewGate { doc /* Mission Management Team (MMT) L-1 review */ :>> name = "Mission Management Team (MMT) L-1 review"; :>> owner = "Deputy Director, NSTS Operations (chairs the MMT, p34; the MMT reports to him, p38)"; :>> nextGate = ""; :>> docYear = "1987"; }
    part <'GAT-014'> gat_014 : ReviewGate { doc /* Program Requirements Control Board (PRCB) */ :>> name = "Program Requirements Control Board (PRCB)"; :>> owner = "Director, NSTS, and Deputy Director, NSTS Program (co-chairs)"; :>> nextGate = ""; :>> docYear = "1987"; }
    part <'GAT-015'> gat_015 : ReviewGate { doc /* Senior Safety Review Board */ :>> name = "Senior Safety Review Board"; :>> owner = ""; :>> nextGate = "PRCB (accepted risk candidates are forwarded to the PRCB for approval by the Director, NSTS)"; :>> docYear = "1987"; }
    part <'GAT-016'> gat_016 : ReviewGate { doc /* Level III Configuration Control Board (CCB) Preboa */ :>> name = "Level III Configuration Control Board (CCB) Preboard"; :>> owner = ""; :>> nextGate = "Level III CCB (the preboard selects the items to submit)"; :>> docYear = "1987"; }
    part <'GAT-017'> gat_017 : ReviewGate { doc /* Level III Configuration Control Board (CCB) */ :>> name = "Level III Configuration Control Board (CCB)"; :>> owner = ""; :>> nextGate = "Level II Program Requirements Change Board (PRCB), for consideration by the NSTS Program Manager"; :>> docYear = "1987"; }
    part <'GAT-018'> gat_018 : ReviewGate { doc /* Level II Program Requirements Change Board (PRCB) */ :>> name = "Level II Program Requirements Change Board (PRCB)"; :>> owner = ""; :>> nextGate = "Level I NASA Headquarters (recommended CIL changes and enhancements go to Level I for approval)"; :>> docYear = "1987"; }
    part <'GAT-019'> gat_019 : ReviewGate { doc /* Level I board */ :>> name = "Level I board"; :>> owner = "NASA Associate Administrator for Space Flight (chair; the board consists of his designated represent"; :>> nextGate = ""; :>> docYear = "1987"; }
    part <'GAT-020'> gat_020 : ReviewGate { doc /* Level II Systems Integration Review Board (element */ :>> name = "Level II Systems Integration Review Board (element interface functional analysis)"; :>> owner = ""; :>> nextGate = "Level II PRCB (the results are then presented to the Level II PRCB for approval)"; :>> docYear = "1987"; }
    part <'GAT-021'> gat_021 : ReviewGate { doc /* Payload Safety Review Panel（最終会議） */ :>> name = "Payload Safety Review Panel（最終会議）"; :>> owner = ""; :>> nextGate = ""; :>> docYear = "2003"; }
    part <'GAT-022'> gat_022 : ReviewGate { doc /* Flight Preparation Process（Project Milestone Revie */ :>> name = "Flight Preparation Process（Project Milestone Reviews・Program Milestone Reviews）"; :>> owner = ""; :>> nextGate = "Flight Readiness Review（本文: At the final review, called the Flight Readiness Review）"; :>> docYear = "2003"; }
    part <'GAT-023'> gat_023 : ReviewGate { doc /* Launch Readiness Review (LRR) */ :>> name = "Launch Readiness Review (LRR)"; :>> owner = "Kennedy の Director of Shuttle Processing（STS-107 の LRR で chair）"; :>> nextGate = ""; :>> docYear = "2003"; }
    part <'GAT-024'> gat_024 : ReviewGate { doc /* Flight Readiness Review (FRR) */ :>> name = "Flight Readiness Review (FRR)"; :>> owner = "Office of Space Flight の Associate Administrator（chair）"; :>> nextGate = "Pre-launch Mission Management Team（FRR 後の open items・変更を評価。FRR で完了しなかった CoFR の exception は Pre-Launc"; :>> docYear = "2003"; }
    part <'GAT-025'> gat_025 : ReviewGate { doc /* Pre-launch Mission Management Team Meeting */ :>> name = "Pre-launch Mission Management Team Meeting"; :>> owner = "Kennedy の Launch Integration Manager（打上げ前の MMT の議長。STS-107 は Acting Manager of Launch Integration）"; :>> nextGate = "Delta Pre-Launch MMT review（STS-107 では翌日: at the Delta Pre-Launch Mission Management Team review the"; :>> docYear = "2003"; }
    part <'GAT-026'> gat_026 : ReviewGate { doc /* Delta Pre-Launch Mission Management Team Meeting（S */ :>> name = "Delta Pre-Launch Mission Management Team Meeting（STS-107）"; :>> owner = "Acting Manager of Launch Integration（議長）"; :>> nextGate = ""; :>> docYear = "2003"; }
    part <'GAT-027'> gat_027 : ReviewGate { doc /* Pre-Tanking Mission Management Team Meeting（STS-10 */ :>> name = "Pre-Tanking Mission Management Team Meeting（STS-107）"; :>> owner = "Acting Manager of Launch Integration（議長）"; :>> nextGate = ""; :>> docYear = "2003"; }
    part <'GAT-028'> gat_028 : ReviewGate { doc /* Mission Evaluation Room への解析の提示 */ :>> name = "Mission Evaluation Room への解析の提示"; :>> owner = "Mission Evaluation Room manager（MMT に提示する者）"; :>> nextGate = "Mission Management Team（本文: is then presented by the MER manager to the MMT）"; :>> docYear = "2003"; }
    part <'GAT-029'> gat_029 : ReviewGate { doc /* SFOC の safety 'gates' */ :>> name = "SFOC の safety 'gates'"; :>> owner = ""; :>> nextGate = ""; :>> docYear = "2003"; }
    part <'GAT-030'> gat_030 : ReviewGate { doc /* Program Requirements Control Board (PRCB) */ :>> name = "Program Requirements Control Board (PRCB)"; :>> owner = "Shuttle Program Manager（STS-112 の帰還後の会議で chair、p.125）"; :>> nextGate = "次の mission の Flight Readiness Review（IFA の resolved/closed の報告。p.123: At the Flight Readiness Review"; :>> docYear = "2003"; }
    part <'GAT-031'> gat_031 : ReviewGate { doc /* Orbiter Rollout Review (ORR) */ :>> name = "Orbiter Rollout Review (ORR)"; :>> owner = "STS-114 の Launch Integration Manager（本文: STS-114 の duties の一つとして chair）"; :>> nextGate = ""; :>> docYear = "2003"; }
    part <'GAT-032'> gat_032 : ReviewGate { doc /* Mission Management Team（飛行中の会議） */ :>> name = "Mission Management Team（飛行中の会議）"; :>> owner = "Space Shuttle Program Integration Manager（Johnson、飛行中の MMT 議長、p.32）"; :>> nextGate = ""; :>> docYear = "2003"; }
    part <'GAT-033'> gat_033 : ReviewGate { doc /* 画像要請の経路（飛行中、Flight Dynamics Officer） */ :>> name = "画像要請の経路（飛行中、Flight Dynamics Officer）"; :>> owner = "Flight Dynamics Officer（p.149: the interagency agreement ... FDO is responsible for initiating such "; :>> nextGate = ""; :>> docYear = "2003"; }
    part <'GAT-034'> gat_034 : ReviewGate { doc /* Pre-launch Assessment Review（安全） */ :>> name = "Pre-launch Assessment Review（安全）"; :>> owner = "Johnson の Space Shuttle SR&QA Division Chief（Headquarters のために orchestrate）"; :>> nextGate = ""; :>> docYear = "2003"; }
    part <'GAT-035'> gat_035 : ReviewGate { doc /* Program Requirements Control Board (PRCB) */ :>> name = "Program Requirements Control Board (PRCB)"; :>> owner = ""; :>> nextGate = ""; :>> docYear = "2005"; }
    part <'GAT-036'> gat_036 : ReviewGate { doc /* MMT Tanking Meeting */ :>> name = "MMT Tanking Meeting"; :>> owner = ""; :>> nextGate = "the readiness of the camera sites is reported to the Launch Director at T-20 minutes, who provides s"; :>> docYear = "2005"; }
    part <'GAT-037'> gat_037 : ReviewGate { doc /* Mission Management Team (MMT), preflight and fligh */ :>> name = "Mission Management Team (MMT), preflight and flight (as described in §3.11.2 Background)"; :>> owner = "MMT Chair (supported by the entire MMT)"; :>> nextGate = "flight MMT at JSC after the Flight Director declares Go for On-Orbit Operations (about 2 hours after"; :>> docYear = "2005"; }
    part <'GAT-038'> gat_038 : ReviewGate { doc /* Mission Management Team (MMT) after the changes */ :>> name = "Mission Management Team (MMT) after the changes"; :>> owner = "Space Shuttle Program Deputy Manager (now chairs both preflight and flight phases)"; :>> nextGate = ""; :>> docYear = "2005"; }
    part <'GAT-039'> gat_039 : ReviewGate { doc /* Safety and Mission Assurance Readiness Reviews (SM */ :>> name = "Safety and Mission Assurance Readiness Reviews (SMARR)"; :>> owner = "Headquarters OSMA (the formalizing is to improve OSMA insight)"; :>> nextGate = ""; :>> docYear = "2005"; }
    part <'GAT-040'> gat_040 : ReviewGate { doc /* Space Operations Mission Directorate Space Shuttle */ :>> name = "Space Operations Mission Directorate Space Shuttle Certificate of Flight Readiness (CoFR) process"; :>> owner = "Space Operations Mission Directorate"; :>> nextGate = ""; :>> docYear = "2005"; }
    part <'GAT-041'> gat_041 : ReviewGate { doc /* Level II ERRP Panel (integrated hazards) */ :>> name = "Level II ERRP Panel (integrated hazards)"; :>> owner = ""; :>> nextGate = "System Integration Configuration Board (SICB), and finally the ITA and the Space Shuttle Program Man"; :>> docYear = "2005"; }
    part <'GAT-042'> gat_042 : ReviewGate { doc /* Flight Readiness Review (L-2 week) as a CSCS repor */ :>> name = "Flight Readiness Review (L-2 week) as a CSCS reporting point"; :>> owner = ""; :>> nextGate = "updates to the CSCS estimate at the L-2-day and L-1-day MMT meetings, the L-9 hour pre-tanking meeti"; :>> docYear = "2005"; }
    part <'GAT-043'> gat_043 : ReviewGate { doc /* Design Certification Review (DCR) for return to fl */ :>> name = "Design Certification Review (DCR) for return to flight (later called Design Verification Review, DVR"; :>> owner = "Space Shuttle Program (PRCBD S062246 approved the plan NSTS 60524 on August 27, 2004)"; :>> nextGate = ""; :>> docYear = "2005"; }
    part <'GAT-044'> gat_044 : ReviewGate { doc /* Certificate of Flight Readiness (CoFR) for STS-107 */ :>> name = "Certificate of Flight Readiness (CoFR) for STS-107"; :>> owner = ""; :>> nextGate = ""; :>> docYear = "2005"; }
    part <'GAT-045'> gat_045 : ReviewGate { doc /* MOD Flight Readiness Review (STS-115/12A) */ :>> name = "MOD Flight Readiness Review (STS-115/12A)"; :>> owner = "JSC Mission Operations Directorate, Flight Director Office (DA8)"; :>> nextGate = "Level 1 FRR (8/15-16/2006): all Standard and Non-Standard open work will be closed out prior to the "; :>> docYear = "2006"; }
    part <'GAT-046'> gat_046 : ReviewGate { doc /* Flight Rules approval (Flight Techniques, JOP, and */ :>> name = "Flight Rules approval (Flight Techniques, JOP, and FRCB forums)"; :>> owner = ""; :>> nextGate = ""; :>> docYear = "2006"; }
    part <'GAT-047'> gat_047 : ReviewGate { doc /* LCC/MEL/MIL review (MOD, with the LCCWG) */ :>> name = "LCC/MEL/MIL review (MOD, with the LCCWG)"; :>> owner = ""; :>> nextGate = "PRCB (the LCN awaits PRCB scheduling for final approval and publication, ECD 9/10)"; :>> docYear = "2008"; }
    part <'GAT-048'> gat_048 : ReviewGate { doc /* MOD Flight Readiness Review (STS-125) */ :>> name = "MOD Flight Readiness Review (STS-125)"; :>> owner = "Space Transportation Vehicle Division (DS1), Agenda Item 4"; :>> nextGate = ""; :>> docYear = "2008"; }
    part <'GAT-049'> gat_049 : ReviewGate { doc /* MOD Flight Readiness Review (STS-400 LON) */ :>> name = "MOD Flight Readiness Review (STS-400 LON)"; :>> owner = "Space Transportation Vehicle Division (DS1)"; :>> nextGate = ""; :>> docYear = "2008"; }
    part <'GAT-050'> gat_050 : ReviewGate { doc /* MOD Flight Readiness Review (STS-119) */ :>> name = "MOD Flight Readiness Review (STS-119)"; :>> owner = "Space Transportation Vehicle Division (DS1), Agenda Item 5"; :>> nextGate = ""; :>> docYear = "2009"; }
    part <'JDG-001'> jdg_001 : LaunchDecision { doc /* Program Requirements Change Board */ :>> decisionDate = "1986-01-22"; :>> forum = "Program Requirements Change Board"; :>> scope = "打上げ・飛行"; :>> docYear = "1986"; }
    part <'JDG-002'> jdg_002 : LaunchDecision { doc /* Evening management conference */ :>> decisionDate = "1986-01-25"; :>> forum = "Evening management conference"; :>> scope = "打上げ・飛行"; :>> docYear = "1986"; }
    part <'JDG-003'> jdg_003 : LaunchDecision { doc /* Meeting to consider the ice inspection team's repo */ :>> decisionDate = "1986-01-28"; :>> forum = "Meeting to consider the ice inspection team's report (after the 01:35–03:00 inspection)"; :>> scope = "打上げ・飛行"; :>> docYear = "1986"; }
    part <'JDG-004'> jdg_004 : LaunchDecision { doc /* Decision after the second ice inspection (08:44 a. */ :>> decisionDate = "1986-01-28"; :>> forum = "Decision after the second ice inspection (08:44 a.m.)"; :>> scope = "打上げ・飛行"; :>> docYear = "1986"; }
    part <'JDG-005'> jdg_005 : LaunchDecision { doc /* Hold at launch minus nine minutes */ :>> decisionDate = "1986-01-28"; :>> forum = "Hold at launch minus nine minutes"; :>> scope = "打上げ・飛行"; :>> docYear = "1986"; }
    part <'JDG-006'> jdg_006 : LaunchDecision { doc /* Level I Flight Readiness Review (then directive of */ :>> decisionDate = "1986-01-15"; :>> forum = "Level I Flight Readiness Review (then directive of January 23)"; :>> scope = "打上げ・飛行"; :>> docYear = "1986"; }
    part <'JDG-007'> jdg_007 : LaunchDecision { doc /* Launch constraint after STS 51-B */ :>> decisionDate = "1985-07"; :>> forum = "Launch constraint after STS 51-B"; :>> scope = "打上げ・飛行"; :>> docYear = "1986"; }
    part <'JDG-008'> jdg_008 : LaunchDecision { doc /* Mission Management Team (12:36 p.m.) */ :>> decisionDate = "1986-01-27"; :>> forum = "Mission Management Team (12:36 p.m.)"; :>> scope = "打上げ・飛行"; :>> docYear = "1986"; }
    part <'JDG-009'> jdg_009 : LaunchDecision { doc /* Mission Management Team (2:00 p.m.) */ :>> decisionDate = "1986-01-27"; :>> forum = "Mission Management Team (2:00 p.m.)"; :>> scope = "打上げ・飛行"; :>> docYear = "1986"; }
    part <'JDG-010'> jdg_010 : LaunchDecision { doc /* Teleconference among Marshall, Kennedy and Thiokol */ :>> decisionDate = "1986-01-27"; :>> forum = "Teleconference among Marshall, Kennedy and Thiokol (first phase, 5:45 p.m.)"; :>> scope = "打上げ・飛行"; :>> docYear = "1986"; }
    part <'JDG-011'> jdg_011 : LaunchDecision { doc /* Second teleconference (Thiokol Wasatch, Marshall,  */ :>> decisionDate = "1986-01-27"; :>> forum = "Second teleconference (Thiokol Wasatch, Marshall, Kennedy), about 8:45 p.m."; :>> scope = "打上げ・飛行"; :>> docYear = "1986"; }
    part <'JDG-012'> jdg_012 : LaunchDecision { doc /* Thiokol management review after off-net caucus (ab */ :>> decisionDate = "1986-01-27"; :>> forum = "Thiokol management review after off-net caucus (about 10:30–11:00 p.m.)"; :>> scope = "打上げ・飛行"; :>> docYear = "1986"; }
    part <'JDG-013'> jdg_013 : LaunchDecision { doc /* Teleconference (Kennedy, Marshall, Thiokol), concl */ :>> decisionDate = "1986-01-27"; :>> forum = "Teleconference (Kennedy, Marshall, Thiokol), conclusion about 11:15 p.m."; :>> scope = "打上げ・飛行"; :>> docYear = "1986"; }
    part <'JDG-014'> jdg_014 : LaunchDecision { doc /* Teleconference among Marshall resident manager at  */ :>> decisionDate = "1986-01-27"; :>> forum = "Teleconference among Marshall resident manager at KSC, the Level II Program Manager and KSC launch o"; :>> scope = "打上げ・飛行"; :>> docYear = "1986"; }
    part <'JDG-015'> jdg_015 : LaunchDecision { doc /* About 5:00 a.m. discussion at Kennedy among Marsha */ :>> decisionDate = "1986-01-28"; :>> forum = "About 5:00 a.m. discussion at Kennedy among Marshall center director and Marshall project managers"; :>> scope = "打上げ・飛行"; :>> docYear = "1986"; }
    part <'JDG-016'> jdg_016 : LaunchDecision { doc /* Rockwell Downey (about 5:30–5:45 a.m. PST) */ :>> decisionDate = "1986-01-28"; :>> forum = "Rockwell Downey (about 5:30–5:45 a.m. PST)"; :>> scope = "打上げ・飛行"; :>> docYear = "1986"; }
    part <'JDG-017'> jdg_017 : LaunchDecision { doc /* Mission Management Team meeting at 9:00 a.m. (Rock */ :>> decisionDate = "1986-01-28"; :>> forum = "Mission Management Team meeting at 9:00 a.m. (Rockwell position)"; :>> scope = "打上げ・飛行"; :>> docYear = "1986"; }
    part <'JDG-018'> jdg_018 : LaunchDecision { doc /* Mission Management Team meeting at 9:00 a.m. */ :>> decisionDate = "1986-01-28"; :>> forum = "Mission Management Team meeting at 9:00 a.m."; :>> scope = "打上げ・飛行"; :>> docYear = "1986"; }
    part <'JDG-019'> jdg_019 : LaunchDecision { doc /* Level I waiver approval of the field joint Critica */ :>> decisionDate = "1983-03-28"; :>> forum = "Level I waiver approval of the field joint Criticality 1 (fail-safe requirement)"; :>> scope = "打上げ・飛行"; :>> docYear = "1986"; }
    part <'JDG-020'> jdg_020 : LaunchDecision { doc /* Level I Flight Readiness Review for STS 51-F (July */ :>> decisionDate = "1985-07-02"; :>> forum = "Level I Flight Readiness Review for STS 51-F (July 2, 1985)"; :>> scope = "打上げ・飛行"; :>> docYear = "1986"; }
    part <'JDG-021'> jdg_021 : LaunchDecision { doc /* Shuttle Program Manager (Level II) approval of the */ :>> decisionDate = ""; :>> forum = "Shuttle Program Manager (Level II) approval of the Criticality change"; :>> scope = "打上げ・飛行"; :>> docYear = "1986"; }
    part <'JDG-022'> jdg_022 : LaunchDecision { doc /* STS-107 Launch Readiness Review（Kennedy Space Cent */ :>> decisionDate = "2002-12-18"; :>> forum = "STS-107 Launch Readiness Review（Kennedy Space Center）"; :>> scope = "打上げ・飛行"; :>> docYear = "2003"; }
    part <'JDG-023'> jdg_023 : LaunchDecision { doc /* STS-107 Flight Readiness Review（最終） */ :>> decisionDate = "2003-01-09"; :>> forum = "STS-107 Flight Readiness Review（最終）"; :>> scope = "打上げ・飛行"; :>> docYear = "2003"; }
    part <'JDG-024'> jdg_024 : LaunchDecision { doc /* Pre-launch Mission Management Team Meeting（Kennedy */ :>> decisionDate = "2003-01-14"; :>> forum = "Pre-launch Mission Management Team Meeting（Kennedy）"; :>> scope = "打上げ・飛行"; :>> docYear = "2003"; }
    part <'JDG-025'> jdg_025 : LaunchDecision { doc /* Delta Pre-Launch Mission Management Team Meeting（K */ :>> decisionDate = "2003-01-15"; :>> forum = "Delta Pre-Launch Mission Management Team Meeting（Kennedy、9:00 a.m. EST）"; :>> scope = "打上げ・飛行"; :>> docYear = "2003"; }
    part <'JDG-026'> jdg_026 : LaunchDecision { doc /* Pre-Tanking Mission Management Team Meeting（12:10  */ :>> decisionDate = "2003-01-16"; :>> forum = "Pre-Tanking Mission Management Team Meeting（12:10 a.m.、議長: Acting Manager of Launch Integration）"; :>> scope = "打上げ・飛行"; :>> docYear = "2003"; }
    part <'JDG-027'> jdg_027 : LaunchDecision { doc /* Launch Mission Management Team の GO/NO-GO poll（T-9 */ :>> decisionDate = "2003-01-16"; :>> forum = "Launch Mission Management Team の GO/NO-GO poll（T-9 分）"; :>> scope = "打上げ・飛行"; :>> docYear = "2003"; }
    part <'JDG-028'> jdg_028 : LaunchDecision { doc /* Mission Management Team の 8:00 a.m. meeting（Flight */ :>> decisionDate = "2003-01-24"; :>> forum = "Mission Management Team の 8:00 a.m. meeting（Flight Day Nine）"; :>> scope = "打上げ・飛行"; :>> docYear = "2003"; }
    part <'JDG-029'> jdg_029 : LaunchDecision { doc /* Mission Control Center（de-orbit の GO/NO-GO poll、8: */ :>> decisionDate = "2003-02-01"; :>> forum = "Mission Control Center（de-orbit の GO/NO-GO poll、8:00 a.m. 過ぎ）"; :>> scope = "打上げ・飛行"; :>> docYear = "2003"; }
    part <'JDG-030'> jdg_030 : LaunchDecision { doc /* Program Requirements Control Board（STS-112 の帰還後の会議 */ :>> decisionDate = ""; :>> forum = "Program Requirements Control Board（STS-112 の帰還後の会議）"; :>> scope = "打上げ・飛行"; :>> docYear = "2003"; }
    part <'JDG-031'> jdg_031 : LaunchDecision { doc /* STS-113 Flight Readiness Review（Associate Administ */ :>> decisionDate = "2002-10-31"; :>> forum = "STS-113 Flight Readiness Review（Associate Administrator for Safety and Mission Assurance が brief を s"; :>> scope = "打上げ・飛行"; :>> docYear = "2003"; }
    part <'JDG-032'> jdg_032 : LaunchDecision { doc /* STS-27R の Flight Day Two（Mission Control） */ :>> decisionDate = ""; :>> forum = "STS-27R の Flight Day Two（Mission Control）"; :>> scope = "打上げ・飛行"; :>> docYear = "2003"; }
    part <'JDG-033'> jdg_033 : LaunchDecision { doc /* Mission Evaluation Room manager の log（4:28 p.m.、電話 */ :>> decisionDate = "2003-01-17"; :>> forum = "Mission Evaluation Room manager の log（4:28 p.m.、電話の連絡）"; :>> scope = "打上げ・飛行"; :>> docYear = "2003"; }
    part <'JDG-034'> jdg_034 : LaunchDecision { doc /* Debris Assessment Team の first formal meeting（Flig */ :>> decisionDate = "2003-01-21"; :>> forum = "Debris Assessment Team の first formal meeting（Flight Day Six）"; :>> scope = "打上げ・飛行"; :>> docYear = "2003"; }
    part <'JDG-035'> jdg_035 : LaunchDecision { doc /* NASA の Department of Defense liaison officer から US */ :>> decisionDate = "2003-01-22"; :>> forum = "NASA の Department of Defense liaison officer から USSTRATCOM への電話（8:30 a.m.）"; :>> scope = "打上げ・飛行"; :>> docYear = "2003"; }
    part <'JDG-036'> jdg_036 : LaunchDecision { doc /* Mission Evaluation Room の console log の記録（10:37 a. */ :>> decisionDate = "2003-01-22"; :>> forum = "Mission Evaluation Room の console log の記録（10:37 a.m.）"; :>> scope = "打上げ・飛行"; :>> docYear = "2003"; }
    part <'JDG-037'> jdg_037 : LaunchDecision { doc /* Flight Director の e-mail（Flight Day Eight） */ :>> decisionDate = "2003-01-23"; :>> forum = "Flight Director の e-mail（Flight Day Eight）"; :>> scope = "打上げ・飛行"; :>> docYear = "2003"; }
    part <'JDG-038'> jdg_038 : LaunchDecision { doc /* 電話（Mission Operations Directorate の代表と Debris Asse */ :>> decisionDate = "2003-01-23"; :>> forum = "電話（Mission Operations Directorate の代表と Debris Assessment Team の NASA Co-Chair）"; :>> scope = "打上げ・飛行"; :>> docYear = "2003"; }
    part <'JDG-039'> jdg_039 : LaunchDecision { doc /* Memorandum for the Record に記された会話 */ :>> decisionDate = "2003-01-29"; :>> forum = "Memorandum for the Record に記された会話"; :>> scope = "打上げ・飛行"; :>> docYear = "2003"; }
    part <'JDG-040'> jdg_040 : LaunchDecision { doc /* Program Requirements Control Board (PRCB) */ :>> decisionDate = "2004-01 (技術の提示。承認の日付は本文に無い)"; :>> forum = "Program Requirements Control Board (PRCB)"; :>> scope = "プログラム管理"; :>> docYear = "2005"; }
    part <'JDG-041'> jdg_041 : LaunchDecision { doc /* Space Shuttle Program Requirements Change Board */ :>> decisionDate = "2003-09-11"; :>> forum = "Space Shuttle Program Requirements Change Board"; :>> scope = "プログラム管理"; :>> docYear = "2005"; }
    part <'JDG-042'> jdg_042 : LaunchDecision { doc /* Space Flight Leadership Council (SFLC) */ :>> decisionDate = "2004-06-09"; :>> forum = "Space Flight Leadership Council (SFLC)"; :>> scope = "プログラム管理"; :>> docYear = "2005"; }
    part <'JDG-043'> jdg_043 : LaunchDecision { doc /* Space Flight Leadership Council (SFLC) */ :>> decisionDate = ""; :>> forum = "Space Flight Leadership Council (SFLC)"; :>> scope = "プログラム管理"; :>> docYear = "2005"; }
    part <'JDG-044'> jdg_044 : LaunchDecision { doc /* Space Shuttle Program (PRCB Directive S062246) */ :>> decisionDate = "2004-08-27"; :>> forum = "Space Shuttle Program (PRCB Directive S062246)"; :>> scope = "プログラム管理"; :>> docYear = "2005"; }
    part <'JDG-045'> jdg_045 : LaunchDecision { doc /* Program DCR at KSC */ :>> decisionDate = "2005-04-19"; :>> forum = "Program DCR at KSC"; :>> scope = "プログラム管理"; :>> docYear = "2005"; }
    part <'JDG-046'> jdg_046 : LaunchDecision { doc /* Ascent/Entry Flight Techniques Panel (A/E FTP) */ :>> decisionDate = "2006-07-28"; :>> forum = "Ascent/Entry Flight Techniques Panel (A/E FTP)"; :>> scope = "飛行前の運用規則"; :>> docYear = "2006"; }
    part <'JDG-047'> jdg_047 : LaunchDecision { doc /* JPRCB */ :>> decisionDate = "2006-07-31"; :>> forum = "JPRCB"; :>> scope = "飛行前の運用規則"; :>> docYear = "2006"; }
    part <'JDG-048'> jdg_048 : LaunchDecision { doc /* meeting of DS and DM with DA8 */ :>> decisionDate = ""; :>> forum = "meeting of DS and DM with DA8"; :>> scope = "打上げ・飛行"; :>> docYear = "2008"; }
    part <'JDG-049'> jdg_049 : LaunchDecision { doc /* OPO */ :>> decisionDate = "2008-08-18 (本文は Monday August 18)"; :>> forum = "OPO"; :>> scope = "打上げ・飛行"; :>> docYear = "2008"; }
    part <'JDG-050'> jdg_050 : LaunchDecision { doc /* PRCB */ :>> decisionDate = ""; :>> forum = "PRCB"; :>> scope = "打上げ・飛行"; :>> docYear = "2008"; }
    part <'JDG-051'> jdg_051 : LaunchDecision { doc /* MOD FRR, Info Only item (S-MIA Diode) */ :>> decisionDate = ""; :>> forum = "MOD FRR, Info Only item (S-MIA Diode)"; :>> scope = "打上げ・飛行"; :>> docYear = "2009"; }
    part <'CFR-01'> cfr_01 : CofrTable { doc /* STS-119 */ :>> flight = "STS-119"; :>> greenCount = 158; :>> naCount = 42; }
    part <'CFR-02'> cfr_02 : CofrTable { doc /* STS-125 */ :>> flight = "STS-125"; :>> greenCount = 158; :>> naCount = 42; }
    part <'CFR-03'> cfr_03 : CofrTable { doc /* STS-400 */ :>> flight = "STS-400"; :>> greenCount = 157; :>> naCount = 43; }
}
