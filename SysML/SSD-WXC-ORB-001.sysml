// SysML v2 テキスト：天候基準定義書（飛行規則と雷の基準の数値つきの規則）
// SSD-WXC-ORB-001 天候基準定義書（飛行規則と雷の基準の数値つきの規則） の表から生成（lib/build_docs_de.py・rev_de/wxdata.py）。根拠の頁は SSD-WXC-ORB-001 にある。
package SSD_WXC_ORB_001 {
    doc /* SSD-WXC-ORB-001 天候基準定義書（飛行規則と雷の基準の数値つきの規則）。天候の数値つきの規則を part def WeatherRule の使用として持つ。版・規則の ID・項目・場面・場所・比較・値・単位・条件・数え方は属性。要求への関係（導出・充足・検証）は張らず、トレースの外に置く。 */
    private import ScalarValues::*;
    part def WeatherRule {
        doc /* 飛行規則・雷の基準の、天候・自然環境の数値の限界の記録。値は本文のとおりで換算しない。判定は付けない。版はその時代の基準で、他の時期の飛行には当てはめない */
        attribute rulebookEdition : String;
        attribute ruleId : String;
        attribute wxParameter : String;
        attribute wxScene : String;
        attribute wxSite : String;
        attribute wxComparison : String;
        attribute limitValue : ScalarValues::Real [0..1];
        attribute limitValueHigh : ScalarValues::Real [0..1];
        attribute limitUnit : String;
        attribute ruleCondition : String;
        attribute isCounted : ScalarValues::Boolean;
    }
    part <'WXC-001'> wxc_001 : WeatherRule { doc /* 1996 A2.1.1-6A.2 CEILING */ :>> rulebookEdition = "1996"; :>> ruleId = "A2.1.1-6A.2"; :>> wxParameter = "ceiling"; :>> wxScene = "landing_eom"; :>> wxSite = "any"; :>> wxComparison = "other"; :>> limitValue = 10.0; :>> limitUnit = "K ft"; :>> ruleCondition = "WX recon must confirm PAPIs/aimpoint visible from 8K (5K for RTLS, TAL) to prefl"; :>> isCounted = false; }
    part <'WXC-002'> wxc_002 : WeatherRule { doc /* 1996 A2.1.1-6A.2 VISIBILITY */ :>> rulebookEdition = "1996"; :>> ruleId = "A2.1.1-6A.2"; :>> wxParameter = "visibility"; :>> wxScene = "landing_eom"; :>> wxSite = "any"; :>> wxComparison = "other"; :>> limitValue = 7.0; :>> limitUnit = "SM"; :>> ruleCondition = "WX recon must confirm PAPIs/aimpoint visible when visibility is less than 7 stat"; :>> isCounted = false; }
    part <'WXC-003'> wxc_003 : WeatherRule { doc /* 1996 A2.1.1-6A.2 CEILING */ :>> rulebookEdition = "1996"; :>> ruleId = "A2.1.1-6A.2"; :>> wxParameter = "ceiling"; :>> wxScene = "landing_eom"; :>> wxSite = "any"; :>> wxComparison = "other"; :>> limitValue = 8.0; :>> limitUnit = "K ft"; :>> ruleCondition = "WX recon GO/NO-GO recommendation is required for ceilings at or below 8K ft; not"; :>> isCounted = false; }
    part <'WXC-004'> wxc_004 : WeatherRule { doc /* 1996 A2.1.1-6A.3 CLOUD LAYERS BELOW 8K FT, COVERAGE */ :>> rulebookEdition = "1996"; :>> ruleId = "A2.1.1-6A.3"; :>> wxParameter = "cloud_cover"; :>> wxScene = "landing_eom"; :>> wxSite = "KSC"; :>> wxComparison = "range"; :>> limitValue = 2.0; :>> limitValueHigh = 4.0; :>> limitUnit = "eighths of sky coverage"; :>> ruleCondition = "KSC EOM only; cloud layers below 8K ft reported by ground weather observers or w"; :>> isCounted = true; }
    part <'WXC-005'> wxc_005 : WeatherRule { doc /* 1996 A2.1.1-6C TSTORM (INCLUDING ATTACHED NONTRANSPAREN */ :>> rulebookEdition = "1996"; :>> ruleId = "A2.1.1-6C"; :>> wxParameter = "thunderstorm"; :>> wxScene = "landing_rtls"; :>> wxSite = "any"; :>> wxComparison = "min"; :>> limitValue = 20.0; :>> limitUnit = "NM"; :>> ruleCondition = "TSTORM (INCLUDING ATTACHED NONTRANSPARENT ANVILS), AND LIGHTNING; prelaunch RTLS"; :>> isCounted = true; }
    part <'WXC-006'> wxc_006 : WeatherRule { doc /* 1996 A2.1.1-6C TSTORM (INCLUDING ATTACHED NONTRANSPAREN */ :>> rulebookEdition = "1996"; :>> ruleId = "A2.1.1-6C"; :>> wxParameter = "thunderstorm"; :>> wxScene = "landing_rtls"; :>> wxSite = "any"; :>> wxComparison = "min"; :>> limitValue = 10.0; :>> limitUnit = "NM"; :>> ruleCondition = "TSTORM (INCLUDING ATTACHED NONTRANSPARENT ANVILS), AND LIGHTNING; prelaunch RTLS"; :>> isCounted = true; }
    part <'WXC-007'> wxc_007 : WeatherRule { doc /* 1996 A2.1.1-6C TSTORM (INCLUDING ATTACHED NONTRANSPAREN */ :>> rulebookEdition = "1996"; :>> ruleId = "A2.1.1-6C"; :>> wxParameter = "thunderstorm"; :>> wxScene = "landing_eom"; :>> wxSite = "any"; :>> wxComparison = "min"; :>> limitValue = 30.0; :>> limitUnit = "NM"; :>> ruleCondition = "TSTORM (INCLUDING ATTACHED NONTRANSPARENT ANVILS), AND LIGHTNING; predeorbit EOM"; :>> isCounted = true; }
    part <'WXC-008'> wxc_008 : WeatherRule { doc /* 1996 A2.1.1-6C TSTORM (INCLUDING ATTACHED NONTRANSPAREN */ :>> rulebookEdition = "1996"; :>> ruleId = "A2.1.1-6C"; :>> wxParameter = "thunderstorm"; :>> wxScene = "landing_eom"; :>> wxSite = "any"; :>> wxComparison = "min"; :>> limitValue = 20.0; :>> limitUnit = "NM"; :>> ruleCondition = "TSTORM (INCLUDING ATTACHED NONTRANSPARENT ANVILS), AND LIGHTNING; predeorbit EOM"; :>> isCounted = true; }
    part <'WXC-009'> wxc_009 : WeatherRule { doc /* 1996 A2.1.1-6C TSTORM (INCLUDING ATTACHED NONTRANSPAREN */ :>> rulebookEdition = "1996"; :>> ruleId = "A2.1.1-6C"; :>> wxParameter = "thunderstorm"; :>> wxScene = "landing_aoa"; :>> wxSite = "any"; :>> wxComparison = "min"; :>> limitValue = 15.0; :>> limitUnit = "NM"; :>> ruleCondition = "TSTORM (INCLUDING ATTACHED NONTRANSPARENT ANVILS), AND LIGHTNING; prelaunch AOA;"; :>> isCounted = true; }
    part <'WXC-010'> wxc_010 : WeatherRule { doc /* 1996 A2.1.1-6C TSTORM (INCLUDING ATTACHED NONTRANSPAREN */ :>> rulebookEdition = "1996"; :>> ruleId = "A2.1.1-6C"; :>> wxParameter = "thunderstorm"; :>> wxScene = "landing_aoa"; :>> wxSite = "any"; :>> wxComparison = "min"; :>> limitValue = 5.0; :>> limitUnit = "NM"; :>> ruleCondition = "TSTORM (INCLUDING ATTACHED NONTRANSPARENT ANVILS), AND LIGHTNING; prelaunch AOA;"; :>> isCounted = true; }
    part <'WXC-011'> wxc_011 : WeatherRule { doc /* 1996 A2.1.1-6C TSTORM (INCLUDING ATTACHED NONTRANSPAREN */ :>> rulebookEdition = "1996"; :>> ruleId = "A2.1.1-6C"; :>> wxParameter = "thunderstorm"; :>> wxScene = "other"; :>> wxSite = "any"; :>> wxComparison = "min"; :>> limitValue = 2.0; :>> limitUnit = "NM"; :>> ruleCondition = "TSTORM (INCLUDING ATTACHED NONTRANSPARENT ANVILS), AND LIGHTNING; vertical clear"; :>> isCounted = false; }
    part <'WXC-012'> wxc_012 : WeatherRule { doc /* 1996 A2.1.1-6C DETACHED NONTRANSPARENT ANVIL < 3 HRS OL */ :>> rulebookEdition = "1996"; :>> ruleId = "A2.1.1-6C"; :>> wxParameter = "thunderstorm"; :>> wxScene = "landing_rtls"; :>> wxSite = "any"; :>> wxComparison = "min"; :>> limitValue = 15.0; :>> limitUnit = "NM"; :>> ruleCondition = "DETACHED NONTRANSPARENT ANVIL < 3 HRS OLD; prelaunch RTLS and TAL (column lists "; :>> isCounted = true; }
    part <'WXC-013'> wxc_013 : WeatherRule { doc /* 1996 A2.1.1-6C DETACHED NONTRANSPARENT ANVIL < 3 HRS OL */ :>> rulebookEdition = "1996"; :>> ruleId = "A2.1.1-6C"; :>> wxParameter = "thunderstorm"; :>> wxScene = "landing_rtls"; :>> wxSite = "any"; :>> wxComparison = "min"; :>> limitValue = 5.0; :>> limitUnit = "NM"; :>> ruleCondition = "DETACHED NONTRANSPARENT ANVIL < 3 HRS OLD; prelaunch RTLS and TAL (column lists "; :>> isCounted = true; }
    part <'WXC-014'> wxc_014 : WeatherRule { doc /* 1996 A2.1.1-6C DETACHED NONTRANSPARENT ANVIL < 3 HRS OL */ :>> rulebookEdition = "1996"; :>> ruleId = "A2.1.1-6C"; :>> wxParameter = "thunderstorm"; :>> wxScene = "landing_eom"; :>> wxSite = "any"; :>> wxComparison = "min"; :>> limitValue = 20.0; :>> limitUnit = "NM"; :>> ruleCondition = "DETACHED NONTRANSPARENT ANVIL < 3 HRS OLD; predeorbit EOM and daily PLS (column "; :>> isCounted = true; }
    part <'WXC-015'> wxc_015 : WeatherRule { doc /* 1996 A2.1.1-6C DETACHED NONTRANSPARENT ANVIL < 3 HRS OL */ :>> rulebookEdition = "1996"; :>> ruleId = "A2.1.1-6C"; :>> wxParameter = "thunderstorm"; :>> wxScene = "landing_eom"; :>> wxSite = "any"; :>> wxComparison = "min"; :>> limitValue = 10.0; :>> limitUnit = "NM"; :>> ruleCondition = "DETACHED NONTRANSPARENT ANVIL < 3 HRS OLD; predeorbit EOM and daily PLS (column "; :>> isCounted = true; }
    part <'WXC-016'> wxc_016 : WeatherRule { doc /* 1996 A2.1.1-6C DETACHED NONTRANSPARENT ANVIL < 3 HRS OL */ :>> rulebookEdition = "1996"; :>> ruleId = "A2.1.1-6C"; :>> wxParameter = "thunderstorm"; :>> wxScene = "landing_aoa"; :>> wxSite = "any"; :>> wxComparison = "min"; :>> limitValue = 15.0; :>> limitUnit = "NM"; :>> ruleCondition = "DETACHED NONTRANSPARENT ANVIL < 3 HRS OLD; prelaunch AOA; radial distance from t"; :>> isCounted = true; }
    part <'WXC-017'> wxc_017 : WeatherRule { doc /* 1996 A2.1.1-6C DETACHED NONTRANSPARENT ANVIL < 3 HRS OL */ :>> rulebookEdition = "1996"; :>> ruleId = "A2.1.1-6C"; :>> wxParameter = "thunderstorm"; :>> wxScene = "landing_aoa"; :>> wxSite = "any"; :>> wxComparison = "min"; :>> limitValue = 5.0; :>> limitUnit = "NM"; :>> ruleCondition = "DETACHED NONTRANSPARENT ANVIL < 3 HRS OLD; prelaunch AOA; lateral distance along"; :>> isCounted = true; }
    part <'WXC-018'> wxc_018 : WeatherRule { doc /* 1996 A2.1.1-6C DETACHED NONTRANSPARENT ANVIL < 3 HRS OL */ :>> rulebookEdition = "1996"; :>> ruleId = "A2.1.1-6C"; :>> wxParameter = "thunderstorm"; :>> wxScene = "other"; :>> wxSite = "any"; :>> wxComparison = "min"; :>> limitValue = 2.0; :>> limitUnit = "NM"; :>> ruleCondition = "DETACHED NONTRANSPARENT ANVIL < 3 HRS OLD; vertical clearance from the top of th"; :>> isCounted = false; }
    part <'WXC-019'> wxc_019 : WeatherRule { doc /* 1996 A2.1.1-6C PRECIPITATION * - RADIAL FROM CENTER OF  */ :>> rulebookEdition = "1996"; :>> ruleId = "A2.1.1-6C"; :>> wxParameter = "precipitation"; :>> wxScene = "landing_rtls"; :>> wxSite = "any"; :>> wxComparison = "min"; :>> limitValue = 20.0; :>> limitUnit = "NM"; :>> ruleCondition = "PRECIPITATION *; prelaunch RTLS and TAL (column lists both; scene = first listed"; :>> isCounted = true; }
    part <'WXC-020'> wxc_020 : WeatherRule { doc /* 1996 A2.1.1-6C PRECIPITATION * - LATERAL ALONG APPROACH */ :>> rulebookEdition = "1996"; :>> ruleId = "A2.1.1-6C"; :>> wxParameter = "precipitation"; :>> wxScene = "landing_rtls"; :>> wxSite = "any"; :>> wxComparison = "min"; :>> limitValue = 10.0; :>> limitUnit = "NM"; :>> ruleCondition = "PRECIPITATION *; prelaunch RTLS and TAL (column lists both; scene = first listed"; :>> isCounted = true; }
    part <'WXC-021'> wxc_021 : WeatherRule { doc /* 1996 A2.1.1-6C PRECIPITATION * - RADIAL FROM CENTER OF  */ :>> rulebookEdition = "1996"; :>> ruleId = "A2.1.1-6C"; :>> wxParameter = "precipitation"; :>> wxScene = "landing_eom"; :>> wxSite = "any"; :>> wxComparison = "min"; :>> limitValue = 30.0; :>> limitUnit = "NM"; :>> ruleCondition = "PRECIPITATION *; predeorbit EOM and daily PLS (column lists both; scene = first "; :>> isCounted = true; }
    part <'WXC-022'> wxc_022 : WeatherRule { doc /* 1996 A2.1.1-6C PRECIPITATION * - LATERAL ALONG APPROACH */ :>> rulebookEdition = "1996"; :>> ruleId = "A2.1.1-6C"; :>> wxParameter = "precipitation"; :>> wxScene = "landing_eom"; :>> wxSite = "any"; :>> wxComparison = "min"; :>> limitValue = 20.0; :>> limitUnit = "NM"; :>> ruleCondition = "PRECIPITATION *; predeorbit EOM and daily PLS (column lists both; scene = first "; :>> isCounted = true; }
    part <'WXC-023'> wxc_023 : WeatherRule { doc /* 1996 A2.1.1-6C PRECIPITATION * - RADIAL FROM CENTER OF  */ :>> rulebookEdition = "1996"; :>> ruleId = "A2.1.1-6C"; :>> wxParameter = "precipitation"; :>> wxScene = "landing_aoa"; :>> wxSite = "any"; :>> wxComparison = "min"; :>> limitValue = 15.0; :>> limitUnit = "NM"; :>> ruleCondition = "PRECIPITATION *; prelaunch AOA; radial distance from the center of the prime run"; :>> isCounted = true; }
    part <'WXC-024'> wxc_024 : WeatherRule { doc /* 1996 A2.1.1-6C PRECIPITATION * - LATERAL ALONG APPROACH */ :>> rulebookEdition = "1996"; :>> ruleId = "A2.1.1-6C"; :>> wxParameter = "precipitation"; :>> wxScene = "landing_aoa"; :>> wxSite = "any"; :>> wxComparison = "min"; :>> limitValue = 5.0; :>> limitUnit = "NM"; :>> ruleCondition = "PRECIPITATION *; prelaunch AOA; lateral distance along the approach path out to "; :>> isCounted = true; }
    part <'WXC-025'> wxc_025 : WeatherRule { doc /* 1996 A2.1.1-6C PRECIPITATION * - VERTICAL FROM TOP OF C */ :>> rulebookEdition = "1996"; :>> ruleId = "A2.1.1-6C"; :>> wxParameter = "precipitation"; :>> wxScene = "other"; :>> wxSite = "any"; :>> wxComparison = "min"; :>> limitValue = 2.0; :>> limitUnit = "NM"; :>> ruleCondition = "PRECIPITATION *; vertical clearance from the top of the cloud/thunderstorm to th"; :>> isCounted = false; }
    part <'WXC-026'> wxc_026 : WeatherRule { doc /* 1996 A2.1.1-6C LATERAL ALONG APPROACH PATH (NM) */ :>> rulebookEdition = "1996"; :>> ruleId = "A2.1.1-6C"; :>> wxParameter = "other"; :>> wxScene = "other"; :>> wxSite = "any"; :>> wxComparison = "min"; :>> limitValue = 0.0; :>> limitUnit = "NM"; :>> ruleCondition = "cumulus clouds produced by smoke/fire, up to 1 hr after detaching; strict '>0'; "; :>> isCounted = false; }
    part <'WXC-027'> wxc_027 : WeatherRule { doc /* 1996 A2.1.1-6C.4.a SHOWER COVERAGE */ :>> rulebookEdition = "1996"; :>> ruleId = "A2.1.1-6C.4.a"; :>> wxParameter = "precipitation"; :>> wxScene = "landing_rtls"; :>> wxSite = "any"; :>> wxComparison = "max"; :>> limitValue = 10.0; :>> limitUnit = "percent of the area within 20 "; :>> ruleCondition = "RTLS; rain showers (excluding thunderstorms) within the limits are acceptable if"; :>> isCounted = true; }
    part <'WXC-028'> wxc_028 : WeatherRule { doc /* 1996 A2.1.1-6C.4.c CLOUD-TOP TEMPERATURE LEVEL (+5 DEG C) */ :>> rulebookEdition = "1996"; :>> ruleId = "A2.1.1-6C.4.c"; :>> wxParameter = "temperature"; :>> wxScene = "landing_rtls"; :>> wxSite = "any"; :>> wxComparison = "max"; :>> limitValue = 5.0; :>> limitUnit = "deg C"; :>> ruleCondition = "RTLS shower exception; tops of clouds containing precipitation do not exceed the"; :>> isCounted = true; }
    part <'WXC-029'> wxc_029 : WeatherRule { doc /* 1996 A2.1.1-6C.4.c CLOUD-TOP TEMPERATURE LEVEL (-10 DEG C) */ :>> rulebookEdition = "1996"; :>> ruleId = "A2.1.1-6C.4.c"; :>> wxParameter = "temperature"; :>> wxScene = "landing_rtls"; :>> wxSite = "any"; :>> wxComparison = "max"; :>> limitValue = -10.0; :>> limitUnit = "deg C"; :>> ruleCondition = "RTLS shower exception; clouds have not exceeded the -10 deg C level within 2.5 h"; :>> isCounted = true; }
    part <'WXC-030'> wxc_030 : WeatherRule { doc /* 1996 A2.1.1-6C.4.d PRECIPITATION INTENSITY */ :>> rulebookEdition = "1996"; :>> ruleId = "A2.1.1-6C.4.d"; :>> wxParameter = "precipitation"; :>> wxScene = "landing_rtls"; :>> wxSite = "any"; :>> wxComparison = "max"; :>> limitValue = 30.0; :>> limitUnit = "dBZ"; :>> ruleCondition = "RTLS shower exception; precipitation is light (less than 30 dBZ) at all levels w"; :>> isCounted = true; }
    part <'WXC-031'> wxc_031 : WeatherRule { doc /* 1996 A2.1.1-6C.4.e SHOWER VERTICAL CLEARANCE */ :>> rulebookEdition = "1996"; :>> ruleId = "A2.1.1-6C.4.e"; :>> wxParameter = "precipitation"; :>> wxScene = "landing_rtls"; :>> wxSite = "any"; :>> wxComparison = "min"; :>> limitValue = 2.0; :>> limitUnit = "NM"; :>> ruleCondition = "RTLS; for any shower within 20 miles of the SLF that exceeds paragraph 4.c or 4."; :>> isCounted = true; }
    part <'WXC-032'> wxc_032 : WeatherRule { doc /* 1996 A2.1.1-6C.4.e SHOWER LATERAL CLEARANCE */ :>> rulebookEdition = "1996"; :>> ruleId = "A2.1.1-6C.4.e"; :>> wxParameter = "precipitation"; :>> wxScene = "landing_rtls"; :>> wxSite = "any"; :>> wxComparison = "min"; :>> limitValue = 10.0; :>> limitUnit = "NM"; :>> ruleCondition = "RTLS; for any shower within 20 miles of the SLF that exceeds paragraph 4.c or 4."; :>> isCounted = true; }
    part <'WXC-033'> wxc_033 : WeatherRule { doc /* 1996 A2.1.1-6C.5 CUMULUS CLOUD ATTACHED TO A FIRE SMOKE P */ :>> rulebookEdition = "1996"; :>> ruleId = "A2.1.1-6C.5"; :>> wxParameter = "other"; :>> wxScene = "other"; :>> wxSite = "any"; :>> wxComparison = "min"; :>> limitValue = 1.0; :>> limitUnit = "hour"; :>> ruleCondition = "the orbiter shall not penetrate a cumulus cloud attached to a smoke plume produc"; :>> isCounted = true; }
    part <'WXC-034'> wxc_034 : WeatherRule { doc /* 1996 A2.1.1-6A CEILING */ :>> rulebookEdition = "1996"; :>> ruleId = "A2.1.1-6A"; :>> wxParameter = "ceiling"; :>> wxScene = "landing_eom"; :>> wxSite = "any"; :>> wxComparison = "min"; :>> limitValue = 10.0; :>> limitUnit = "K ft"; :>> ruleCondition = "concrete runway; day; MLS column (redundant / single string / none) is not recov"; :>> isCounted = true; }
    part <'WXC-035'> wxc_035 : WeatherRule { doc /* 1996 A2.1.1-6A VISIBILITY */ :>> rulebookEdition = "1996"; :>> ruleId = "A2.1.1-6A"; :>> wxParameter = "visibility"; :>> wxScene = "landing_eom"; :>> wxSite = "any"; :>> wxComparison = "min"; :>> limitValue = 7.0; :>> limitUnit = "SM"; :>> ruleCondition = "concrete runway; day; MLS column (redundant / single string / none) is not recov"; :>> isCounted = true; }
    part <'WXC-036'> wxc_036 : WeatherRule { doc /* 1996 A2.1.1-6A CEILING */ :>> rulebookEdition = "1996"; :>> ruleId = "A2.1.1-6A"; :>> wxParameter = "ceiling"; :>> wxScene = "landing_eom"; :>> wxSite = "any"; :>> wxComparison = "min"; :>> limitValue = 8.0; :>> limitUnit = "K ft"; :>> ruleCondition = "concrete runway; value printed after the NIGHT row; MLS column (redundant / sing"; :>> isCounted = false; }
    part <'WXC-037'> wxc_037 : WeatherRule { doc /* 1996 A2.1.1-6A VISIBILITY */ :>> rulebookEdition = "1996"; :>> ruleId = "A2.1.1-6A"; :>> wxParameter = "visibility"; :>> wxScene = "landing_eom"; :>> wxSite = "any"; :>> wxComparison = "min"; :>> limitValue = 5.0; :>> limitUnit = "SM"; :>> ruleCondition = "concrete runway; value printed after the NIGHT row; MLS column (redundant / sing"; :>> isCounted = false; }
    part <'WXC-038'> wxc_038 : WeatherRule { doc /* 1996 A2.1.1-6A CEILING */ :>> rulebookEdition = "1996"; :>> ruleId = "A2.1.1-6A"; :>> wxParameter = "ceiling"; :>> wxScene = "landing_eom"; :>> wxSite = "any"; :>> wxComparison = "min"; :>> limitValue = 10.0; :>> limitUnit = "K ft"; :>> ruleCondition = "lakebed runway; day; WX recon required; MLS column (redundant / single string / "; :>> isCounted = true; }
    part <'WXC-039'> wxc_039 : WeatherRule { doc /* 1996 A2.1.1-6A VISIBILITY */ :>> rulebookEdition = "1996"; :>> ruleId = "A2.1.1-6A"; :>> wxParameter = "visibility"; :>> wxScene = "landing_eom"; :>> wxSite = "any"; :>> wxComparison = "min"; :>> limitValue = 7.0; :>> limitUnit = "SM"; :>> ruleCondition = "lakebed runway; day; WX recon required; MLS column (redundant / single string / "; :>> isCounted = true; }
    part <'WXC-040'> wxc_040 : WeatherRule { doc /* 1996 A2.1.1-6A CEILING */ :>> rulebookEdition = "1996"; :>> ruleId = "A2.1.1-6A"; :>> wxParameter = "ceiling"; :>> wxScene = "landing_eom"; :>> wxSite = "any"; :>> wxComparison = "min"; :>> limitValue = 15.0; :>> limitUnit = "K ft"; :>> ruleCondition = "lakebed runway; night; MLS column (redundant / single string / none) is not reco"; :>> isCounted = true; }
    part <'WXC-041'> wxc_041 : WeatherRule { doc /* 1996 A2.1.1-6A VISIBILITY */ :>> rulebookEdition = "1996"; :>> ruleId = "A2.1.1-6A"; :>> wxParameter = "visibility"; :>> wxScene = "landing_eom"; :>> wxSite = "any"; :>> wxComparison = "min"; :>> limitValue = 7.0; :>> limitUnit = "SM"; :>> ruleCondition = "lakebed runway; night; MLS column (redundant / single string / none) is not reco"; :>> isCounted = true; }
    part <'WXC-042'> wxc_042 : WeatherRule { doc /* 1996 A2.1.1-6A CEILING */ :>> rulebookEdition = "1996"; :>> ruleId = "A2.1.1-6A"; :>> wxParameter = "ceiling"; :>> wxScene = "landing_rtls"; :>> wxSite = "any"; :>> wxComparison = "min"; :>> limitValue = 5.0; :>> limitUnit = "K ft"; :>> ruleCondition = "RTLS; concrete runway; day; MLS column (redundant / single string / none) is not"; :>> isCounted = true; }
    part <'WXC-043'> wxc_043 : WeatherRule { doc /* 1996 A2.1.1-6A VISIBILITY */ :>> rulebookEdition = "1996"; :>> ruleId = "A2.1.1-6A"; :>> wxParameter = "visibility"; :>> wxScene = "landing_rtls"; :>> wxSite = "any"; :>> wxComparison = "min"; :>> limitValue = 4.0; :>> limitUnit = "SM"; :>> ruleCondition = "RTLS; concrete runway; day; MLS column (redundant / single string / none) is not"; :>> isCounted = true; }
    part <'WXC-044'> wxc_044 : WeatherRule { doc /* 1996 A2.1.1-6A CEILING */ :>> rulebookEdition = "1996"; :>> ruleId = "A2.1.1-6A"; :>> wxParameter = "ceiling"; :>> wxScene = "landing_tal"; :>> wxSite = "any"; :>> wxComparison = "min"; :>> limitValue = 5.0; :>> limitUnit = "K ft"; :>> ruleCondition = "TAL; concrete runway; day; the table prints '>5/5' (strict) for TAL while RTLS i"; :>> isCounted = true; }
    part <'WXC-045'> wxc_045 : WeatherRule { doc /* 1996 A2.1.1-6A VISIBILITY */ :>> rulebookEdition = "1996"; :>> ruleId = "A2.1.1-6A"; :>> wxParameter = "visibility"; :>> wxScene = "landing_tal"; :>> wxSite = "any"; :>> wxComparison = "min"; :>> limitValue = 5.0; :>> limitUnit = "SM"; :>> ruleCondition = "TAL; concrete runway; day; the table prints '>5/5' (strict) for TAL while RTLS i"; :>> isCounted = true; }
    part <'WXC-046'> wxc_046 : WeatherRule { doc /* 1996 A2.1.1-6A CEILING */ :>> rulebookEdition = "1996"; :>> ruleId = "A2.1.1-6A"; :>> wxParameter = "ceiling"; :>> wxScene = "landing_rtls"; :>> wxSite = "any"; :>> wxComparison = "min"; :>> limitValue = 10.0; :>> limitUnit = "K ft"; :>> ruleCondition = "RTLS and TAL; concrete runway; day; second value of the row (after '>5/5 TAL'); "; :>> isCounted = true; }
    part <'WXC-047'> wxc_047 : WeatherRule { doc /* 1996 A2.1.1-6A VISIBILITY */ :>> rulebookEdition = "1996"; :>> ruleId = "A2.1.1-6A"; :>> wxParameter = "visibility"; :>> wxScene = "landing_rtls"; :>> wxSite = "any"; :>> wxComparison = "min"; :>> limitValue = 7.0; :>> limitUnit = "SM"; :>> ruleCondition = "RTLS and TAL; concrete runway; day; second value of the row (after '>5/5 TAL'); "; :>> isCounted = true; }
    part <'WXC-048'> wxc_048 : WeatherRule { doc /* 1996 A2.1.1-6A CEILING */ :>> rulebookEdition = "1996"; :>> ruleId = "A2.1.1-6A"; :>> wxParameter = "ceiling"; :>> wxScene = "other"; :>> wxSite = "any"; :>> wxComparison = "min"; :>> limitValue = 0.0; :>> limitUnit = "K ft"; :>> ruleCondition = "ACLS/ECAL/ELS; zero/zero value; MLS column (redundant / single string / none) is"; :>> isCounted = false; }
    part <'WXC-049'> wxc_049 : WeatherRule { doc /* 1996 A2.1.1-6A VISIBILITY */ :>> rulebookEdition = "1996"; :>> ruleId = "A2.1.1-6A"; :>> wxParameter = "visibility"; :>> wxScene = "other"; :>> wxSite = "any"; :>> wxComparison = "min"; :>> limitValue = 0.0; :>> limitUnit = "SM"; :>> ruleCondition = "ACLS/ECAL/ELS; zero/zero value; MLS column (redundant / single string / none) is"; :>> isCounted = false; }
    part <'WXC-050'> wxc_050 : WeatherRule { doc /* 1996 A2.1.1-6A CEILING */ :>> rulebookEdition = "1996"; :>> ruleId = "A2.1.1-6A"; :>> wxParameter = "ceiling"; :>> wxScene = "other"; :>> wxSite = "any"; :>> wxComparison = "min"; :>> limitValue = 8.0; :>> limitUnit = "K ft"; :>> ruleCondition = "ACLS/ECAL/ELS; second value of the row; MLS column (redundant / single string / "; :>> isCounted = false; }
    part <'WXC-051'> wxc_051 : WeatherRule { doc /* 1996 A2.1.1-6A VISIBILITY */ :>> rulebookEdition = "1996"; :>> ruleId = "A2.1.1-6A"; :>> wxParameter = "visibility"; :>> wxScene = "other"; :>> wxSite = "any"; :>> wxComparison = "min"; :>> limitValue = 5.0; :>> limitUnit = "SM"; :>> ruleCondition = "ACLS/ECAL/ELS; second value of the row; MLS column (redundant / single string / "; :>> isCounted = false; }
    part <'WXC-052'> wxc_052 : WeatherRule { doc /* 1996 A2.1.1-6A CEILING */ :>> rulebookEdition = "1996"; :>> ruleId = "A2.1.1-6A"; :>> wxParameter = "ceiling"; :>> wxScene = "deorbit"; :>> wxSite = "any"; :>> wxComparison = "min"; :>> limitValue = 10.0; :>> limitUnit = "K ft"; :>> ruleCondition = "predeorbit; one APU failed or attempt-two-APUs procedure"; :>> isCounted = true; }
    part <'WXC-053'> wxc_053 : WeatherRule { doc /* 1996 A2.1.1-6A VISIBILITY */ :>> rulebookEdition = "1996"; :>> ruleId = "A2.1.1-6A"; :>> wxParameter = "visibility"; :>> wxScene = "deorbit"; :>> wxSite = "any"; :>> wxComparison = "min"; :>> limitValue = 7.0; :>> limitUnit = "SM"; :>> ruleCondition = "predeorbit; one APU failed or attempt-two-APUs procedure"; :>> isCounted = true; }
    part <'WXC-054'> wxc_054 : WeatherRule { doc /* 1996 A2.1.1-6B CROSS PEAK (surface wind, knots) */ :>> rulebookEdition = "1996"; :>> ruleId = "A2.1.1-6B"; :>> wxParameter = "crosswind"; :>> wxScene = "landing_rtls"; :>> wxSite = "any"; :>> wxComparison = "max"; :>> limitValue = 15.0; :>> limitUnit = "knots"; :>> ruleCondition = "RTLS; peak crosswind; * requires an STA evaluation to 17 knots and a GO from the"; :>> isCounted = true; }
    part <'WXC-055'> wxc_055 : WeatherRule { doc /* 1996 A2.1.1-6B CROSS PEAK (surface wind, knots), footno */ :>> rulebookEdition = "1996"; :>> ruleId = "A2.1.1-6B"; :>> wxParameter = "crosswind"; :>> wxScene = "landing_rtls"; :>> wxSite = "any"; :>> wxComparison = "max"; :>> limitValue = 17.0; :>> limitUnit = "knots"; :>> ruleCondition = "RTLS; peak crosswind above 15 knots needs an STA evaluation up to 17 knots and a"; :>> isCounted = true; }
    part <'WXC-056'> wxc_056 : WeatherRule { doc /* 1996 A2.1.1-6B CROSS PEAK (surface wind, knots) */ :>> rulebookEdition = "1996"; :>> ruleId = "A2.1.1-6B"; :>> wxParameter = "crosswind"; :>> wxScene = "landing_eom"; :>> wxSite = "any"; :>> wxComparison = "max"; :>> limitValue = 15.0; :>> limitUnit = "knots"; :>> ruleCondition = "day; peak crosswind; the row lists EOM, TAL, AOA and daily PLS selection"; :>> isCounted = true; }
    part <'WXC-057'> wxc_057 : WeatherRule { doc /* 1996 A2.1.1-6B CROSS PEAK (surface wind, knots) */ :>> rulebookEdition = "1996"; :>> ruleId = "A2.1.1-6B"; :>> wxParameter = "crosswind"; :>> wxScene = "landing_eom"; :>> wxSite = "any"; :>> wxComparison = "max"; :>> limitValue = 12.0; :>> limitUnit = "knots"; :>> ruleCondition = "night; peak crosswind; the row lists EOM, TAL, AOA and daily PLS selection"; :>> isCounted = true; }
    part <'WXC-058'> wxc_058 : WeatherRule { doc /* 1996 A2.1.1-6B CROSS PEAK (surface wind, knots) */ :>> rulebookEdition = "1996"; :>> ruleId = "A2.1.1-6B"; :>> wxParameter = "crosswind"; :>> wxScene = "other"; :>> wxSite = "any"; :>> wxComparison = "range"; :>> limitValue = 10.0; :>> limitValueHigh = 15.0; :>> limitUnit = "knots"; :>> ruleCondition = "crosswind DTO; peak crosswind from at least 10 up to 15 knots"; :>> isCounted = true; }
    part <'WXC-059'> wxc_059 : WeatherRule { doc /* 1996 A2.1.1-6B CROSS PEAK (surface wind, knots) */ :>> rulebookEdition = "1996"; :>> ruleId = "A2.1.1-6B"; :>> wxParameter = "crosswind"; :>> wxScene = "other"; :>> wxSite = "any"; :>> wxComparison = "max"; :>> limitValue = 15.0; :>> limitUnit = "knots"; :>> ruleCondition = "nominal drag chute deploy; peak crosswind"; :>> isCounted = true; }
    part <'WXC-060'> wxc_060 : WeatherRule { doc /* 1996 A2.1.1-6B CROSS PEAK (surface wind, knots) */ :>> rulebookEdition = "1996"; :>> ruleId = "A2.1.1-6B"; :>> wxParameter = "crosswind"; :>> wxScene = "other"; :>> wxSite = "any"; :>> wxComparison = "max"; :>> limitValue = 12.0; :>> limitUnit = "knots"; :>> ruleCondition = "landing at or after the CDR's flight day 19 (table); the p102 rationale text say"; :>> isCounted = true; }
    part <'WXC-061'> wxc_061 : WeatherRule { doc /* 1996 A2.1.1-6B CROSS PEAK (surface wind, knots) */ :>> rulebookEdition = "1996"; :>> ruleId = "A2.1.1-6B"; :>> wxParameter = "crosswind"; :>> wxScene = "deorbit"; :>> wxSite = "any"; :>> wxComparison = "max"; :>> limitValue = 10.0; :>> limitUnit = "knots"; :>> ruleCondition = "predeorbit; one APU failed or attempt-2-APUs procedure; peak crosswind"; :>> isCounted = true; }
    part <'WXC-062'> wxc_062 : WeatherRule { doc /* 1996 A2.1.1-6B CROSS PEAK (surface wind, knots) */ :>> rulebookEdition = "1996"; :>> ruleId = "A2.1.1-6B"; :>> wxParameter = "crosswind"; :>> wxScene = "other"; :>> wxSite = "any"; :>> wxComparison = "max"; :>> limitValue = 15.0; :>> limitUnit = "knots"; :>> ruleCondition = "ECAL/ELS; peak crosswind"; :>> isCounted = true; }
    part <'WXC-063'> wxc_063 : WeatherRule { doc /* 1996 A2.1.1-6B HEAD PEAK (surface wind, knots) */ :>> rulebookEdition = "1996"; :>> ruleId = "A2.1.1-6B"; :>> wxParameter = "headwind"; :>> wxScene = "other"; :>> wxSite = "any"; :>> wxComparison = "max"; :>> limitValue = 25.0; :>> limitUnit = "knots"; :>> ruleCondition = "peak headwind component; printed in the RTLS row"; :>> isCounted = false; }
    part <'WXC-064'> wxc_064 : WeatherRule { doc /* 1996 A2.1.1-6B TAIL AVG (surface wind, knots) */ :>> rulebookEdition = "1996"; :>> ruleId = "A2.1.1-6B"; :>> wxParameter = "tailwind"; :>> wxScene = "other"; :>> wxSite = "any"; :>> wxComparison = "max"; :>> limitValue = 10.0; :>> limitUnit = "knots"; :>> ruleCondition = "average tailwind component; printed in the RTLS row"; :>> isCounted = false; }
    part <'WXC-065'> wxc_065 : WeatherRule { doc /* 1996 A2.1.1-6B TAIL PEAK (surface wind, knots) */ :>> rulebookEdition = "1996"; :>> ruleId = "A2.1.1-6B"; :>> wxParameter = "tailwind"; :>> wxScene = "other"; :>> wxSite = "any"; :>> wxComparison = "max"; :>> limitValue = 15.0; :>> limitUnit = "knots"; :>> ruleCondition = "peak tailwind component; printed in the RTLS row"; :>> isCounted = false; }
    part <'WXC-066'> wxc_066 : WeatherRule { doc /* 1996 A2.1.1-6B GUST (surface wind, knots) */ :>> rulebookEdition = "1996"; :>> ruleId = "A2.1.1-6B"; :>> wxParameter = "wind_speed"; :>> wxScene = "other"; :>> wxSite = "any"; :>> wxComparison = "max"; :>> limitValue = 10.0; :>> limitUnit = "knots"; :>> ruleCondition = "gust = difference between peak and average wind (rationale p99); strict '<10'; p"; :>> isCounted = false; }
    part <'WXC-067'> wxc_067 : WeatherRule { doc /* 1996 A2.1.4-7E CEILING */ :>> rulebookEdition = "1996"; :>> ruleId = "A2.1.4-7E"; :>> wxParameter = "ceiling"; :>> wxScene = "deorbit"; :>> wxSite = "any"; :>> wxComparison = "min"; :>> limitValue = 10.0; :>> limitUnit = "K ft"; :>> ruleCondition = "WX placards for the priority of landing sites after systems failures (note [2] o"; :>> isCounted = true; }
    part <'WXC-068'> wxc_068 : WeatherRule { doc /* 1996 A2.1.4-7E VISIBILITY */ :>> rulebookEdition = "1996"; :>> ruleId = "A2.1.4-7E"; :>> wxParameter = "visibility"; :>> wxScene = "deorbit"; :>> wxSite = "any"; :>> wxComparison = "min"; :>> limitValue = 7.0; :>> limitUnit = "SM"; :>> ruleCondition = "WX placards for the priority of landing sites after systems failures (note [2] o"; :>> isCounted = true; }
    part <'WXC-069'> wxc_069 : WeatherRule { doc /* 1996 A2.1.4-7E CROSSWIND (PEAK) */ :>> rulebookEdition = "1996"; :>> ruleId = "A2.1.4-7E"; :>> wxParameter = "crosswind"; :>> wxScene = "deorbit"; :>> wxSite = "any"; :>> wxComparison = "max"; :>> limitValue = 10.0; :>> limitUnit = "knots"; :>> ruleCondition = "WX placards for the priority of landing sites after systems failures (note [2] o"; :>> isCounted = true; }
    part <'WXC-070'> wxc_070 : WeatherRule { doc /* 1996 A2.1.5-11 XWIND <10 KNOTS PEAK */ :>> rulebookEdition = "1996"; :>> ruleId = "A2.1.5-11"; :>> wxParameter = "crosswind"; :>> wxScene = "other"; :>> wxSite = "any"; :>> wxComparison = "min"; :>> limitValue = 10.0; :>> limitUnit = "knots"; :>> ruleCondition = "crosswind DTO is NO-GO when the peak crosswind is below 10 knots (p379 rationale"; :>> isCounted = true; }
    part <'WXC-071'> wxc_071 : WeatherRule { doc /* 1996 A2.1.5-11 XWIND >15 KNOTS PEAK */ :>> rulebookEdition = "1996"; :>> ruleId = "A2.1.5-11"; :>> wxParameter = "crosswind"; :>> wxScene = "other"; :>> wxSite = "any"; :>> wxComparison = "max"; :>> limitValue = 15.0; :>> limitUnit = "knots"; :>> ruleCondition = "crosswind DTO is NO-GO when the peak crosswind is above 15 knots (nominal crossw"; :>> isCounted = true; }
    part <'WXC-072'> wxc_072 : WeatherRule { doc /* 1996 A2.1.5-11 XWIND >10 KNOTS GUST */ :>> rulebookEdition = "1996"; :>> ruleId = "A2.1.5-11"; :>> wxParameter = "wind_speed"; :>> wxScene = "other"; :>> wxSite = "any"; :>> wxComparison = "max"; :>> limitValue = 10.0; :>> limitUnit = "knots"; :>> ruleCondition = "crosswind DTO is NO-GO when the gust is above 10 knots (gust above the steady-st"; :>> isCounted = true; }
    part <'WXC-073'> wxc_073 : WeatherRule { doc /* 1996 A2.1.5-12D CROSSWIND LANDING DTO'S ABOVE 12 KNOTS P */ :>> rulebookEdition = "1996"; :>> ruleId = "A2.1.5-12D"; :>> wxParameter = "crosswind"; :>> wxScene = "other"; :>> wxSite = "any"; :>> wxComparison = "max"; :>> limitValue = 12.0; :>> limitUnit = "knots"; :>> ruleCondition = "crosswind landing DTOs above 12 knots peak will not be performed on night landin"; :>> isCounted = true; }
    part <'WXC-074'> wxc_074 : WeatherRule { doc /* 1996 A4.1.4-5A SUN POSITION ON FINAL, AZIMUTH FROM CENT */ :>> rulebookEdition = "1996"; :>> ruleId = "A4.1.4-5A"; :>> wxParameter = "other"; :>> wxScene = "other"; :>> wxSite = "any"; :>> wxComparison = "min"; :>> limitValue = 10.0; :>> limitUnit = "degrees"; :>> ruleCondition = "for a runway to be GO the sun position on final must not be within 10 degrees of"; :>> isCounted = false; }
    part <'WXC-075'> wxc_075 : WeatherRule { doc /* 1996 A4.1.4-5A SUN POSITION ON FINAL, ELEVATION */ :>> rulebookEdition = "1996"; :>> ruleId = "A4.1.4-5A"; :>> wxParameter = "other"; :>> wxScene = "other"; :>> wxSite = "any"; :>> wxComparison = "range"; :>> limitValue = 0.0; :>> limitValueHigh = 20.0; :>> limitUnit = "degrees"; :>> ruleCondition = "sun elevation from 0 to 20 degrees, together with the azimuth within 10 degrees "; :>> isCounted = false; }
    part <'WXC-076'> wxc_076 : WeatherRule { doc /* 1996 A6.1.3-1C AMBIENT TEMPERATURE AT THE LAUNCH SITE */ :>> rulebookEdition = "1996"; :>> ruleId = "A6.1.3-1C"; :>> wxParameter = "temperature"; :>> wxScene = "launch"; :>> wxSite = "any"; :>> wxComparison = "other"; :>> limitValue = 50.0; :>> limitUnit = "deg F"; :>> ruleCondition = "RCS primary thruster heaters are off for ascent unless the ambient temperature a"; :>> isCounted = false; }
    part <'WXC-077'> wxc_077 : WeatherRule { doc /* 1996 A8.1.1-18A CEILINGS > 10K FEET / < 10K FEET */ :>> rulebookEdition = "1996"; :>> ruleId = "A8.1.1-18A"; :>> wxParameter = "ceiling"; :>> wxScene = "other"; :>> wxSite = "any"; :>> wxComparison = "other"; :>> limitValue = 10.0; :>> limitUnit = "K ft"; :>> ruleCondition = "number of onboard MSBLS required: daylight landing; ceilings above 10K ft need 0"; :>> isCounted = false; }
    part <'WXC-078'> wxc_078 : WeatherRule { doc /* 1996 A8.1.1-18A CEILINGS > 15K FEET / < 15K FEET */ :>> rulebookEdition = "1996"; :>> ruleId = "A8.1.1-18A"; :>> wxParameter = "ceiling"; :>> wxScene = "other"; :>> wxSite = "any"; :>> wxComparison = "other"; :>> limitValue = 15.0; :>> limitUnit = "K ft"; :>> ruleCondition = "number of onboard MSBLS required: night landing; ceilings above 15K ft need 1 (l"; :>> isCounted = false; }
    part <'WXC-079'> wxc_079 : WeatherRule { doc /* 1996 A8.1.3-12B.3 HIGH WINDS ON THE HAC */ :>> rulebookEdition = "1996"; :>> ruleId = "A8.1.3-12B.3"; :>> wxParameter = "wind_speed"; :>> wxScene = "other"; :>> wxSite = "any"; :>> wxComparison = "min"; :>> limitValue = 80.0; :>> limitUnit = "knots"; :>> ruleCondition = "a single good ADTA is incorporated into G&C when winds on the HAC are 80 knots o"; :>> isCounted = false; }
    part <'WXC-080'> wxc_080 : WeatherRule { doc /* 1996 A10.1.2-3A.1 CEILING */ :>> rulebookEdition = "1996"; :>> ruleId = "A10.1.2-3A.1"; :>> wxParameter = "ceiling"; :>> wxScene = "deorbit"; :>> wxSite = "any"; :>> wxComparison = "min"; :>> limitValue = 10.0; :>> limitUnit = "K ft"; :>> ruleCondition = "prior to the deorbit burn, if an APU/hydraulic system fails or its capability to"; :>> isCounted = true; }
    part <'WXC-081'> wxc_081 : WeatherRule { doc /* 1996 A10.1.2-3A.1 VISIBILITY */ :>> rulebookEdition = "1996"; :>> ruleId = "A10.1.2-3A.1"; :>> wxParameter = "visibility"; :>> wxScene = "deorbit"; :>> wxSite = "any"; :>> wxComparison = "min"; :>> limitValue = 7.0; :>> limitUnit = "SM"; :>> ruleCondition = "prior to the deorbit burn, if an APU/hydraulic system fails or its capability to"; :>> isCounted = true; }
    part <'WXC-082'> wxc_082 : WeatherRule { doc /* 1996 A10.1.2-3A.1 CROSSWIND (PEAK) */ :>> rulebookEdition = "1996"; :>> ruleId = "A10.1.2-3A.1"; :>> wxParameter = "crosswind"; :>> wxScene = "deorbit"; :>> wxSite = "any"; :>> wxComparison = "max"; :>> limitValue = 10.0; :>> limitUnit = "knots"; :>> ruleCondition = "prior to the deorbit burn, if an APU/hydraulic system fails or its capability to"; :>> isCounted = true; }
    part <'WXC-083'> wxc_083 : WeatherRule { doc /* 1996 A10.1.8-3A CROSSWIND (PEAK) */ :>> rulebookEdition = "1996"; :>> ruleId = "A10.1.8-3A"; :>> wxParameter = "crosswind"; :>> wxScene = "other"; :>> wxSite = "any"; :>> wxComparison = "max"; :>> limitValue = 15.0; :>> limitUnit = "knots"; :>> ruleCondition = "the drag chute will not be deployed if the crosswind is above 15 knots peak"; :>> isCounted = true; }
    part <'WXC-084'> wxc_084 : WeatherRule { doc /* 1996 A16.1.1-10A LIGHTNING WITHIN 5 MILES */ :>> rulebookEdition = "1996"; :>> ruleId = "A16.1.1-10A"; :>> wxParameter = "lightning_distance"; :>> wxScene = "other"; :>> wxSite = "any"; :>> wxComparison = "min"; :>> limitValue = 5.0; :>> limitUnit = "miles"; :>> ruleCondition = "normal postlanding operations continue except for lightning within 5 miles (the "; :>> isCounted = true; }
    part <'WXC-085'> wxc_085 : WeatherRule { doc /* 2002 A2-6A (Table A2-6-I) CEILING / VISIBILITY (K FT)/(SM) */ :>> rulebookEdition = "2002"; :>> ruleId = "A2-6A (Table A2-6-I)"; :>> wxParameter = "ceiling"; :>> wxScene = "landing_rtls"; :>> wxSite = "any"; :>> wxComparison = "min"; :>> limitValue = 5.0; :>> limitUnit = "K FT"; :>> ruleCondition = "RTLS, concrete runway, DAY; MLS column not legible in the text layer (A3-202: re"; :>> isCounted = true; }
    part <'WXC-086'> wxc_086 : WeatherRule { doc /* 2002 A2-6A (Table A2-6-I) CEILING / VISIBILITY (K FT)/(SM) */ :>> rulebookEdition = "2002"; :>> ruleId = "A2-6A (Table A2-6-I)"; :>> wxParameter = "visibility"; :>> wxScene = "landing_rtls"; :>> wxSite = "any"; :>> wxComparison = "min"; :>> limitValue = 4.0; :>> limitUnit = "SM"; :>> ruleCondition = "RTLS, concrete runway, DAY; MLS column not legible in the text layer (A3-202: re"; :>> isCounted = true; }
    part <'WXC-087'> wxc_087 : WeatherRule { doc /* 2002 A2-6A (Table A2-6-I) CEILING / VISIBILITY (K FT)/(SM) */ :>> rulebookEdition = "2002"; :>> ruleId = "A2-6A (Table A2-6-I)"; :>> wxParameter = "ceiling"; :>> wxScene = "landing_tal"; :>> wxSite = "any"; :>> wxComparison = "min"; :>> limitValue = 5.0; :>> limitUnit = "K FT"; :>> ruleCondition = "TAL, concrete runway, DAY; printed as '>5/5 TAL'; MLS column not legible in the "; :>> isCounted = true; }
    part <'WXC-088'> wxc_088 : WeatherRule { doc /* 2002 A2-6A (Table A2-6-I) CEILING / VISIBILITY (K FT)/(SM) */ :>> rulebookEdition = "2002"; :>> ruleId = "A2-6A (Table A2-6-I)"; :>> wxParameter = "visibility"; :>> wxScene = "landing_tal"; :>> wxSite = "any"; :>> wxComparison = "min"; :>> limitValue = 5.0; :>> limitUnit = "SM"; :>> ruleCondition = "TAL, concrete runway, DAY; printed as '>5/5 TAL'; MLS column not legible in the "; :>> isCounted = true; }
    part <'WXC-089'> wxc_089 : WeatherRule { doc /* 2002 A2-6A (Table A2-6-I) CEILING / VISIBILITY (K FT)/(SM) */ :>> rulebookEdition = "2002"; :>> ruleId = "A2-6A (Table A2-6-I)"; :>> wxParameter = "ceiling"; :>> wxScene = "other"; :>> wxSite = "any"; :>> wxComparison = "min"; :>> limitValue = 15.0; :>> limitUnit = "K FT"; :>> ruleCondition = "lakebed runway, NIGHT; MLS column not legible (rationale pdf 497: single-string "; :>> isCounted = true; }
    part <'WXC-090'> wxc_090 : WeatherRule { doc /* 2002 A2-6A (Table A2-6-I) CEILING / VISIBILITY (K FT)/(SM) */ :>> rulebookEdition = "2002"; :>> ruleId = "A2-6A (Table A2-6-I)"; :>> wxParameter = "visibility"; :>> wxScene = "other"; :>> wxSite = "any"; :>> wxComparison = "min"; :>> limitValue = 7.0; :>> limitUnit = "SM"; :>> ruleCondition = "lakebed runway, NIGHT; MLS column not legible (rationale pdf 497: single-string "; :>> isCounted = true; }
    part <'WXC-091'> wxc_091 : WeatherRule { doc /* 2002 A2-6A (Table A2-6-I) CEILING / VISIBILITY (K FT)/(SM) */ :>> rulebookEdition = "2002"; :>> ruleId = "A2-6A (Table A2-6-I)"; :>> wxParameter = "ceiling"; :>> wxScene = "other"; :>> wxSite = "any"; :>> wxComparison = "min"; :>> limitValue = 10.0; :>> limitUnit = "K FT"; :>> ruleCondition = "cell label order: KSC, EDW, NOR CONCRETE / AOA / DAILY PLS SELECTION (ALL SITES)"; :>> isCounted = false; }
    part <'WXC-092'> wxc_092 : WeatherRule { doc /* 2002 A2-6A (Table A2-6-I) CEILING / VISIBILITY (K FT)/(SM) */ :>> rulebookEdition = "2002"; :>> ruleId = "A2-6A (Table A2-6-I)"; :>> wxParameter = "visibility"; :>> wxScene = "other"; :>> wxSite = "any"; :>> wxComparison = "min"; :>> limitValue = 7.0; :>> limitUnit = "SM"; :>> ruleCondition = "cell label order: KSC, EDW, NOR CONCRETE / AOA / DAILY PLS SELECTION (ALL SITES)"; :>> isCounted = false; }
    part <'WXC-093'> wxc_093 : WeatherRule { doc /* 2002 A2-6A (Table A2-6-I) CEILING / VISIBILITY (K FT)/(SM) */ :>> rulebookEdition = "2002"; :>> ruleId = "A2-6A (Table A2-6-I)"; :>> wxParameter = "ceiling"; :>> wxScene = "other"; :>> wxSite = "any"; :>> wxComparison = "min"; :>> limitValue = 8.0; :>> limitUnit = "K FT"; :>> ruleCondition = "cell label order: KSC, EDW, NOR CONCRETE / AOA / DAILY PLS SELECTION (ALL SITES)"; :>> isCounted = false; }
    part <'WXC-094'> wxc_094 : WeatherRule { doc /* 2002 A2-6A (Table A2-6-I) CEILING / VISIBILITY (K FT)/(SM) */ :>> rulebookEdition = "2002"; :>> ruleId = "A2-6A (Table A2-6-I)"; :>> wxParameter = "visibility"; :>> wxScene = "other"; :>> wxSite = "any"; :>> wxComparison = "min"; :>> limitValue = 5.0; :>> limitUnit = "SM"; :>> ruleCondition = "cell label order: KSC, EDW, NOR CONCRETE / AOA / DAILY PLS SELECTION (ALL SITES)"; :>> isCounted = false; }
    part <'WXC-095'> wxc_095 : WeatherRule { doc /* 2002 A2-6A (Table A2-6-I) CEILING / VISIBILITY (K FT)/(SM) */ :>> rulebookEdition = "2002"; :>> ruleId = "A2-6A (Table A2-6-I)"; :>> wxParameter = "ceiling"; :>> wxScene = "other"; :>> wxSite = "any"; :>> wxComparison = "min"; :>> limitValue = 10.0; :>> limitUnit = "K FT"; :>> ruleCondition = "cell label order: LAKEBED, DAY (WX RECON REQUIRED)"; :>> isCounted = false; }
    part <'WXC-096'> wxc_096 : WeatherRule { doc /* 2002 A2-6A (Table A2-6-I) CEILING / VISIBILITY (K FT)/(SM) */ :>> rulebookEdition = "2002"; :>> ruleId = "A2-6A (Table A2-6-I)"; :>> wxParameter = "visibility"; :>> wxScene = "other"; :>> wxSite = "any"; :>> wxComparison = "min"; :>> limitValue = 7.0; :>> limitUnit = "SM"; :>> ruleCondition = "cell label order: LAKEBED, DAY (WX RECON REQUIRED)"; :>> isCounted = false; }
    part <'WXC-097'> wxc_097 : WeatherRule { doc /* 2002 A2-6A (Table A2-6-I) CEILING / VISIBILITY (K FT)/(SM) */ :>> rulebookEdition = "2002"; :>> ruleId = "A2-6A (Table A2-6-I)"; :>> wxParameter = "ceiling"; :>> wxScene = "other"; :>> wxSite = "any"; :>> wxComparison = "min"; :>> limitValue = 10.0; :>> limitUnit = "K FT"; :>> ruleCondition = "cell label order: RTLS, TAL CONCRETE, DAY (second value of the row)"; :>> isCounted = false; }
    part <'WXC-098'> wxc_098 : WeatherRule { doc /* 2002 A2-6A (Table A2-6-I) CEILING / VISIBILITY (K FT)/(SM) */ :>> rulebookEdition = "2002"; :>> ruleId = "A2-6A (Table A2-6-I)"; :>> wxParameter = "visibility"; :>> wxScene = "other"; :>> wxSite = "any"; :>> wxComparison = "min"; :>> limitValue = 7.0; :>> limitUnit = "SM"; :>> ruleCondition = "cell label order: RTLS, TAL CONCRETE, DAY (second value of the row)"; :>> isCounted = false; }
    part <'WXC-099'> wxc_099 : WeatherRule { doc /* 2002 A2-6A (Table A2-6-I) CEILING / VISIBILITY (K FT)/(SM) */ :>> rulebookEdition = "2002"; :>> ruleId = "A2-6A (Table A2-6-I)"; :>> wxParameter = "ceiling"; :>> wxScene = "other"; :>> wxSite = "any"; :>> wxComparison = "min"; :>> limitValue = 0.0; :>> limitUnit = "K FT"; :>> ruleCondition = "cell label order: ACLS / ECAL / ELS (0/0)"; :>> isCounted = false; }
    part <'WXC-100'> wxc_100 : WeatherRule { doc /* 2002 A2-6A (Table A2-6-I) CEILING / VISIBILITY (K FT)/(SM) */ :>> rulebookEdition = "2002"; :>> ruleId = "A2-6A (Table A2-6-I)"; :>> wxParameter = "visibility"; :>> wxScene = "other"; :>> wxSite = "any"; :>> wxComparison = "min"; :>> limitValue = 0.0; :>> limitUnit = "SM"; :>> ruleCondition = "cell label order: ACLS / ECAL / ELS (0/0)"; :>> isCounted = false; }
    part <'WXC-101'> wxc_101 : WeatherRule { doc /* 2002 A2-6A (Table A2-6-I) CEILING / VISIBILITY (K FT)/(SM) */ :>> rulebookEdition = "2002"; :>> ruleId = "A2-6A (Table A2-6-I)"; :>> wxParameter = "ceiling"; :>> wxScene = "other"; :>> wxSite = "any"; :>> wxComparison = "min"; :>> limitValue = 8.0; :>> limitUnit = "K FT"; :>> ruleCondition = "cell label order: ACLS / ECAL / ELS (second value of the row)"; :>> isCounted = false; }
    part <'WXC-102'> wxc_102 : WeatherRule { doc /* 2002 A2-6A (Table A2-6-I) CEILING / VISIBILITY (K FT)/(SM) */ :>> rulebookEdition = "2002"; :>> ruleId = "A2-6A (Table A2-6-I)"; :>> wxParameter = "visibility"; :>> wxScene = "other"; :>> wxSite = "any"; :>> wxComparison = "min"; :>> limitValue = 5.0; :>> limitUnit = "SM"; :>> ruleCondition = "cell label order: ACLS / ECAL / ELS (second value of the row)"; :>> isCounted = false; }
    part <'WXC-103'> wxc_103 : WeatherRule { doc /* 2002 A2-6A.2 CEILINGS BELOW 10K FT */ :>> rulebookEdition = "2002"; :>> ruleId = "A2-6A.2"; :>> wxParameter = "ceiling"; :>> wxScene = "landing_eom"; :>> wxSite = "any"; :>> wxComparison = "other"; :>> limitValue = 10.0; :>> limitUnit = "K FT"; :>> ruleCondition = "WX RECON must confirm PAPI/aimpoint/ball bar visible when ceiling below 10K FT a"; :>> isCounted = false; }
    part <'WXC-104'> wxc_104 : WeatherRule { doc /* 2002 A2-6A.2 VISIBILITY LESS THAN 7 STATUTE MILES (SM */ :>> rulebookEdition = "2002"; :>> ruleId = "A2-6A.2"; :>> wxParameter = "visibility"; :>> wxScene = "landing_eom"; :>> wxSite = "any"; :>> wxComparison = "other"; :>> limitValue = 7.0; :>> limitUnit = "SM"; :>> ruleCondition = "WX RECON must confirm PAPI/aimpoint/ball bar visible when ceiling below 10K FT a"; :>> isCounted = false; }
    part <'WXC-105'> wxc_105 : WeatherRule { doc /* 2002 A2-6A.2 CEILINGS AT OR BELOW 8K FT */ :>> rulebookEdition = "2002"; :>> ruleId = "A2-6A.2"; :>> wxParameter = "ceiling"; :>> wxScene = "other"; :>> wxSite = "any"; :>> wxComparison = "other"; :>> limitValue = 8.0; :>> limitUnit = "K FT"; :>> ruleCondition = "WX RECON GO/NO-GO recommendation required for ceilings at or below 8K FT; not re"; :>> isCounted = false; }
    part <'WXC-106'> wxc_106 : WeatherRule { doc /* 2002 A2-6A.3 CLOUD LAYERS BELOW 8K FT ... GREATER THA */ :>> rulebookEdition = "2002"; :>> ruleId = "A2-6A.3"; :>> wxParameter = "cloud_cover"; :>> wxScene = "landing_eom"; :>> wxSite = "KSC"; :>> wxComparison = "range"; :>> limitValue = 2.0; :>> limitValueHigh = 4.0; :>> limitUnit = "eighths of sky coverage"; :>> ruleCondition = "cloud layers below 8K FT reported by ground observers or weather aircraft, at th"; :>> isCounted = true; }
    part <'WXC-107'> wxc_107 : WeatherRule { doc /* 2002 A2-6B (Table A2-6-II) CROSS PEAK */ :>> rulebookEdition = "2002"; :>> ruleId = "A2-6B (Table A2-6-II)"; :>> wxParameter = "crosswind"; :>> wxScene = "landing_rtls"; :>> wxSite = "any"; :>> wxComparison = "max"; :>> limitValue = 15.0; :>> limitUnit = "knots"; :>> ruleCondition = "RTLS; footnote * applies to this value (STA evaluation to 17 knots)"; :>> isCounted = true; }
    part <'WXC-108'> wxc_108 : WeatherRule { doc /* 2002 A2-6B (Table A2-6-II) CROSS PEAK ... REQUIRES AN STA EVALUATIO */ :>> rulebookEdition = "2002"; :>> ruleId = "A2-6B (Table A2-6-II)"; :>> wxParameter = "crosswind"; :>> wxScene = "landing_rtls"; :>> wxSite = "any"; :>> wxComparison = "max"; :>> limitValue = 17.0; :>> limitUnit = "knots"; :>> ruleCondition = "RTLS, only with an STA evaluation to 17 knots and a GO from the STA pilot (also "; :>> isCounted = true; }
    part <'WXC-109'> wxc_109 : WeatherRule { doc /* 2002 A2-6B (Table A2-6-II) CROSS PEAK */ :>> rulebookEdition = "2002"; :>> ruleId = "A2-6B (Table A2-6-II)"; :>> wxParameter = "crosswind"; :>> wxScene = "landing_eom"; :>> wxSite = "any"; :>> wxComparison = "max"; :>> limitValue = 15.0; :>> limitUnit = "knots"; :>> ruleCondition = "DAY; the row cell is shared by EOM, TAL, AOA and DAILY PLS SELECTION (this recor"; :>> isCounted = true; }
    part <'WXC-110'> wxc_110 : WeatherRule { doc /* 2002 A2-6B (Table A2-6-II) CROSS PEAK */ :>> rulebookEdition = "2002"; :>> ruleId = "A2-6B (Table A2-6-II)"; :>> wxParameter = "crosswind"; :>> wxScene = "landing_tal"; :>> wxSite = "any"; :>> wxComparison = "max"; :>> limitValue = 15.0; :>> limitUnit = "knots"; :>> ruleCondition = "DAY; the row cell is shared by EOM, TAL, AOA and DAILY PLS SELECTION (this recor"; :>> isCounted = true; }
    part <'WXC-111'> wxc_111 : WeatherRule { doc /* 2002 A2-6B (Table A2-6-II) CROSS PEAK */ :>> rulebookEdition = "2002"; :>> ruleId = "A2-6B (Table A2-6-II)"; :>> wxParameter = "crosswind"; :>> wxScene = "landing_aoa"; :>> wxSite = "any"; :>> wxComparison = "max"; :>> limitValue = 15.0; :>> limitUnit = "knots"; :>> ruleCondition = "DAY; the row cell is shared by EOM, TAL, AOA and DAILY PLS SELECTION (this recor"; :>> isCounted = true; }
    part <'WXC-112'> wxc_112 : WeatherRule { doc /* 2002 A2-6B (Table A2-6-II) CROSS PEAK */ :>> rulebookEdition = "2002"; :>> ruleId = "A2-6B (Table A2-6-II)"; :>> wxParameter = "crosswind"; :>> wxScene = "landing_eom"; :>> wxSite = "any"; :>> wxComparison = "max"; :>> limitValue = 12.0; :>> limitUnit = "knots"; :>> ruleCondition = "NIGHT; the row cell is shared by EOM and DAILY PLS SELECTION"; :>> isCounted = true; }
    part <'WXC-113'> wxc_113 : WeatherRule { doc /* 2002 A2-6B (Table A2-6-II) CROSS PEAK */ :>> rulebookEdition = "2002"; :>> ruleId = "A2-6B (Table A2-6-II)"; :>> wxParameter = "crosswind"; :>> wxScene = "landing_tal"; :>> wxSite = "any"; :>> wxComparison = "max"; :>> limitValue = 15.0; :>> limitUnit = "knots"; :>> ruleCondition = "NIGHT; the row cell is shared by TAL and AOA (this record: TAL)"; :>> isCounted = true; }
    part <'WXC-114'> wxc_114 : WeatherRule { doc /* 2002 A2-6B (Table A2-6-II) CROSS PEAK */ :>> rulebookEdition = "2002"; :>> ruleId = "A2-6B (Table A2-6-II)"; :>> wxParameter = "crosswind"; :>> wxScene = "landing_aoa"; :>> wxSite = "any"; :>> wxComparison = "max"; :>> limitValue = 15.0; :>> limitUnit = "knots"; :>> ruleCondition = "NIGHT; the row cell is shared by TAL and AOA (this record: AOA)"; :>> isCounted = true; }
    part <'WXC-115'> wxc_115 : WeatherRule { doc /* 2002 A2-6B (Table A2-6-II) CROSS PEAK */ :>> rulebookEdition = "2002"; :>> ruleId = "A2-6B (Table A2-6-II)"; :>> wxParameter = "crosswind"; :>> wxScene = "other"; :>> wxSite = "any"; :>> wxComparison = "max"; :>> limitValue = 15.0; :>> limitUnit = "knots"; :>> ruleCondition = "ECAL/ELS; turbulence column N/A"; :>> isCounted = true; }
    part <'WXC-116'> wxc_116 : WeatherRule { doc /* 2002 A2-6B (Table A2-6-II) CROSS PEAK */ :>> rulebookEdition = "2002"; :>> ruleId = "A2-6B (Table A2-6-II)"; :>> wxParameter = "crosswind"; :>> wxScene = "other"; :>> wxSite = "any"; :>> wxComparison = "max"; :>> limitValue = 12.0; :>> limitUnit = "knots"; :>> ruleCondition = "landing after the CDR's flight day 19 (printed 'LANDING ? CDR FD19'; the sign gl"; :>> isCounted = true; }
    part <'WXC-117'> wxc_117 : WeatherRule { doc /* 2002 A2-6B (Table A2-6-II) HEAD PEAK */ :>> rulebookEdition = "2002"; :>> ruleId = "A2-6B (Table A2-6-II)"; :>> wxParameter = "headwind"; :>> wxScene = "landing_rtls"; :>> wxSite = "any"; :>> wxComparison = "max"; :>> limitValue = 25.0; :>> limitUnit = "knots"; :>> ruleCondition = "peak headwind; RTLS row value; rationale pdf 500 gives a 20-knot certification l"; :>> isCounted = false; }
    part <'WXC-118'> wxc_118 : WeatherRule { doc /* 2002 A2-6B (Table A2-6-II) TAIL AVG */ :>> rulebookEdition = "2002"; :>> ruleId = "A2-6B (Table A2-6-II)"; :>> wxParameter = "tailwind"; :>> wxScene = "landing_rtls"; :>> wxSite = "any"; :>> wxComparison = "max"; :>> limitValue = 10.0; :>> limitUnit = "knots"; :>> ruleCondition = "average tailwind; RTLS row value"; :>> isCounted = false; }
    part <'WXC-119'> wxc_119 : WeatherRule { doc /* 2002 A2-6B (Table A2-6-II) TAIL PEAK */ :>> rulebookEdition = "2002"; :>> ruleId = "A2-6B (Table A2-6-II)"; :>> wxParameter = "tailwind"; :>> wxScene = "landing_rtls"; :>> wxSite = "any"; :>> wxComparison = "max"; :>> limitValue = 15.0; :>> limitUnit = "knots"; :>> ruleCondition = "peak tailwind; RTLS row value"; :>> isCounted = false; }
    part <'WXC-120'> wxc_120 : WeatherRule { doc /* 2002 A2-6B (Table A2-6-II) GUST */ :>> rulebookEdition = "2002"; :>> ruleId = "A2-6B (Table A2-6-II)"; :>> wxParameter = "wind_speed"; :>> wxScene = "landing_rtls"; :>> wxSite = "any"; :>> wxComparison = "max"; :>> limitValue = 10.0; :>> limitUnit = "knots"; :>> ruleCondition = "gust = difference between peak and average wind (rationale pdf 500); printed '<1"; :>> isCounted = false; }
    part <'WXC-121'> wxc_121 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "landing_rtls"; :>> wxSite = "any"; :>> wxComparison = "min"; :>> limitValue = 20.0; :>> limitUnit = "NM"; :>> ruleCondition = "radial from center of prime runway; TSTORM (INCLUDING ATTACHED NONTRANSPARENT AN"; :>> isCounted = true; }
    part <'WXC-122'> wxc_122 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "landing_tal"; :>> wxSite = "any"; :>> wxComparison = "min"; :>> limitValue = 20.0; :>> limitUnit = "NM"; :>> ruleCondition = "radial from center of prime runway; TSTORM (INCLUDING ATTACHED NONTRANSPARENT AN"; :>> isCounted = true; }
    part <'WXC-123'> wxc_123 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "landing_eom"; :>> wxSite = "any"; :>> wxComparison = "min"; :>> limitValue = 30.0; :>> limitUnit = "NM"; :>> ruleCondition = "radial from center of prime runway; TSTORM (INCLUDING ATTACHED NONTRANSPARENT AN"; :>> isCounted = true; }
    part <'WXC-124'> wxc_124 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "other"; :>> wxSite = "any"; :>> wxComparison = "min"; :>> limitValue = 15.0; :>> limitUnit = "NM"; :>> ruleCondition = "radial from center of prime runway; TSTORM (INCLUDING ATTACHED NONTRANSPARENT AN"; :>> isCounted = false; }
    part <'WXC-125'> wxc_125 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "landing_rtls"; :>> wxSite = "any"; :>> wxComparison = "min"; :>> limitValue = 10.0; :>> limitUnit = "NM"; :>> ruleCondition = "lateral along approach path out to 30 NM; TSTORM (INCLUDING ATTACHED NONTRANSPAR"; :>> isCounted = true; }
    part <'WXC-126'> wxc_126 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "landing_tal"; :>> wxSite = "any"; :>> wxComparison = "min"; :>> limitValue = 10.0; :>> limitUnit = "NM"; :>> ruleCondition = "lateral along approach path out to 30 NM; TSTORM (INCLUDING ATTACHED NONTRANSPAR"; :>> isCounted = true; }
    part <'WXC-127'> wxc_127 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "landing_eom"; :>> wxSite = "any"; :>> wxComparison = "min"; :>> limitValue = 20.0; :>> limitUnit = "NM"; :>> ruleCondition = "lateral along approach path out to 30 NM; TSTORM (INCLUDING ATTACHED NONTRANSPAR"; :>> isCounted = true; }
    part <'WXC-128'> wxc_128 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "other"; :>> wxSite = "any"; :>> wxComparison = "min"; :>> limitValue = 5.0; :>> limitUnit = "NM"; :>> ruleCondition = "lateral along approach path out to 30 NM; TSTORM (INCLUDING ATTACHED NONTRANSPAR"; :>> isCounted = false; }
    part <'WXC-129'> wxc_129 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "landing_rtls"; :>> wxSite = "any"; :>> wxComparison = "min"; :>> limitValue = 15.0; :>> limitUnit = "NM"; :>> ruleCondition = "radial from center of prime runway; DETACHED NONTRANSPARENT ANVIL < 3 HRS OLD; t"; :>> isCounted = true; }
    part <'WXC-130'> wxc_130 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "landing_tal"; :>> wxSite = "any"; :>> wxComparison = "min"; :>> limitValue = 15.0; :>> limitUnit = "NM"; :>> ruleCondition = "radial from center of prime runway; DETACHED NONTRANSPARENT ANVIL < 3 HRS OLD; t"; :>> isCounted = true; }
    part <'WXC-131'> wxc_131 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "landing_eom"; :>> wxSite = "any"; :>> wxComparison = "min"; :>> limitValue = 20.0; :>> limitUnit = "NM"; :>> ruleCondition = "radial from center of prime runway; DETACHED NONTRANSPARENT ANVIL < 3 HRS OLD; t"; :>> isCounted = true; }
    part <'WXC-132'> wxc_132 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "other"; :>> wxSite = "any"; :>> wxComparison = "min"; :>> limitValue = 15.0; :>> limitUnit = "NM"; :>> ruleCondition = "radial from center of prime runway; DETACHED NONTRANSPARENT ANVIL < 3 HRS OLD; t"; :>> isCounted = false; }
    part <'WXC-133'> wxc_133 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "landing_rtls"; :>> wxSite = "any"; :>> wxComparison = "min"; :>> limitValue = 5.0; :>> limitUnit = "NM"; :>> ruleCondition = "lateral along approach path out to 30 NM; DETACHED NONTRANSPARENT ANVIL < 3 HRS "; :>> isCounted = true; }
    part <'WXC-134'> wxc_134 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "landing_tal"; :>> wxSite = "any"; :>> wxComparison = "min"; :>> limitValue = 5.0; :>> limitUnit = "NM"; :>> ruleCondition = "lateral along approach path out to 30 NM; DETACHED NONTRANSPARENT ANVIL < 3 HRS "; :>> isCounted = true; }
    part <'WXC-135'> wxc_135 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "landing_eom"; :>> wxSite = "any"; :>> wxComparison = "min"; :>> limitValue = 10.0; :>> limitUnit = "NM"; :>> ruleCondition = "lateral along approach path out to 30 NM; DETACHED NONTRANSPARENT ANVIL < 3 HRS "; :>> isCounted = true; }
    part <'WXC-136'> wxc_136 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "other"; :>> wxSite = "any"; :>> wxComparison = "min"; :>> limitValue = 5.0; :>> limitUnit = "NM"; :>> ruleCondition = "lateral along approach path out to 30 NM; DETACHED NONTRANSPARENT ANVIL < 3 HRS "; :>> isCounted = false; }
    part <'WXC-137'> wxc_137 : WeatherRule { doc /* 2002 A2-6C (Table A2-6-III) PRECIPITATION * */ :>> rulebookEdition = "2002"; :>> ruleId = "A2-6C (Table A2-6-III)"; :>> wxParameter = "precipitation"; :>> wxScene = "landing_rtls"; :>> wxSite = "any"; :>> wxComparison = "min"; :>> limitValue = 20.0; :>> limitUnit = "NM"; :>> ruleCondition = "radial from center of prime runway; PRECIPITATION *; the column cell is shared b"; :>> isCounted = true; }
    part <'WXC-138'> wxc_138 : WeatherRule { doc /* 2002 A2-6C (Table A2-6-III) PRECIPITATION * */ :>> rulebookEdition = "2002"; :>> ruleId = "A2-6C (Table A2-6-III)"; :>> wxParameter = "precipitation"; :>> wxScene = "landing_tal"; :>> wxSite = "any"; :>> wxComparison = "min"; :>> limitValue = 20.0; :>> limitUnit = "NM"; :>> ruleCondition = "radial from center of prime runway; PRECIPITATION *; the column cell is shared b"; :>> isCounted = true; }
    part <'WXC-139'> wxc_139 : WeatherRule { doc /* 2002 A2-6C (Table A2-6-III) PRECIPITATION * */ :>> rulebookEdition = "2002"; :>> ruleId = "A2-6C (Table A2-6-III)"; :>> wxParameter = "precipitation"; :>> wxScene = "landing_eom"; :>> wxSite = "any"; :>> wxComparison = "min"; :>> limitValue = 30.0; :>> limitUnit = "NM"; :>> ruleCondition = "radial from center of prime runway; PRECIPITATION *; the column cell is shared b"; :>> isCounted = true; }
    part <'WXC-140'> wxc_140 : WeatherRule { doc /* 2002 A2-6C (Table A2-6-III) PRECIPITATION * */ :>> rulebookEdition = "2002"; :>> ruleId = "A2-6C (Table A2-6-III)"; :>> wxParameter = "precipitation"; :>> wxScene = "other"; :>> wxSite = "any"; :>> wxComparison = "min"; :>> limitValue = 15.0; :>> limitUnit = "NM"; :>> ruleCondition = "radial from center of prime runway; PRECIPITATION *; third number of the row"; :>> isCounted = false; }
    part <'WXC-141'> wxc_141 : WeatherRule { doc /* 2002 A2-6C (Table A2-6-III) PRECIPITATION * */ :>> rulebookEdition = "2002"; :>> ruleId = "A2-6C (Table A2-6-III)"; :>> wxParameter = "precipitation"; :>> wxScene = "landing_rtls"; :>> wxSite = "any"; :>> wxComparison = "min"; :>> limitValue = 10.0; :>> limitUnit = "NM"; :>> ruleCondition = "lateral along approach path out to 30 NM; PRECIPITATION *; the column cell is sh"; :>> isCounted = true; }
    part <'WXC-142'> wxc_142 : WeatherRule { doc /* 2002 A2-6C (Table A2-6-III) PRECIPITATION * */ :>> rulebookEdition = "2002"; :>> ruleId = "A2-6C (Table A2-6-III)"; :>> wxParameter = "precipitation"; :>> wxScene = "landing_tal"; :>> wxSite = "any"; :>> wxComparison = "min"; :>> limitValue = 10.0; :>> limitUnit = "NM"; :>> ruleCondition = "lateral along approach path out to 30 NM; PRECIPITATION *; the column cell is sh"; :>> isCounted = true; }
    part <'WXC-143'> wxc_143 : WeatherRule { doc /* 2002 A2-6C (Table A2-6-III) PRECIPITATION * */ :>> rulebookEdition = "2002"; :>> ruleId = "A2-6C (Table A2-6-III)"; :>> wxParameter = "precipitation"; :>> wxScene = "landing_eom"; :>> wxSite = "any"; :>> wxComparison = "min"; :>> limitValue = 20.0; :>> limitUnit = "NM"; :>> ruleCondition = "lateral along approach path out to 30 NM; PRECIPITATION *; the column cell is sh"; :>> isCounted = true; }
    part <'WXC-144'> wxc_144 : WeatherRule { doc /* 2002 A2-6C (Table A2-6-III) PRECIPITATION * */ :>> rulebookEdition = "2002"; :>> ruleId = "A2-6C (Table A2-6-III)"; :>> wxParameter = "precipitation"; :>> wxScene = "other"; :>> wxSite = "any"; :>> wxComparison = "min"; :>> limitValue = 5.0; :>> limitUnit = "NM"; :>> ruleCondition = "lateral along approach path out to 30 NM; PRECIPITATION *; third number of the r"; :>> isCounted = false; }
    part <'WXC-145'> wxc_145 : WeatherRule { doc /* 2002 A2-6C (Table A2-6-III) TSTORM (INCLUDING ATTACHED NONTRANSPAREN */ :>> rulebookEdition = "2002"; :>> ruleId = "A2-6C (Table A2-6-III)"; :>> wxParameter = "thunderstorm"; :>> wxScene = "other"; :>> wxSite = "any"; :>> wxComparison = "min"; :>> limitValue = 2.0; :>> limitUnit = "NM"; :>> ruleCondition = "vertical from top of cloud; TSTORM (INCLUDING ATTACHED NONTRANSPARENT ANVILS), A"; :>> isCounted = false; }
    part <'WXC-146'> wxc_146 : WeatherRule { doc /* 2002 A2-6C (Table A2-6-III) DETACHED NONTRANSPARENT ANVIL < 3 HRS OL */ :>> rulebookEdition = "2002"; :>> ruleId = "A2-6C (Table A2-6-III)"; :>> wxParameter = "thunderstorm"; :>> wxScene = "other"; :>> wxSite = "any"; :>> wxComparison = "min"; :>> limitValue = 2.0; :>> limitUnit = "NM"; :>> ruleCondition = "vertical from top of cloud; DETACHED NONTRANSPARENT ANVIL < 3 HRS OLD"; :>> isCounted = false; }
    part <'WXC-147'> wxc_147 : WeatherRule { doc /* 2002 A2-6C (Table A2-6-III) PRECIPITATION * */ :>> rulebookEdition = "2002"; :>> ruleId = "A2-6C (Table A2-6-III)"; :>> wxParameter = "precipitation"; :>> wxScene = "other"; :>> wxSite = "any"; :>> wxComparison = "min"; :>> limitValue = 2.0; :>> limitUnit = "NM"; :>> ruleCondition = "vertical from top of cloud; PRECIPITATION *"; :>> isCounted = false; }
    part <'WXC-148'> wxc_148 : WeatherRule { doc /* 2002 A2-6C.4.a SHOWERS COVER LESS THAN 10 PERCENT OF TH */ :>> rulebookEdition = "2002"; :>> ruleId = "A2-6C.4.a"; :>> wxParameter = "precipitation"; :>> wxScene = "landing_rtls"; :>> wxSite = "any"; :>> wxComparison = "max"; :>> limitValue = 10.0; :>> limitUnit = "percent"; :>> ruleCondition = "area coverage of showers within 20 NM of the SLF, or multiple HAC's clear of sho"; :>> isCounted = true; }
    part <'WXC-149'> wxc_149 : WeatherRule { doc /* 2002 A2-6C.4.c TOPS OF CLOUDS CONTAINING PRECIPITATION  */ :>> rulebookEdition = "2002"; :>> ruleId = "A2-6C.4.c"; :>> wxParameter = "temperature"; :>> wxScene = "landing_rtls"; :>> wxSite = "any"; :>> wxComparison = "max"; :>> limitValue = 5.0; :>> limitUnit = "deg C"; :>> ruleCondition = "cloud-top temperature level of clouds containing precipitation; RTLS rain shower"; :>> isCounted = true; }
    part <'WXC-150'> wxc_150 : WeatherRule { doc /* 2002 A2-6C.4.c HAVE NOT EXCEEDED THE -10 DEG C LEVEL WI */ :>> rulebookEdition = "2002"; :>> ruleId = "A2-6C.4.c"; :>> wxParameter = "temperature"; :>> wxScene = "landing_rtls"; :>> wxSite = "any"; :>> wxComparison = "max"; :>> limitValue = -10.0; :>> limitUnit = "deg C"; :>> ruleCondition = "cloud tops must not have exceeded the -10 deg C level within 2.5 hours prior to "; :>> isCounted = true; }
    part <'WXC-151'> wxc_151 : WeatherRule { doc /* 2002 A2-6C.4.d PRECIPITATION IS LIGHT (LESS THAN 30 DBZ */ :>> rulebookEdition = "2002"; :>> ruleId = "A2-6C.4.d"; :>> wxParameter = "precipitation"; :>> wxScene = "landing_rtls"; :>> wxSite = "any"; :>> wxComparison = "max"; :>> limitValue = 30.0; :>> limitUnit = "dBZ"; :>> ruleCondition = "radar reflectivity at all levels within and below the cloud; RTLS rain showers ("; :>> isCounted = true; }
    part <'WXC-152'> wxc_152 : WeatherRule { doc /* 2002 A2-6C.4.e A 2-NM VERTICAL CLEARANCE FROM THE TOP O */ :>> rulebookEdition = "2002"; :>> ruleId = "A2-6C.4.e"; :>> wxParameter = "precipitation"; :>> wxScene = "landing_rtls"; :>> wxSite = "any"; :>> wxComparison = "min"; :>> limitValue = 2.0; :>> limitUnit = "NM"; :>> ruleCondition = "vertical clearance; for any shower within 20 miles of the SLF that exceeds C.4.c"; :>> isCounted = true; }
    part <'WXC-153'> wxc_153 : WeatherRule { doc /* 2002 A2-6C.4.e A 10-NM LATERAL CLEARANCE */ :>> rulebookEdition = "2002"; :>> ruleId = "A2-6C.4.e"; :>> wxParameter = "precipitation"; :>> wxScene = "landing_rtls"; :>> wxSite = "any"; :>> wxComparison = "min"; :>> limitValue = 10.0; :>> limitUnit = "NM"; :>> ruleCondition = "lateral clearance; for any shower within 20 miles of the SLF that exceeds C.4.c "; :>> isCounted = true; }
    part <'WXC-154'> wxc_154 : WeatherRule { doc /* 2002 A2-6C.5 CUMULUS CLOUD ATTACHED TO A SMOKE PLUME  */ :>> rulebookEdition = "2002"; :>> ruleId = "A2-6C.5"; :>> wxParameter = "other"; :>> wxScene = "other"; :>> wxSite = "any"; :>> wxComparison = "min"; :>> limitValue = 1.0; :>> limitUnit = "hour"; :>> ruleCondition = "after the cumulus cloud detaches from the smoke plume, 1 hour must elapse before"; :>> isCounted = true; }
    part <'WXC-155'> wxc_155 : WeatherRule { doc /* 2002 A2-207D note [2].A CEILING - GREATER THAN OR EQUAL TO 10K F */ :>> rulebookEdition = "2002"; :>> ruleId = "A2-207D note [2].A"; :>> wxParameter = "ceiling"; :>> wxScene = "deorbit"; :>> wxSite = "any"; :>> wxComparison = "min"; :>> limitValue = 10.0; :>> limitUnit = "K FEET"; :>> ruleCondition = "single APU WX placards: landing sites for 1 or 2 APU/HYD system failures (and th"; :>> isCounted = true; }
    part <'WXC-156'> wxc_156 : WeatherRule { doc /* 2002 A2-207D note [2].B VISIBILITY - GREATER THAN OR EQUAL TO 7  */ :>> rulebookEdition = "2002"; :>> ruleId = "A2-207D note [2].B"; :>> wxParameter = "visibility"; :>> wxScene = "deorbit"; :>> wxSite = "any"; :>> wxComparison = "min"; :>> limitValue = 7.0; :>> limitUnit = "STATUTE MILES"; :>> ruleCondition = "single APU WX placards: landing sites for 1 or 2 APU/HYD system failures (and th"; :>> isCounted = true; }
    part <'WXC-157'> wxc_157 : WeatherRule { doc /* 2002 A2-207D note [2].C CROSSWIND - LESS THAN OR EQUAL TO 10 KNO */ :>> rulebookEdition = "2002"; :>> ruleId = "A2-207D note [2].C"; :>> wxParameter = "crosswind"; :>> wxScene = "deorbit"; :>> wxSite = "any"; :>> wxComparison = "max"; :>> limitValue = 10.0; :>> limitUnit = "KNOTS (PEAK)"; :>> ruleCondition = "single APU WX placards: landing sites for 1 or 2 APU/HYD system failures (and th"; :>> isCounted = true; }
    part <'WXC-158'> wxc_158 : WeatherRule { doc /* 2002 A2-207D note [4] UPPER LEVEL HAC WINDS IN EXCESS OF 80 KN */ :>> rulebookEdition = "2002"; :>> ruleId = "A2-207D note [4]"; :>> wxParameter = "wind_speed"; :>> wxScene = "deorbit"; :>> wxSite = "any"; :>> wxComparison = "other"; :>> limitValue = 80.0; :>> limitUnit = "KNOTS"; :>> ruleCondition = "defines 'unfavorable atmospheric conditions' (upper level HAC winds in excess of"; :>> isCounted = false; }
    part <'WXC-159'> wxc_159 : WeatherRule { doc /* 2002 A2-261 (XWIND DTO NO-GO, GROUND SYSTEMS) XWIND <10 KNOTS PEAK */ :>> rulebookEdition = "2002"; :>> ruleId = "A2-261 (XWIND DTO NO-GO, GROUND SYSTEMS)"; :>> wxParameter = "crosswind"; :>> wxScene = "other"; :>> wxSite = "any"; :>> wxComparison = "min"; :>> limitValue = 10.0; :>> limitUnit = "KNOTS PEAK"; :>> ruleCondition = "crosswind DTO is NO-GO for peak crosswind below 10 knots (not within DTO limits)"; :>> isCounted = true; }
    part <'WXC-160'> wxc_160 : WeatherRule { doc /* 2002 A2-261 (XWIND DTO NO-GO, GROUND SYSTEMS) XWIND >15 KNOTS PEAK */ :>> rulebookEdition = "2002"; :>> ruleId = "A2-261 (XWIND DTO NO-GO, GROUND SYSTEMS)"; :>> wxParameter = "crosswind"; :>> wxScene = "other"; :>> wxSite = "any"; :>> wxComparison = "max"; :>> limitValue = 15.0; :>> limitUnit = "KNOTS PEAK"; :>> ruleCondition = "crosswind DTO is NO-GO for peak crosswind above 15 knots"; :>> isCounted = true; }
    part <'WXC-161'> wxc_161 : WeatherRule { doc /* 2002 A2-261 (XWIND DTO NO-GO, GROUND SYSTEMS) XWIND >10 KNOTS GUST */ :>> rulebookEdition = "2002"; :>> ruleId = "A2-261 (XWIND DTO NO-GO, GROUND SYSTEMS)"; :>> wxParameter = "wind_speed"; :>> wxScene = "other"; :>> wxSite = "any"; :>> wxComparison = "max"; :>> limitValue = 10.0; :>> limitUnit = "KNOTS GUST"; :>> ruleCondition = "crosswind DTO is NO-GO for gusts above 10 knots (gust = above the steady-state w"; :>> isCounted = true; }
    part <'WXC-162'> wxc_162 : WeatherRule { doc /* 2002 A2-262D ABOVE 12 KNOTS PEAK */ :>> rulebookEdition = "2002"; :>> ruleId = "A2-262D"; :>> wxParameter = "crosswind"; :>> wxScene = "other"; :>> wxSite = "any"; :>> wxComparison = "max"; :>> limitValue = 12.0; :>> limitUnit = "KNOTS PEAK"; :>> ruleCondition = "crosswind landing DTO's above 12 knots peak will not be performed on night landi"; :>> isCounted = true; }
    part <'WXC-163'> wxc_163 : WeatherRule { doc /* 2002 A4-107A.6 DAYLIGHT LANDING (SUNRISE MINUS 15 MINUT */ :>> rulebookEdition = "2002"; :>> ruleId = "A4-107A.6"; :>> wxParameter = "other"; :>> wxScene = "landing_eom"; :>> wxSite = "any"; :>> wxComparison = "other"; :>> limitValue = 15.0; :>> limitUnit = "minutes"; :>> ruleCondition = "daylight window = sunrise minus 15 minutes to sunset plus 15 minutes, unless the"; :>> isCounted = false; }
    part <'WXC-164'> wxc_164 : WeatherRule { doc /* 2002 A4-155A SUN POSITION ... WITHIN 10 DEGREES OF CE */ :>> rulebookEdition = "2002"; :>> ruleId = "A4-155A"; :>> wxParameter = "other"; :>> wxScene = "other"; :>> wxSite = "any"; :>> wxComparison = "min"; :>> limitValue = 10.0; :>> limitUnit = "degrees"; :>> ruleCondition = "sun must not be within 10 degrees of the runway centerline in azimuth while its "; :>> isCounted = false; }
    part <'WXC-165'> wxc_165 : WeatherRule { doc /* 2002 A4-155A SUN POSITION ... FROM 0 TO 20 DEGREES EL */ :>> rulebookEdition = "2002"; :>> ruleId = "A4-155A"; :>> wxParameter = "other"; :>> wxScene = "other"; :>> wxSite = "any"; :>> wxComparison = "range"; :>> limitValue = 0.0; :>> limitValueHigh = 20.0; :>> limitUnit = "degrees"; :>> ruleCondition = "sun elevation band 0 to 20 degrees in which the 10-degree azimuth exclusion appl"; :>> isCounted = false; }
    part <'WXC-166'> wxc_166 : WeatherRule { doc /* 2002 A4-210 CROSSWINDS ... 10 KNOTS OR GREATER */ :>> rulebookEdition = "2002"; :>> ruleId = "A4-210"; :>> wxParameter = "crosswind"; :>> wxScene = "landing_eom"; :>> wxSite = "any"; :>> wxComparison = "other"; :>> limitValue = 10.0; :>> limitUnit = "KNOTS"; :>> ruleCondition = "if crosswinds are observed to be 10 knots or greater as the orbiter approaches t"; :>> isCounted = false; }
    part <'WXC-167'> wxc_167 : WeatherRule { doc /* 2002 A6-251C AMBIENT TEMPERATURE AT THE LAUNCH SITE I */ :>> rulebookEdition = "2002"; :>> ruleId = "A6-251C"; :>> wxParameter = "temperature"; :>> wxScene = "launch"; :>> wxSite = "any"; :>> wxComparison = "other"; :>> limitValue = 50.0; :>> limitUnit = "deg F"; :>> ruleCondition = "RCS primary thruster heaters are off for ascent unless the ambient temperature a"; :>> isCounted = false; }
    part <'WXC-168'> wxc_168 : WeatherRule { doc /* 2002 A8-18A CEILINGS > 10K FEET */ :>> rulebookEdition = "2002"; :>> ruleId = "A8-18A"; :>> wxParameter = "ceiling"; :>> wxScene = "other"; :>> wxSite = "any"; :>> wxComparison = "other"; :>> limitValue = 10.0; :>> limitUnit = "K FEET"; :>> ruleCondition = "number of onboard MSBLS required (lakebed / concrete runway) depends on whether "; :>> isCounted = false; }
    part <'WXC-169'> wxc_169 : WeatherRule { doc /* 2002 A8-18A CEILINGS > 15K FEET */ :>> rulebookEdition = "2002"; :>> ruleId = "A8-18A"; :>> wxParameter = "ceiling"; :>> wxScene = "other"; :>> wxSite = "any"; :>> wxComparison = "other"; :>> limitValue = 15.0; :>> limitUnit = "K FEET"; :>> ruleCondition = "number of onboard MSBLS required (lakebed / concrete runway) depends on whether "; :>> isCounted = false; }
    part <'WXC-170'> wxc_170 : WeatherRule { doc /* 2002 A10-144A CROSSWIND > 15 KNOTS PEAK */ :>> rulebookEdition = "2002"; :>> ruleId = "A10-144A"; :>> wxParameter = "crosswind"; :>> wxScene = "other"; :>> wxSite = "any"; :>> wxComparison = "max"; :>> limitValue = 15.0; :>> limitUnit = "KNOTS PEAK"; :>> ruleCondition = "the drag chute will not be deployed if crosswind is greater than 15 knots peak"; :>> isCounted = true; }
    part <'WXC-171'> wxc_171 : WeatherRule { doc /* 2002 A16-10A LIGHTNING WITHIN 5 MILES */ :>> rulebookEdition = "2002"; :>> ruleId = "A16-10A"; :>> wxParameter = "lightning_distance"; :>> wxScene = "other"; :>> wxSite = "any"; :>> wxComparison = "min"; :>> limitValue = 5.0; :>> limitUnit = "MILES"; :>> ruleCondition = "normal postlanding operations will be continued except for lightning within 5 mi"; :>> isCounted = true; }
    part <'WXC-172'> wxc_172 : WeatherRule { doc /* 2010 G417.5(a) electric field measurement */ :>> rulebookEdition = "2010"; :>> ruleId = "G417.5(a)"; :>> wxParameter = "electric_field"; :>> wxScene = "launch"; :>> wxSite = "any"; :>> wxComparison = "max"; :>> limitValue = 1500.0; :>> limitUnit = "V/m"; :>> ruleCondition = "absolute value of any electric field measurement within 5 nmi of the flight path"; :>> isCounted = true; }
    part <'WXC-173'> wxc_173 : WeatherRule { doc /* 2010 G417.5(a) waiting time after field reached the lim */ :>> rulebookEdition = "2010"; :>> ruleId = "G417.5(a)"; :>> wxParameter = "other"; :>> wxScene = "launch"; :>> wxSite = "any"; :>> wxComparison = "min"; :>> limitValue = 15.0; :>> limitUnit = "minutes"; :>> ruleCondition = "after the field measurement has reached 1500 V/m"; :>> isCounted = true; }
    part <'WXC-174'> wxc_174 : WeatherRule { doc /* 2010 G417.5(a) distance of electric field measurement f */ :>> rulebookEdition = "2010"; :>> ruleId = "G417.5(a)"; :>> wxParameter = "other"; :>> wxScene = "launch"; :>> wxSite = "any"; :>> wxComparison = "max"; :>> limitValue = 5.0; :>> limitUnit = "nautical miles"; :>> ruleCondition = "which measurements apply"; :>> isCounted = false; }
    part <'WXC-175'> wxc_175 : WeatherRule { doc /* 2010 G417.5(b) electric field measurement */ :>> rulebookEdition = "2010"; :>> ruleId = "G417.5(b)"; :>> wxParameter = "electric_field"; :>> wxScene = "launch"; :>> wxSite = "any"; :>> wxComparison = "max"; :>> limitValue = 1000.0; :>> limitUnit = "V/m"; :>> ruleCondition = "absolute value of any electric field measurement within 5 nmi of the flight path"; :>> isCounted = true; }
    part <'WXC-176'> wxc_176 : WeatherRule { doc /* 2010 G417.5(b) waiting time after field reached the lim */ :>> rulebookEdition = "2010"; :>> ruleId = "G417.5(b)"; :>> wxParameter = "other"; :>> wxScene = "launch"; :>> wxSite = "any"; :>> wxComparison = "min"; :>> limitValue = 15.0; :>> limitUnit = "minutes"; :>> ruleCondition = "after the field measurement has reached 1000 V/m"; :>> isCounted = true; }
    part <'WXC-177'> wxc_177 : WeatherRule { doc /* 2010 G417.5(b) distance of electric field measurement f */ :>> rulebookEdition = "2010"; :>> ruleId = "G417.5(b)"; :>> wxParameter = "other"; :>> wxScene = "launch"; :>> wxSite = "any"; :>> wxComparison = "max"; :>> limitValue = 5.0; :>> limitUnit = "nautical miles"; :>> ruleCondition = "which measurements apply"; :>> isCounted = false; }
    part <'WXC-178'> wxc_178 : WeatherRule { doc /* 2010 G417.5(b)(1) distance of clouds from flight path (all */ :>> rulebookEdition = "2010"; :>> ruleId = "G417.5(b)(1)"; :>> wxParameter = "other"; :>> wxScene = "launch"; :>> wxSite = "any"; :>> wxComparison = "max"; :>> limitValue = 10.0; :>> limitUnit = "nautical miles"; :>> ruleCondition = "exception: all clouds within this distance of the flight path are transparent"; :>> isCounted = true; }
    part <'WXC-179'> wxc_179 : WeatherRule { doc /* 2010 G417.5(b)(2) distance of clouds from flight path (top */ :>> rulebookEdition = "2010"; :>> ruleId = "G417.5(b)(2)"; :>> wxParameter = "other"; :>> wxScene = "launch"; :>> wxSite = "any"; :>> wxComparison = "max"; :>> limitValue = 10.0; :>> limitUnit = "nautical miles"; :>> ruleCondition = "exception: all clouds within this distance of the flight path meet the cloud-top"; :>> isCounted = true; }
    part <'WXC-180'> wxc_180 : WeatherRule { doc /* 2010 G417.5(b)(2) cloud top temperature (warmer than) */ :>> rulebookEdition = "2010"; :>> ruleId = "G417.5(b)(2)"; :>> wxParameter = "temperature"; :>> wxScene = "launch"; :>> wxSite = "any"; :>> wxComparison = "min"; :>> limitValue = 5.0; :>> limitUnit = "degrees Celsius"; :>> ruleCondition = "exception: cloud tops of all clouds within 10 nmi"; :>> isCounted = true; }
    part <'WXC-181'> wxc_181 : WeatherRule { doc /* 2010 G417.5(b)(2) cloud top temperature of convective clou */ :>> rulebookEdition = "2010"; :>> ruleId = "G417.5(b)(2)"; :>> wxParameter = "temperature"; :>> wxScene = "launch"; :>> wxSite = "any"; :>> wxComparison = "min"; :>> limitValue = -10.0; :>> limitUnit = "degrees Celsius"; :>> ruleCondition = "exception: clouds have not been part of convective clouds with tops this cold du"; :>> isCounted = true; }
    part <'WXC-182'> wxc_182 : WeatherRule { doc /* 2010 G417.5(b)(2) look-back time for convective cloud with */ :>> rulebookEdition = "2010"; :>> ruleId = "G417.5(b)(2)"; :>> wxParameter = "other"; :>> wxScene = "launch"; :>> wxSite = "any"; :>> wxComparison = "min"; :>> limitValue = 3.0; :>> limitUnit = "hours"; :>> ruleCondition = "exception: look-back period"; :>> isCounted = true; }
    part <'WXC-183'> wxc_183 : WeatherRule { doc /* 2010 G417.7(a) waiting time after lightning in a thunde */ :>> rulebookEdition = "2010"; :>> ruleId = "G417.7(a)"; :>> wxParameter = "other"; :>> wxScene = "launch"; :>> wxSite = "any"; :>> wxComparison = "min"; :>> limitValue = 30.0; :>> limitUnit = "minutes"; :>> ruleCondition = "any type of lightning in a thunderstorm; flight path within 10 nmi of that thund"; :>> isCounted = true; }
    part <'WXC-184'> wxc_184 : WeatherRule { doc /* 2010 G417.7(a) distance of flight path from thunderstor */ :>> rulebookEdition = "2010"; :>> ruleId = "G417.7(a)"; :>> wxParameter = "thunderstorm"; :>> wxScene = "launch"; :>> wxSite = "any"; :>> wxComparison = "min"; :>> limitValue = 10.0; :>> limitUnit = "nautical miles"; :>> ruleCondition = "after lightning in the thunderstorm; an attached anvil cloud is not part of its "; :>> isCounted = true; }
    part <'WXC-185'> wxc_185 : WeatherRule { doc /* 2010 G417.7(b) waiting time after lightning */ :>> rulebookEdition = "2010"; :>> ruleId = "G417.7(b)"; :>> wxParameter = "other"; :>> wxScene = "launch"; :>> wxSite = "any"; :>> wxComparison = "min"; :>> limitValue = 30.0; :>> limitUnit = "minutes"; :>> ruleCondition = "any type of lightning within 10 nmi of the flight path; unless (b)(1)-(3) all sa"; :>> isCounted = true; }
    part <'WXC-186'> wxc_186 : WeatherRule { doc /* 2010 G417.7(b) distance of lightning from flight path */ :>> rulebookEdition = "2010"; :>> ruleId = "G417.7(b)"; :>> wxParameter = "lightning_distance"; :>> wxScene = "launch"; :>> wxSite = "any"; :>> wxComparison = "min"; :>> limitValue = 10.0; :>> limitUnit = "nautical miles"; :>> ruleCondition = "any type of lightning; unless all three of (b)(1)-(3) satisfied"; :>> isCounted = true; }
    part <'WXC-187'> wxc_187 : WeatherRule { doc /* 2010 G417.7(b)(1) distance of the lightning-producing clou */ :>> rulebookEdition = "2010"; :>> ruleId = "G417.7(b)(1)"; :>> wxParameter = "other"; :>> wxScene = "launch"; :>> wxSite = "any"; :>> wxComparison = "min"; :>> limitValue = 10.0; :>> limitUnit = "nautical miles"; :>> ruleCondition = "exception: the cloud that produced the lightning"; :>> isCounted = true; }
    part <'WXC-188'> wxc_188 : WeatherRule { doc /* 2010 G417.7(b)(2) distance of working field mill from each */ :>> rulebookEdition = "2010"; :>> ruleId = "G417.7(b)(2)"; :>> wxParameter = "other"; :>> wxScene = "launch"; :>> wxSite = "any"; :>> wxComparison = "max"; :>> limitValue = 5.0; :>> limitUnit = "nautical miles"; :>> ruleCondition = "exception: at least one working field mill"; :>> isCounted = false; }
    part <'WXC-189'> wxc_189 : WeatherRule { doc /* 2010 G417.7(b)(3) electric field measurement */ :>> rulebookEdition = "2010"; :>> ruleId = "G417.7(b)(3)"; :>> wxParameter = "electric_field"; :>> wxScene = "launch"; :>> wxSite = "any"; :>> wxComparison = "max"; :>> limitValue = 1000.0; :>> limitUnit = "V/m"; :>> ruleCondition = "exception: absolute values of all measurements within 5 nmi of the flight path a"; :>> isCounted = true; }
    part <'WXC-190'> wxc_190 : WeatherRule { doc /* 2010 G417.7(b)(3) duration the field has been below the li */ :>> rulebookEdition = "2010"; :>> ruleId = "G417.7(b)(3)"; :>> wxParameter = "other"; :>> wxScene = "launch"; :>> wxSite = "any"; :>> wxComparison = "min"; :>> limitValue = 15.0; :>> limitUnit = "minutes"; :>> ruleCondition = "exception: electric field measurements below 1000 V/m"; :>> isCounted = true; }
    part <'WXC-191'> wxc_191 : WeatherRule { doc /* 2010 G417.7(b)(3) distance of electric field measurement f */ :>> rulebookEdition = "2010"; :>> ruleId = "G417.7(b)(3)"; :>> wxParameter = "other"; :>> wxScene = "launch"; :>> wxSite = "any"; :>> wxComparison = "max"; :>> limitValue = 5.0; :>> limitUnit = "nautical miles"; :>> ruleCondition = "which measurements apply"; :>> isCounted = false; }
    part <'WXC-192'> wxc_192 : WeatherRule { doc /* 2010 G417.9(a) distance of flight path from cumulus clo */ :>> rulebookEdition = "2010"; :>> ruleId = "G417.9(a)"; :>> wxParameter = "other"; :>> wxScene = "launch"; :>> wxSite = "any"; :>> wxComparison = "min"; :>> limitValue = 10.0; :>> limitUnit = "nautical miles"; :>> ruleCondition = "cumulus cloud with cloud top colder than or equal to -20 C"; :>> isCounted = true; }
    part <'WXC-193'> wxc_193 : WeatherRule { doc /* 2010 G417.9(a) cloud top temperature (cumulus) */ :>> rulebookEdition = "2010"; :>> ruleId = "G417.9(a)"; :>> wxParameter = "temperature"; :>> wxScene = "launch"; :>> wxSite = "any"; :>> wxComparison = "min"; :>> limitValue = -20.0; :>> limitUnit = "degrees Celsius"; :>> ruleCondition = "cloud top colder than or equal to this triggers the standoff"; :>> isCounted = true; }
    part <'WXC-194'> wxc_194 : WeatherRule { doc /* 2010 G417.9(b) distance of flight path from cumulus clo */ :>> rulebookEdition = "2010"; :>> ruleId = "G417.9(b)"; :>> wxParameter = "other"; :>> wxScene = "launch"; :>> wxSite = "any"; :>> wxComparison = "min"; :>> limitValue = 5.0; :>> limitUnit = "nautical miles"; :>> ruleCondition = "cumulus cloud with cloud top colder than or equal to -10 C"; :>> isCounted = true; }
    part <'WXC-195'> wxc_195 : WeatherRule { doc /* 2010 G417.9(b) cloud top temperature (cumulus) */ :>> rulebookEdition = "2010"; :>> ruleId = "G417.9(b)"; :>> wxParameter = "temperature"; :>> wxScene = "launch"; :>> wxSite = "any"; :>> wxComparison = "min"; :>> limitValue = -10.0; :>> limitUnit = "degrees Celsius"; :>> ruleCondition = "cloud top colder than or equal to this triggers the standoff"; :>> isCounted = true; }
    part <'WXC-196'> wxc_196 : WeatherRule { doc /* 2010 G417.9(c) cloud top temperature (cumulus, flight t */ :>> rulebookEdition = "2010"; :>> ruleId = "G417.9(c)"; :>> wxParameter = "temperature"; :>> wxScene = "launch"; :>> wxSite = "any"; :>> wxComparison = "min"; :>> limitValue = -5.0; :>> limitUnit = "degrees Celsius"; :>> ruleCondition = "flight path through any cumulus cloud whose top is colder than or equal to this"; :>> isCounted = true; }
    part <'WXC-197'> wxc_197 : WeatherRule { doc /* 2010 G417.9(d) cloud top temperature band (cumulus, fli */ :>> rulebookEdition = "2010"; :>> ruleId = "G417.9(d)"; :>> wxParameter = "temperature"; :>> wxScene = "launch"; :>> wxSite = "any"; :>> wxComparison = "range"; :>> limitValue = -5.0; :>> limitValueHigh = 5.0; :>> limitUnit = "degrees Celsius"; :>> ruleCondition = "flight through cumulus with top warmer than -5 C to colder than or equal to +5 C"; :>> isCounted = true; }
    part <'WXC-198'> wxc_198 : WeatherRule { doc /* 2010 G417.9(d)(2) distance from center of cloud top to a w */ :>> rulebookEdition = "2010"; :>> ruleId = "G417.9(d)(2)"; :>> wxParameter = "other"; :>> wxScene = "launch"; :>> wxSite = "any"; :>> wxComparison = "max"; :>> limitValue = 2.0; :>> limitUnit = "nautical miles"; :>> ruleCondition = "exception condition: at least one working field mill"; :>> isCounted = false; }
    part <'WXC-199'> wxc_199 : WeatherRule { doc /* 2010 G417.9(d)(3) electric field measurement band */ :>> rulebookEdition = "2010"; :>> ruleId = "G417.9(d)(3)"; :>> wxParameter = "electric_field"; :>> wxScene = "launch"; :>> wxSite = "any"; :>> wxComparison = "range"; :>> limitValue = -100.0; :>> limitValueHigh = 500.0; :>> limitUnit = "V/m"; :>> ruleCondition = "exception: all measurements within 5 nmi of the flight path and at each field mi"; :>> isCounted = true; }
    part <'WXC-200'> wxc_200 : WeatherRule { doc /* 2010 G417.9(d)(3) duration the field has been inside the b */ :>> rulebookEdition = "2010"; :>> ruleId = "G417.9(d)(3)"; :>> wxParameter = "other"; :>> wxScene = "launch"; :>> wxSite = "any"; :>> wxComparison = "min"; :>> limitValue = 15.0; :>> limitUnit = "minutes"; :>> ruleCondition = "exception: electric field measurements inside -100..+500 V/m"; :>> isCounted = true; }
    part <'WXC-201'> wxc_201 : WeatherRule { doc /* 2010 G417.9(d)(3) distance of electric field measurement f */ :>> rulebookEdition = "2010"; :>> ruleId = "G417.9(d)(3)"; :>> wxParameter = "other"; :>> wxScene = "launch"; :>> wxSite = "any"; :>> wxComparison = "max"; :>> limitValue = 5.0; :>> limitUnit = "nautical miles"; :>> ruleCondition = "which measurements apply"; :>> isCounted = false; }
    part <'WXC-202'> wxc_202 : WeatherRule { doc /* 2010 G417.11(a) distance band of flight path from attach */ :>> rulebookEdition = "2010"; :>> ruleId = "G417.11(a)"; :>> wxParameter = "other"; :>> wxScene = "launch"; :>> wxSite = "any"; :>> wxComparison = "range"; :>> limitValue = 5.0; :>> limitValueHigh = 10.0; :>> limitUnit = "nautical miles"; :>> ruleCondition = "attached anvil cloud; first 30 minutes after the last lightning discharge in or "; :>> isCounted = true; }
    part <'WXC-203'> wxc_203 : WeatherRule { doc /* 2010 G417.11(a) waiting time after last lightning in or  */ :>> rulebookEdition = "2010"; :>> ruleId = "G417.11(a)"; :>> wxParameter = "other"; :>> wxScene = "launch"; :>> wxSite = "any"; :>> wxComparison = "min"; :>> limitValue = 30.0; :>> limitUnit = "minutes"; :>> ruleCondition = "band 5-10 nmi from attached anvil"; :>> isCounted = true; }
    part <'WXC-204'> wxc_204 : WeatherRule { doc /* 2010 G417.11(a) temperature of altitudes of anvil portio */ :>> rulebookEdition = "2010"; :>> ruleId = "G417.11(a)"; :>> wxParameter = "temperature"; :>> wxScene = "launch"; :>> wxSite = "any"; :>> wxComparison = "max"; :>> limitValue = 0.0; :>> limitUnit = "degrees Celsius"; :>> ruleCondition = "exception: the portion of the attached anvil within 10 nmi of the flight path lo"; :>> isCounted = true; }
    part <'WXC-205'> wxc_205 : WeatherRule { doc /* 2010 G417.11(b) distance band of flight path from attach */ :>> rulebookEdition = "2010"; :>> ruleId = "G417.11(b)"; :>> wxParameter = "other"; :>> wxScene = "launch"; :>> wxSite = "any"; :>> wxComparison = "range"; :>> limitValue = 3.0; :>> limitValueHigh = 5.0; :>> limitUnit = "nautical miles"; :>> ruleCondition = "attached anvil cloud; first three hours after the last lightning discharge"; :>> isCounted = true; }
    part <'WXC-206'> wxc_206 : WeatherRule { doc /* 2010 G417.11(b) waiting time after last lightning in or  */ :>> rulebookEdition = "2010"; :>> ruleId = "G417.11(b)"; :>> wxParameter = "other"; :>> wxScene = "launch"; :>> wxSite = "any"; :>> wxComparison = "min"; :>> limitValue = 3.0; :>> limitUnit = "hours"; :>> ruleCondition = "band 3-5 nmi from attached anvil"; :>> isCounted = true; }
    part <'WXC-207'> wxc_207 : WeatherRule { doc /* 2010 G417.11(b) temperature of altitudes of anvil portio */ :>> rulebookEdition = "2010"; :>> ruleId = "G417.11(b)"; :>> wxParameter = "temperature"; :>> wxScene = "launch"; :>> wxSite = "any"; :>> wxComparison = "max"; :>> limitValue = 0.0; :>> limitUnit = "degrees Celsius"; :>> ruleCondition = "exception: the portion of the attached anvil within 5 nmi of the flight path loc"; :>> isCounted = true; }
    part <'WXC-208'> wxc_208 : WeatherRule { doc /* 2010 G417.11(c) distance of flight path from attached an */ :>> rulebookEdition = "2010"; :>> ruleId = "G417.11(c)"; :>> wxParameter = "other"; :>> wxScene = "launch"; :>> wxSite = "any"; :>> wxComparison = "min"; :>> limitValue = 3.0; :>> limitUnit = "nautical miles"; :>> ruleCondition = "attached anvil cloud; unless (c)(1)-(3) all satisfied"; :>> isCounted = true; }
    part <'WXC-209'> wxc_209 : WeatherRule { doc /* 2010 G417.11(c)(1) temperature of altitudes of anvil portio */ :>> rulebookEdition = "2010"; :>> ruleId = "G417.11(c)(1)"; :>> wxParameter = "temperature"; :>> wxScene = "launch"; :>> wxSite = "any"; :>> wxComparison = "max"; :>> limitValue = 0.0; :>> limitUnit = "degrees Celsius"; :>> ruleCondition = "exception: portion of the attached anvil within 5 nmi of the flight path located"; :>> isCounted = true; }
    part <'WXC-210'> wxc_210 : WeatherRule { doc /* 2010 G417.11(c)(1) distance of anvil portion from flight pa */ :>> rulebookEdition = "2010"; :>> ruleId = "G417.11(c)(1)"; :>> wxParameter = "other"; :>> wxScene = "launch"; :>> wxSite = "any"; :>> wxComparison = "max"; :>> limitValue = 5.0; :>> limitUnit = "nautical miles"; :>> ruleCondition = "exception: the portion of the attached anvil considered"; :>> isCounted = true; }
    part <'WXC-211'> wxc_211 : WeatherRule { doc /* 2010 G417.11(c)(2) volume-averaged, height-integrated radar */ :>> rulebookEdition = "2010"; :>> ruleId = "G417.11(c)(2)"; :>> wxParameter = "other"; :>> wxScene = "launch"; :>> wxSite = "any"; :>> wxComparison = "max"; :>> limitValue = 10.0; :>> limitUnit = "dBZ-km"; :>> ruleCondition = "exception: at every point within 1 nmi of the flight path (also written +33 dBZ-"; :>> isCounted = true; }
    part <'WXC-212'> wxc_212 : WeatherRule { doc /* 2010 G417.11(c)(2) distance of VAHIRR evaluation points fro */ :>> rulebookEdition = "2010"; :>> ruleId = "G417.11(c)(2)"; :>> wxParameter = "other"; :>> wxScene = "launch"; :>> wxSite = "any"; :>> wxComparison = "max"; :>> limitValue = 1.0; :>> limitUnit = "nautical miles"; :>> ruleCondition = "exception: VAHIRR criterion applies at every point within this distance"; :>> isCounted = false; }
    part <'WXC-213'> wxc_213 : WeatherRule { doc /* 2010 G417.13(a) distance band of flight path from detach */ :>> rulebookEdition = "2010"; :>> ruleId = "G417.13(a)"; :>> wxParameter = "other"; :>> wxScene = "launch"; :>> wxSite = "any"; :>> wxComparison = "range"; :>> limitValue = 3.0; :>> limitValueHigh = 10.0; :>> limitUnit = "nautical miles"; :>> ruleCondition = "detached anvil cloud; first 30 minutes after the last lightning discharge"; :>> isCounted = true; }
    part <'WXC-214'> wxc_214 : WeatherRule { doc /* 2010 G417.13(a) waiting time after last lightning in or  */ :>> rulebookEdition = "2010"; :>> ruleId = "G417.13(a)"; :>> wxParameter = "other"; :>> wxScene = "launch"; :>> wxSite = "any"; :>> wxComparison = "min"; :>> limitValue = 30.0; :>> limitUnit = "minutes"; :>> ruleCondition = "band 3-10 nmi from detached anvil"; :>> isCounted = true; }
    part <'WXC-215'> wxc_215 : WeatherRule { doc /* 2010 G417.13(a) temperature of altitudes of anvil portio */ :>> rulebookEdition = "2010"; :>> ruleId = "G417.13(a)"; :>> wxParameter = "temperature"; :>> wxScene = "launch"; :>> wxSite = "any"; :>> wxComparison = "max"; :>> limitValue = 0.0; :>> limitUnit = "degrees Celsius"; :>> ruleCondition = "exception: the portion of the detached anvil within 10 nmi of the flight path lo"; :>> isCounted = true; }
    part <'WXC-216'> wxc_216 : WeatherRule { doc /* 2010 G417.13(b) distance band of flight path from detach */ :>> rulebookEdition = "2010"; :>> ruleId = "G417.13(b)"; :>> wxParameter = "other"; :>> wxScene = "launch"; :>> wxSite = "any"; :>> wxComparison = "range"; :>> limitValue = 0.0; :>> limitValueHigh = 3.0; :>> limitUnit = "nautical miles"; :>> ruleCondition = "detached anvil cloud; first 30 minutes after the last lightning discharge; unles"; :>> isCounted = true; }
    part <'WXC-217'> wxc_217 : WeatherRule { doc /* 2010 G417.13(b) waiting time after last lightning */ :>> rulebookEdition = "2010"; :>> ruleId = "G417.13(b)"; :>> wxParameter = "other"; :>> wxScene = "launch"; :>> wxSite = "any"; :>> wxComparison = "min"; :>> limitValue = 30.0; :>> limitUnit = "minutes"; :>> ruleCondition = "band 0-3 nmi from detached anvil"; :>> isCounted = true; }
    part <'WXC-218'> wxc_218 : WeatherRule { doc /* 2010 G417.13(b)(1) temperature of altitudes of anvil portio */ :>> rulebookEdition = "2010"; :>> ruleId = "G417.13(b)(1)"; :>> wxParameter = "temperature"; :>> wxScene = "launch"; :>> wxSite = "any"; :>> wxComparison = "max"; :>> limitValue = 0.0; :>> limitUnit = "degrees Celsius"; :>> ruleCondition = "exception: portion of the detached anvil within 5 nmi of the flight path entirel"; :>> isCounted = true; }
    part <'WXC-219'> wxc_219 : WeatherRule { doc /* 2010 G417.13(b)(1) distance of anvil portion from flight pa */ :>> rulebookEdition = "2010"; :>> ruleId = "G417.13(b)(1)"; :>> wxParameter = "other"; :>> wxScene = "launch"; :>> wxSite = "any"; :>> wxComparison = "max"; :>> limitValue = 5.0; :>> limitUnit = "nautical miles"; :>> ruleCondition = "exception: the portion of the detached anvil considered"; :>> isCounted = true; }
    part <'WXC-220'> wxc_220 : WeatherRule { doc /* 2010 G417.13(b)(2) volume-averaged, height-integrated radar */ :>> rulebookEdition = "2010"; :>> ruleId = "G417.13(b)(2)"; :>> wxParameter = "other"; :>> wxScene = "launch"; :>> wxSite = "any"; :>> wxComparison = "max"; :>> limitValue = 10.0; :>> limitUnit = "dBZ-km"; :>> ruleCondition = "exception: at every point within 1 nmi of the flight path (also written +33 dBZ-"; :>> isCounted = true; }
    part <'WXC-221'> wxc_221 : WeatherRule { doc /* 2010 G417.13(b)(2) distance of VAHIRR evaluation points fro */ :>> rulebookEdition = "2010"; :>> ruleId = "G417.13(b)(2)"; :>> wxParameter = "other"; :>> wxScene = "launch"; :>> wxSite = "any"; :>> wxComparison = "max"; :>> limitValue = 1.0; :>> limitUnit = "nautical miles"; :>> ruleCondition = "exception: VAHIRR criterion applies at every point within this distance"; :>> isCounted = false; }
    part <'WXC-222'> wxc_222 : WeatherRule { doc /* 2010 G417.13(c) distance band of flight path from detach */ :>> rulebookEdition = "2010"; :>> ruleId = "G417.13(c)"; :>> wxParameter = "other"; :>> wxScene = "launch"; :>> wxSite = "any"; :>> wxComparison = "range"; :>> limitValue = 0.0; :>> limitValueHigh = 3.0; :>> limitUnit = "nautical miles"; :>> ruleCondition = "detached anvil cloud; after the first 30 minutes up to 3 hours after the last li"; :>> isCounted = true; }
    part <'WXC-223'> wxc_223 : WeatherRule { doc /* 2010 G417.13(c) period after last lightning: upper end */ :>> rulebookEdition = "2010"; :>> ruleId = "G417.13(c)"; :>> wxParameter = "other"; :>> wxScene = "launch"; :>> wxSite = "any"; :>> wxComparison = "max"; :>> limitValue = 3.0; :>> limitUnit = "hours"; :>> ruleCondition = "period during which (c) applies"; :>> isCounted = true; }
    part <'WXC-224'> wxc_224 : WeatherRule { doc /* 2010 G417.13(c) period after last lightning: lower end */ :>> rulebookEdition = "2010"; :>> ruleId = "G417.13(c)"; :>> wxParameter = "other"; :>> wxScene = "launch"; :>> wxSite = "any"; :>> wxComparison = "min"; :>> limitValue = 30.0; :>> limitUnit = "minutes"; :>> ruleCondition = "period during which (c) applies"; :>> isCounted = true; }
    part <'WXC-225'> wxc_225 : WeatherRule { doc /* 2010 G417.13(c)(1)(i) distance of working field mill from the  */ :>> rulebookEdition = "2010"; :>> ruleId = "G417.13(c)(1)(i)"; :>> wxParameter = "other"; :>> wxScene = "launch"; :>> wxSite = "any"; :>> wxComparison = "max"; :>> limitValue = 5.0; :>> limitUnit = "nautical miles"; :>> ruleCondition = "exception (c)(1): at least one working field mill"; :>> isCounted = false; }
    part <'WXC-226'> wxc_226 : WeatherRule { doc /* 2010 G417.13(c)(1)(ii) electric field measurement */ :>> rulebookEdition = "2010"; :>> ruleId = "G417.13(c)(1)(ii)"; :>> wxParameter = "electric_field"; :>> wxScene = "launch"; :>> wxSite = "any"; :>> wxComparison = "max"; :>> limitValue = 1000.0; :>> limitUnit = "V/m"; :>> ruleCondition = "exception (c)(1): absolute values of all measurements within 5 nmi of the flight"; :>> isCounted = true; }
    part <'WXC-227'> wxc_227 : WeatherRule { doc /* 2010 G417.13(c)(1)(ii) duration the field has been below the li */ :>> rulebookEdition = "2010"; :>> ruleId = "G417.13(c)(1)(ii)"; :>> wxParameter = "other"; :>> wxScene = "launch"; :>> wxSite = "any"; :>> wxComparison = "min"; :>> limitValue = 15.0; :>> limitUnit = "minutes"; :>> ruleCondition = "exception (c)(1)"; :>> isCounted = true; }
    part <'WXC-228'> wxc_228 : WeatherRule { doc /* 2010 G417.13(c)(1)(ii) distance of electric field measurement f */ :>> rulebookEdition = "2010"; :>> ruleId = "G417.13(c)(1)(ii)"; :>> wxParameter = "other"; :>> wxScene = "launch"; :>> wxSite = "any"; :>> wxComparison = "max"; :>> limitValue = 5.0; :>> limitUnit = "nautical miles"; :>> ruleCondition = "which measurements apply"; :>> isCounted = false; }
    part <'WXC-229'> wxc_229 : WeatherRule { doc /* 2010 G417.13(c)(1)(iii) maximum radar reflectivity of the detach */ :>> rulebookEdition = "2010"; :>> ruleId = "G417.13(c)(1)(iii)"; :>> wxParameter = "other"; :>> wxScene = "launch"; :>> wxSite = "any"; :>> wxComparison = "max"; :>> limitValue = 10.0; :>> limitUnit = "dBZ"; :>> ruleCondition = "exception (c)(1): has been below this value for 15 minutes"; :>> isCounted = true; }
    part <'WXC-230'> wxc_230 : WeatherRule { doc /* 2010 G417.13(c)(1)(iii) duration reflectivity has been below the */ :>> rulebookEdition = "2010"; :>> ruleId = "G417.13(c)(1)(iii)"; :>> wxParameter = "other"; :>> wxScene = "launch"; :>> wxSite = "any"; :>> wxComparison = "min"; :>> limitValue = 15.0; :>> limitUnit = "minutes"; :>> ruleCondition = "exception (c)(1)"; :>> isCounted = true; }
    part <'WXC-231'> wxc_231 : WeatherRule { doc /* 2010 G417.13(c)(1)(iii) distance of detached anvil part (radar m */ :>> rulebookEdition = "2010"; :>> ruleId = "G417.13(c)(1)(iii)"; :>> wxParameter = "other"; :>> wxScene = "launch"; :>> wxSite = "any"; :>> wxComparison = "max"; :>> limitValue = 5.0; :>> limitUnit = "nautical miles"; :>> ruleCondition = "which part of the anvil counts"; :>> isCounted = false; }
    part <'WXC-232'> wxc_232 : WeatherRule { doc /* 2010 G417.13(c)(2)(i) temperature of altitudes of anvil portio */ :>> rulebookEdition = "2010"; :>> ruleId = "G417.13(c)(2)(i)"; :>> wxParameter = "temperature"; :>> wxScene = "launch"; :>> wxSite = "any"; :>> wxComparison = "max"; :>> limitValue = 0.0; :>> limitUnit = "degrees Celsius"; :>> ruleCondition = "exception (c)(2): portion within 5 nmi of the flight path entirely at altitudes "; :>> isCounted = true; }
    part <'WXC-233'> wxc_233 : WeatherRule { doc /* 2010 G417.13(c)(2)(i) distance of anvil portion from flight pa */ :>> rulebookEdition = "2010"; :>> ruleId = "G417.13(c)(2)(i)"; :>> wxParameter = "other"; :>> wxScene = "launch"; :>> wxSite = "any"; :>> wxComparison = "max"; :>> limitValue = 5.0; :>> limitUnit = "nautical miles"; :>> ruleCondition = "exception (c)(2)"; :>> isCounted = true; }
    part <'WXC-234'> wxc_234 : WeatherRule { doc /* 2010 G417.13(c)(2)(ii) volume-averaged, height-integrated radar */ :>> rulebookEdition = "2010"; :>> ruleId = "G417.13(c)(2)(ii)"; :>> wxParameter = "other"; :>> wxScene = "launch"; :>> wxSite = "any"; :>> wxComparison = "max"; :>> limitValue = 10.0; :>> limitUnit = "dBZ-km"; :>> ruleCondition = "exception (c)(2): at every point within 1 nmi of the flight path (also written +"; :>> isCounted = true; }
    part <'WXC-235'> wxc_235 : WeatherRule { doc /* 2010 G417.13(c)(2)(ii) distance of VAHIRR evaluation points fro */ :>> rulebookEdition = "2010"; :>> ruleId = "G417.13(c)(2)(ii)"; :>> wxParameter = "other"; :>> wxScene = "launch"; :>> wxSite = "any"; :>> wxComparison = "max"; :>> limitValue = 1.0; :>> limitUnit = "nautical miles"; :>> ruleCondition = "exception (c)(2)"; :>> isCounted = false; }
    part <'WXC-236'> wxc_236 : WeatherRule { doc /* 2010 G417.13(d)(1)(i) time since last lightning in or from the */ :>> rulebookEdition = "2010"; :>> ruleId = "G417.13(d)(1)(i)"; :>> wxParameter = "other"; :>> wxScene = "launch"; :>> wxSite = "any"; :>> wxComparison = "min"; :>> limitValue = 4.0; :>> limitUnit = "hours"; :>> ruleCondition = "flight path through a detached anvil cloud; exception (d)(1)"; :>> isCounted = true; }
    part <'WXC-237'> wxc_237 : WeatherRule { doc /* 2010 G417.13(d)(1)(ii) time since the anvil cloud was observed  */ :>> rulebookEdition = "2010"; :>> ruleId = "G417.13(d)(1)(ii)"; :>> wxParameter = "other"; :>> wxScene = "launch"; :>> wxSite = "any"; :>> wxComparison = "min"; :>> limitValue = 3.0; :>> limitUnit = "hours"; :>> ruleCondition = "flight path through a detached anvil cloud; exception (d)(1)"; :>> isCounted = true; }
    part <'WXC-238'> wxc_238 : WeatherRule { doc /* 2010 G417.13(d)(2)(i) temperature of altitudes of anvil portio */ :>> rulebookEdition = "2010"; :>> ruleId = "G417.13(d)(2)(i)"; :>> wxParameter = "temperature"; :>> wxScene = "launch"; :>> wxSite = "any"; :>> wxComparison = "max"; :>> limitValue = 0.0; :>> limitUnit = "degrees Celsius"; :>> ruleCondition = "exception (d)(2): portion within 5 nmi of the flight path entirely at altitudes "; :>> isCounted = true; }
    part <'WXC-239'> wxc_239 : WeatherRule { doc /* 2010 G417.13(d)(2)(i) distance of anvil portion from flight pa */ :>> rulebookEdition = "2010"; :>> ruleId = "G417.13(d)(2)(i)"; :>> wxParameter = "other"; :>> wxScene = "launch"; :>> wxSite = "any"; :>> wxComparison = "max"; :>> limitValue = 5.0; :>> limitUnit = "nautical miles"; :>> ruleCondition = "exception (d)(2)"; :>> isCounted = true; }
    part <'WXC-240'> wxc_240 : WeatherRule { doc /* 2010 G417.13(d)(2)(ii) volume-averaged, height-integrated radar */ :>> rulebookEdition = "2010"; :>> ruleId = "G417.13(d)(2)(ii)"; :>> wxParameter = "other"; :>> wxScene = "launch"; :>> wxSite = "any"; :>> wxComparison = "max"; :>> limitValue = 10.0; :>> limitUnit = "dBZ-km"; :>> ruleCondition = "exception (d)(2): everywhere along the flight path (also written +33 dBZ-kft)"; :>> isCounted = true; }
    part <'WXC-241'> wxc_241 : WeatherRule { doc /* 2010 G417.15(a) distance band of flight path from debris */ :>> rulebookEdition = "2010"; :>> ruleId = "G417.15(a)"; :>> wxParameter = "other"; :>> wxScene = "launch"; :>> wxSite = "any"; :>> wxComparison = "range"; :>> limitValue = 0.0; :>> limitValueHigh = 3.0; :>> limitUnit = "nautical miles"; :>> ruleCondition = "debris cloud; 3 hours after observed detached or after formed by collapse of par"; :>> isCounted = true; }
    part <'WXC-242'> wxc_242 : WeatherRule { doc /* 2010 G417.15(a) waiting period after debris cloud observ */ :>> rulebookEdition = "2010"; :>> ruleId = "G417.15(a)"; :>> wxParameter = "other"; :>> wxScene = "launch"; :>> wxSite = "any"; :>> wxComparison = "min"; :>> limitValue = 3.0; :>> limitUnit = "hours"; :>> ruleCondition = "debris cloud, band 0-3 nmi"; :>> isCounted = true; }
    part <'WXC-243'> wxc_243 : WeatherRule { doc /* 2010 G417.15(a) temperature of parent cloud top after co */ :>> rulebookEdition = "2010"; :>> ruleId = "G417.15(a)"; :>> wxParameter = "temperature"; :>> wxScene = "launch"; :>> wxSite = "any"; :>> wxComparison = "min"; :>> limitValue = -10.0; :>> limitUnit = "degrees Celsius"; :>> ruleCondition = "debris cloud observed to have formed by the collapse of the parent cloud top to "; :>> isCounted = true; }
    part <'WXC-244'> wxc_244 : WeatherRule { doc /* 2010 G417.15(a)(1)(i) distance of working field mill from the  */ :>> rulebookEdition = "2010"; :>> ruleId = "G417.15(a)(1)(i)"; :>> wxParameter = "other"; :>> wxScene = "launch"; :>> wxSite = "any"; :>> wxComparison = "max"; :>> limitValue = 5.0; :>> limitUnit = "nautical miles"; :>> ruleCondition = "exception (a)(1): at least one working field mill"; :>> isCounted = false; }
    part <'WXC-245'> wxc_245 : WeatherRule { doc /* 2010 G417.15(a)(1)(ii) electric field measurement */ :>> rulebookEdition = "2010"; :>> ruleId = "G417.15(a)(1)(ii)"; :>> wxParameter = "electric_field"; :>> wxScene = "launch"; :>> wxSite = "any"; :>> wxComparison = "max"; :>> limitValue = 1000.0; :>> limitUnit = "V/m"; :>> ruleCondition = "exception (a)(1): absolute values of all measurements within 5 nmi of the flight"; :>> isCounted = true; }
    part <'WXC-246'> wxc_246 : WeatherRule { doc /* 2010 G417.15(a)(1)(ii) duration the field has been below the li */ :>> rulebookEdition = "2010"; :>> ruleId = "G417.15(a)(1)(ii)"; :>> wxParameter = "other"; :>> wxScene = "launch"; :>> wxSite = "any"; :>> wxComparison = "min"; :>> limitValue = 15.0; :>> limitUnit = "minutes"; :>> ruleCondition = "exception (a)(1)"; :>> isCounted = true; }
    part <'WXC-247'> wxc_247 : WeatherRule { doc /* 2010 G417.15(a)(1)(ii) distance of electric field measurement f */ :>> rulebookEdition = "2010"; :>> ruleId = "G417.15(a)(1)(ii)"; :>> wxParameter = "other"; :>> wxScene = "launch"; :>> wxSite = "any"; :>> wxComparison = "max"; :>> limitValue = 5.0; :>> limitUnit = "nautical miles"; :>> ruleCondition = "which measurements apply"; :>> isCounted = false; }
    part <'WXC-248'> wxc_248 : WeatherRule { doc /* 2010 G417.15(a)(1)(iii) maximum radar reflectivity of the debris */ :>> rulebookEdition = "2010"; :>> ruleId = "G417.15(a)(1)(iii)"; :>> wxParameter = "other"; :>> wxScene = "launch"; :>> wxSite = "any"; :>> wxComparison = "max"; :>> limitValue = 10.0; :>> limitUnit = "dBZ"; :>> ruleCondition = "exception (a)(1): has been below this value for 15 minutes or longer"; :>> isCounted = true; }
    part <'WXC-249'> wxc_249 : WeatherRule { doc /* 2010 G417.15(a)(1)(iii) duration reflectivity has been below the */ :>> rulebookEdition = "2010"; :>> ruleId = "G417.15(a)(1)(iii)"; :>> wxParameter = "other"; :>> wxScene = "launch"; :>> wxSite = "any"; :>> wxComparison = "min"; :>> limitValue = 15.0; :>> limitUnit = "minutes"; :>> ruleCondition = "exception (a)(1)"; :>> isCounted = true; }
    part <'WXC-250'> wxc_250 : WeatherRule { doc /* 2010 G417.15(a)(1)(iii) distance of debris cloud part (radar max */ :>> rulebookEdition = "2010"; :>> ruleId = "G417.15(a)(1)(iii)"; :>> wxParameter = "other"; :>> wxScene = "launch"; :>> wxSite = "any"; :>> wxComparison = "max"; :>> limitValue = 5.0; :>> limitUnit = "nautical miles"; :>> ruleCondition = "which part of the debris cloud counts"; :>> isCounted = false; }
    part <'WXC-251'> wxc_251 : WeatherRule { doc /* 2010 G417.15(a)(2)(i) temperature of altitudes of debris cloud */ :>> rulebookEdition = "2010"; :>> ruleId = "G417.15(a)(2)(i)"; :>> wxParameter = "temperature"; :>> wxScene = "launch"; :>> wxSite = "any"; :>> wxComparison = "max"; :>> limitValue = 0.0; :>> limitUnit = "degrees Celsius"; :>> ruleCondition = "exception (a)(2): portion within 5 nmi of the flight path entirely at altitudes "; :>> isCounted = true; }
    part <'WXC-252'> wxc_252 : WeatherRule { doc /* 2010 G417.15(a)(2)(i) distance of debris cloud portion from fl */ :>> rulebookEdition = "2010"; :>> ruleId = "G417.15(a)(2)(i)"; :>> wxParameter = "other"; :>> wxScene = "launch"; :>> wxSite = "any"; :>> wxComparison = "max"; :>> limitValue = 5.0; :>> limitUnit = "nautical miles"; :>> ruleCondition = "exception (a)(2)"; :>> isCounted = true; }
    part <'WXC-253'> wxc_253 : WeatherRule { doc /* 2010 G417.15(a)(2)(ii) volume-averaged, height-integrated radar */ :>> rulebookEdition = "2010"; :>> ruleId = "G417.15(a)(2)(ii)"; :>> wxParameter = "other"; :>> wxScene = "launch"; :>> wxSite = "any"; :>> wxComparison = "max"; :>> limitValue = 10.0; :>> limitUnit = "dBZ-km"; :>> ruleCondition = "exception (a)(2): at every point within 1 nmi of the flight path (also written +"; :>> isCounted = true; }
    part <'WXC-254'> wxc_254 : WeatherRule { doc /* 2010 G417.15(a)(2)(ii) distance of VAHIRR evaluation points fro */ :>> rulebookEdition = "2010"; :>> ruleId = "G417.15(a)(2)(ii)"; :>> wxParameter = "other"; :>> wxScene = "launch"; :>> wxSite = "any"; :>> wxComparison = "max"; :>> limitValue = 1.0; :>> limitUnit = "nautical miles"; :>> ruleCondition = "exception (a)(2)"; :>> isCounted = false; }
    part <'WXC-255'> wxc_255 : WeatherRule { doc /* 2010 G417.15(b)(1) temperature of altitudes of debris cloud */ :>> rulebookEdition = "2010"; :>> ruleId = "G417.15(b)(1)"; :>> wxParameter = "temperature"; :>> wxScene = "launch"; :>> wxSite = "any"; :>> wxComparison = "max"; :>> limitValue = 0.0; :>> limitUnit = "degrees Celsius"; :>> ruleCondition = "condition (b)(1): flight through a debris cloud during the 3-hour period; portio"; :>> isCounted = true; }
    part <'WXC-256'> wxc_256 : WeatherRule { doc /* 2010 G417.15(b)(1) distance of debris cloud portion from fl */ :>> rulebookEdition = "2010"; :>> ruleId = "G417.15(b)(1)"; :>> wxParameter = "other"; :>> wxScene = "launch"; :>> wxSite = "any"; :>> wxComparison = "max"; :>> limitValue = 5.0; :>> limitUnit = "nautical miles"; :>> ruleCondition = "condition (b)(1)"; :>> isCounted = true; }
    part <'WXC-257'> wxc_257 : WeatherRule { doc /* 2010 G417.15(b)(2) volume-averaged, height-integrated radar */ :>> rulebookEdition = "2010"; :>> ruleId = "G417.15(b)(2)"; :>> wxParameter = "other"; :>> wxScene = "launch"; :>> wxSite = "any"; :>> wxComparison = "max"; :>> limitValue = 10.0; :>> limitUnit = "dBZ-km"; :>> ruleCondition = "condition (b)(2): everywhere along the flight path (also written +33 dBZ-kft)"; :>> isCounted = true; }
    part <'WXC-258'> wxc_258 : WeatherRule { doc /* 2010 G417.17 cloud top temperature of clouds associat */ :>> rulebookEdition = "2010"; :>> ruleId = "G417.17"; :>> wxParameter = "temperature"; :>> wxScene = "launch"; :>> wxSite = "any"; :>> wxComparison = "other"; :>> limitValue = 0.0; :>> limitUnit = "degrees Celsius"; :>> ruleCondition = "clouds with tops colder than or equal to this that contain moderate precipitatio"; :>> isCounted = true; }
    part <'WXC-259'> wxc_259 : WeatherRule { doc /* 2010 G417.17 distance of precipitation within the dis */ :>> rulebookEdition = "2010"; :>> ruleId = "G417.17"; :>> wxParameter = "other"; :>> wxScene = "launch"; :>> wxSite = "any"; :>> wxComparison = "other"; :>> limitValue = 5.0; :>> limitUnit = "nautical miles"; :>> ruleCondition = "cloud contains moderate precipitation or greater, or evidence of melting precipi"; :>> isCounted = true; }
    part <'WXC-260'> wxc_260 : WeatherRule { doc /* 2010 G417.19(a)(1) thickness of cloud layer through which t */ :>> rulebookEdition = "2010"; :>> ruleId = "G417.19(a)(1)"; :>> wxParameter = "cloud_thickness"; :>> wxScene = "launch"; :>> wxSite = "any"; :>> wxComparison = "max"; :>> limitValue = 4500.0; :>> limitUnit = "feet"; :>> ruleCondition = "cloud layer with any part along the flight path at a temperature between 0 and -"; :>> isCounted = true; }
    part <'WXC-261'> wxc_261 : WeatherRule { doc /* 2010 G417.19(a)(1) temperature of altitudes of any part of  */ :>> rulebookEdition = "2010"; :>> ruleId = "G417.19(a)(1)"; :>> wxParameter = "temperature"; :>> wxScene = "launch"; :>> wxSite = "any"; :>> wxComparison = "range"; :>> limitValue = -20.0; :>> limitValueHigh = 0.0; :>> limitUnit = "degrees Celsius"; :>> ruleCondition = "applicability band of the thick-layer prohibition"; :>> isCounted = true; }
    part <'WXC-262'> wxc_262 : WeatherRule { doc /* 2010 G417.19(a)(2) thickness of connected thick cloud layer */ :>> rulebookEdition = "2010"; :>> ruleId = "G417.19(a)(2)"; :>> wxParameter = "cloud_thickness"; :>> wxScene = "launch"; :>> wxSite = "any"; :>> wxComparison = "max"; :>> limitValue = 4500.0; :>> limitUnit = "feet"; :>> ruleCondition = "layer connected to a thick cloud layer within 5 nmi of the flight path, any part"; :>> isCounted = true; }
    part <'WXC-263'> wxc_263 : WeatherRule { doc /* 2010 G417.19(a)(2) distance of connected thick cloud layer  */ :>> rulebookEdition = "2010"; :>> ruleId = "G417.19(a)(2)"; :>> wxParameter = "other"; :>> wxScene = "launch"; :>> wxSite = "any"; :>> wxComparison = "max"; :>> limitValue = 5.0; :>> limitUnit = "nautical miles"; :>> ruleCondition = "connected thick cloud layer"; :>> isCounted = true; }
    part <'WXC-264'> wxc_264 : WeatherRule { doc /* 2010 G417.19(a)(2) temperature of altitudes of any part of  */ :>> rulebookEdition = "2010"; :>> ruleId = "G417.19(a)(2)"; :>> wxParameter = "temperature"; :>> wxScene = "launch"; :>> wxSite = "any"; :>> wxComparison = "range"; :>> limitValue = -20.0; :>> limitValueHigh = 0.0; :>> limitUnit = "degrees Celsius"; :>> ruleCondition = "applicability band of the connected-layer prohibition"; :>> isCounted = true; }
    part <'WXC-265'> wxc_265 : WeatherRule { doc /* 2010 G417.19(b) temperature of altitudes of cirriform cl */ :>> rulebookEdition = "2010"; :>> ruleId = "G417.19(b)"; :>> wxParameter = "temperature"; :>> wxScene = "launch"; :>> wxSite = "any"; :>> wxComparison = "max"; :>> limitValue = -15.0; :>> limitUnit = "degrees Celsius"; :>> ruleCondition = "exemption: cirriform layer never associated with convective clouds, located enti"; :>> isCounted = true; }
    part <'WXC-266'> wxc_266 : WeatherRule { doc /* 2010 G417.21(a) time after cumulus cloud observed detach */ :>> rulebookEdition = "2010"; :>> ruleId = "G417.21(a)"; :>> wxParameter = "other"; :>> wxScene = "launch"; :>> wxSite = "any"; :>> wxComparison = "min"; :>> limitValue = 60.0; :>> limitUnit = "minutes"; :>> ruleCondition = "flight through a cumulus cloud developed from a smoke plume, while attached or f"; :>> isCounted = true; }
    part <'WXC-267'> wxc_267 : WeatherRule { doc /* 2010 G417.23(a) temperature at the altitude in cloud (co */ :>> rulebookEdition = "2010"; :>> ruleId = "G417.23(a)"; :>> wxParameter = "temperature"; :>> wxScene = "launch"; :>> wxSite = "any"; :>> wxComparison = "other"; :>> limitValue = -10.0; :>> limitUnit = "degrees Celsius"; :>> ruleCondition = "flight through any part of a cloud (including transparent parts) at this tempera"; :>> isCounted = false; }
}
