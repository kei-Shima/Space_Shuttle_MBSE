// SysML v2 テキスト：関係者・関心事・ビューポイント・ビュー（図）と表記の規約
// SSD-VPT-SYS-001 ビューポイント定義書（関係者・関心事・ビュー・表記の規約） の表から生成（lib/build_docs_am.py）。
package SSD_VPT_SYS_001 {
    doc /* SSD-VPT-SYS-001 ビューポイント定義書（関係者・関心事・ビュー・表記の規約）。ビューは SSD-SYS-ARC-001 の図（327件）。 */
    private import SSD_BLK_SYS_001::*;
    private import StandardViewDefinitions::*;
    private import ScalarValues::*;
    // ---- 関係者
    part def <'SH-SE'> SystemsEngineer { doc /* システム技術者：全体の構成・整合・要求の割付を見る */ }
    part def <'SH-DES'> SubsystemDesigner { doc /* 系の設計者：受け持つ系の機能・IF・機器を見る */ }
    part def <'SH-OPS'> FlightOperations { doc /* 運用管制（MCC）・飛行計画：フェーズごとの手順と系の状態を見る */ }
    part def <'SH-CREW'> CrewMember { doc /* 乗員：操作と非常時の処置を見る */ }
    part def <'SH-SMA'> SafetyMissionAssurance { doc /* 安全・信頼性（S&MA）：冗長・故障・ハザードを見る */ }
    part def <'SH-VER'> VerificationEngineer { doc /* 検証担当：要求の検証方法と判定を見る */ }
    part def <'SH-LPS'> LaunchProcessing { doc /* 打上げ処理（KSC）：地上との IF と打上げ前の構成を見る */ }
    part def <'SH-PL'> PayloadCustomer { doc /* ペイロード顧客：ペイロードへの資源と運用を見る */ }
    part def <'SH-MGT'> ProgramManagement { doc /* 計画・構成管理：機体・キットの構成と収支の幅、モデルの管理を見る */ }
    part def <'SH-HSI'> HumanSystemsEngineer { doc /* 航空医官・人間系の技術者：乗員の健康・能力・居住性と、人と機械の分担を見る */ }
    // ---- 関心事（その関心事を持つ関係者）
    concern def <'CN-01'> SystemComposition {
        doc /* 系の構成と境界：システムは何で構成され、外部と何がつながるか */
        subject sts : SpaceTransportationSystem;
        stakeholder systemsEngineer : SystemsEngineer;
        stakeholder subsystemDesigner : SubsystemDesigner;
    }
    concern def <'CN-02'> InterfaceConsistency {
        doc /* インタフェースの整合：IF の両端・種別・上位下位がそろっているか */
        subject sts : SpaceTransportationSystem;
        stakeholder systemsEngineer : SystemsEngineer;
        stakeholder subsystemDesigner : SubsystemDesigner;
        stakeholder launchProcessing : LaunchProcessing;
    }
    concern def <'CN-03'> RequirementSatisfaction {
        doc /* 要求と充足：どの要求がどの部品・IF で満たされるか */
        subject sts : SpaceTransportationSystem;
        stakeholder systemsEngineer : SystemsEngineer;
        stakeholder verificationEngineer : VerificationEngineer;
    }
    concern def <'CN-04'> VerificationStatus {
        doc /* 検証の状態：要求がどの方法で確かめられ、判定は何か */
        subject sts : SpaceTransportationSystem;
        stakeholder systemsEngineer : SystemsEngineer;
        stakeholder verificationEngineer : VerificationEngineer;
    }
    concern def <'CN-05'> OperationsFlow {
        doc /* 運用の流れとフェーズ：いつ誰が何をし、系はどの状態か */
        subject sts : SpaceTransportationSystem;
        stakeholder subsystemDesigner : SubsystemDesigner;
        stakeholder flightOperations : FlightOperations;
        stakeholder crewMember : CrewMember;
        stakeholder launchProcessing : LaunchProcessing;
        stakeholder payloadCustomer : PayloadCustomer;
    }
    concern def <'CN-06'> FailureTolerance {
        doc /* 故障への備え：冗長・故障処置・故障の木で何が守られるか */
        subject sts : SpaceTransportationSystem;
        stakeholder flightOperations : FlightOperations;
        stakeholder crewMember : CrewMember;
        stakeholder safetyMissionAssurance : SafetyMissionAssurance;
    }
    concern def <'CN-07'> ResourceMargins {
        doc /* 資源とマージン：電力・消耗品・質量・Δv に余裕があるか */
        subject sts : SpaceTransportationSystem;
        stakeholder systemsEngineer : SystemsEngineer;
        stakeholder payloadCustomer : PayloadCustomer;
        stakeholder programManagement : ProgramManagement;
    }
    concern def <'CN-08'> PhysicalArrangement {
        doc /* 物理配置：機器がどの区画にあり、どの機能を担うか */
        subject sts : SpaceTransportationSystem;
        stakeholder subsystemDesigner : SubsystemDesigner;
        stakeholder launchProcessing : LaunchProcessing;
    }
    concern def <'CN-09'> ConfigurationVariants {
        doc /* 構成の違い：機体・キットで何が変わるか */
        subject sts : SpaceTransportationSystem;
        stakeholder flightOperations : FlightOperations;
        stakeholder payloadCustomer : PayloadCustomer;
        stakeholder programManagement : ProgramManagement;
    }
    concern def <'CN-10'> SourceTraceability {
        doc /* 根拠の追跡：記述の出典と運用資料の節を辿れるか */
        subject sts : SpaceTransportationSystem;
        stakeholder systemsEngineer : SystemsEngineer;
        stakeholder subsystemDesigner : SubsystemDesigner;
        stakeholder programManagement : ProgramManagement;
    }
    concern def <'CN-11'> ModelConsistency {
        doc /* モデルの整合：文書・図・モデルが同じ内容を指しているか */
        subject sts : SpaceTransportationSystem;
        stakeholder systemsEngineer : SystemsEngineer;
        stakeholder programManagement : ProgramManagement;
    }
    concern def <'CN-12'> ChangeImpactCoverage {
        doc /* 変更の影響と連鎖の網羅：ある要素を変えると何に影響し、要求から検証までの連鎖はどこで切れているか */
        subject sts : SpaceTransportationSystem;
        stakeholder systemsEngineer : SystemsEngineer;
        stakeholder safetyMissionAssurance : SafetyMissionAssurance;
        stakeholder verificationEngineer : VerificationEngineer;
        stakeholder programManagement : ProgramManagement;
    }
    concern def <'CN-13'> HumanSystemIntegration {
        doc /* 乗員の健康・能力と居住性：乗員はどんな環境にさらされ、何をどう操作し、どこで誤りうり、どう暮らし、どう退避するか */
        subject sts : SpaceTransportationSystem;
        stakeholder flightOperations : FlightOperations;
        stakeholder crewMember : CrewMember;
        stakeholder safetyMissionAssurance : SafetyMissionAssurance;
        stakeholder humanSystemsEngineer : HumanSystemsEngineer;
    }
    concern def <'CN-14'> HumanSystemConcern01 {
        doc /* 乗員の健康と安全：乗員の健康と安全（医療・覚醒時間・訓練）について、どの要求と図表で何が分かるか（人間系の評価方法定義書 の HCV-01） */
        subject sts : SpaceTransportationSystem;
        stakeholder flightOperations : FlightOperations;
        stakeholder crewMember : CrewMember;
        stakeholder safetyMissionAssurance : SafetyMissionAssurance;
        stakeholder humanSystemsEngineer : HumanSystemsEngineer;
    }
    concern def <'CN-15'> HumanSystemConcern02 {
        doc /* 作業の負荷と時間：作業の負荷と時間（作業分析・作業負荷・時間線）について、どの要求と図表で何が分かるか（人間系の評価方法定義書 の HCV-02） */
        subject sts : SpaceTransportationSystem;
        stakeholder flightOperations : FlightOperations;
        stakeholder crewMember : CrewMember;
        stakeholder safetyMissionAssurance : SafetyMissionAssurance;
        stakeholder humanSystemsEngineer : HumanSystemsEngineer;
    }
    concern def <'CN-16'> HumanSystemConcern03 {
        doc /* 人の誤りとその抑え：人の誤りとその抑え（HEA・誤操作の防止・検出と回復）について、どの要求と図表で何が分かるか（人間系の評価方法定義書 の HCV-03） */
        subject sts : SpaceTransportationSystem;
        stakeholder flightOperations : FlightOperations;
        stakeholder crewMember : CrewMember;
        stakeholder safetyMissionAssurance : SafetyMissionAssurance;
        stakeholder humanSystemsEngineer : HumanSystemsEngineer;
    }
    concern def <'CN-17'> HumanSystemConcern04 {
        doc /* 乗員インタフェース：乗員インタフェース（表示・操作器・ラベル・警報・操縦性）について、どの要求と図表で何が分かるか（人間系の評価方法定義書 の HCV-04） */
        subject sts : SpaceTransportationSystem;
        stakeholder flightOperations : FlightOperations;
        stakeholder crewMember : CrewMember;
        stakeholder safetyMissionAssurance : SafetyMissionAssurance;
        stakeholder humanSystemsEngineer : HumanSystemsEngineer;
    }
    concern def <'CN-18'> HumanSystemConcern05 {
        doc /* 居住性：居住性（容積・配置・照明・睡眠・衛生）について、どの要求と図表で何が分かるか（人間系の評価方法定義書 の HCV-05） */
        subject sts : SpaceTransportationSystem;
        stakeholder flightOperations : FlightOperations;
        stakeholder crewMember : CrewMember;
        stakeholder safetyMissionAssurance : SafetyMissionAssurance;
        stakeholder humanSystemsEngineer : HumanSystemsEngineer;
    }
    concern def <'CN-19'> HumanSystemConcern06 {
        doc /* 体格と身体の能力への適合：体格と身体の能力への適合（人体寸法・届く範囲・筋力）について、どの要求と図表で何が分かるか（人間系の評価方法定義書 の HCV-06） */
        subject sts : SpaceTransportationSystem;
        stakeholder flightOperations : FlightOperations;
        stakeholder crewMember : CrewMember;
        stakeholder safetyMissionAssurance : SafetyMissionAssurance;
        stakeholder humanSystemsEngineer : HumanSystemsEngineer;
    }
    concern def <'CN-20'> HumanSystemConcern07 {
        doc /* 環境の曝露：環境の曝露（騒音・大気・放射線・加速度・振動）について、どの要求と図表で何が分かるか（人間系の評価方法定義書 の HCV-07） */
        subject sts : SpaceTransportationSystem;
        stakeholder flightOperations : FlightOperations;
        stakeholder crewMember : CrewMember;
        stakeholder safetyMissionAssurance : SafetyMissionAssurance;
        stakeholder humanSystemsEngineer : HumanSystemsEngineer;
    }
    concern def <'CN-21'> HumanSystemConcern08 {
        doc /* 緊急時の退避：緊急時の退避（脱出の経路・時間・支援）について、どの要求と図表で何が分かるか（人間系の評価方法定義書 の HCV-08） */
        subject sts : SpaceTransportationSystem;
        stakeholder flightOperations : FlightOperations;
        stakeholder crewMember : CrewMember;
        stakeholder safetyMissionAssurance : SafetyMissionAssurance;
        stakeholder humanSystemsEngineer : HumanSystemsEngineer;
    }
    // ---- ビューポイント（関心事を枠に入れる）とビュー定義（標準のビュー定義を特化し、ビューポイントを満たす）
    viewpoint def <'VP-01'> CompositionViewpoint {
        doc /* 構成の観点。主な定義書：SSD-FD-*・SSD-BLK-SYS-001 */
        subject v : Views::View;
        frame concern cn01 : SystemComposition;
    }
    view def CompositionView :> GeneralView {
        satisfy requirement framedViewpoint : CompositionViewpoint;
        render Views::asTreeDiagram;
    }
    viewpoint def <'VP-02'> InterfacesViewpoint {
        doc /* インタフェースの観点。主な定義書：SSD-ICD-ORB-001・SSD-BLK-SYS-001・SSD-IBD-ORB-001・SSD-EMU-EVA-001・SSD-GNC-ORB-001・SSD-ETS-SYS-001・SSD-BEH-ORB-008・SSD-CBA-ECL-001 */
        subject v : Views::View;
        frame concern cn02 : InterfaceConsistency;
    }
    view def InterfacesView :> InterconnectionView {
        satisfy requirement framedViewpoint : InterfacesViewpoint;
        render Views::asInterconnectionDiagram;
    }
    viewpoint def <'VP-03'> RequirementsVerificationViewpoint {
        doc /* 要求・検証の観点。主な定義書：SSD-REQ-*・SSD-RQM-SYS-001・SSD-VER-SYS-001・SSD-RQF-SYS-001・SSD-FLT-ORB-001・SSD-HSI-SYS-001・SSD-RQL-ECL-001・SSD-IRQ-SYS-001・SSD-RQL-SYS-001・SSD-IRQ-ECL-001・SSD-IRQ-LOW-001・SSD-VAL-ORB-001 */
        subject v : Views::View;
        frame concern cn03 : RequirementSatisfaction;
        frame concern cn04 : VerificationStatus;
    }
    view def RequirementsVerificationView :> GridView {
        satisfy requirement framedViewpoint : RequirementsVerificationViewpoint;
        render Views::asElementTable;
    }
    viewpoint def <'VP-04'> OperationsViewpoint {
        doc /* 運用の観点。主な定義書：SSD-OPS-PHASE-001・SSD-UC-ORB-001・SSD-BEH-ORB-001・003・004・SSD-MTY-ORB-001 */
        subject v : Views::View;
        frame concern cn05 : OperationsFlow;
    }
    view def OperationsView :> GeneralView {
        satisfy requirement framedViewpoint : OperationsViewpoint;
        render Views::asTreeDiagram;
    }
    viewpoint def <'VP-05'> SubsystemBehaviorViewpoint {
        doc /* 系の振る舞いの観点。主な定義書：SSD-BEH-ORB-005・SSD-BEH-ORB-006・SSD-BEH-ORB-007・SSD-EMU-EVA-001・SSD-GNC-ORB-001・SSD-ETS-SYS-001・SSD-BEH-ORB-008・SSD-GND-ORB-001 */
        subject v : Views::View;
        frame concern cn05 : OperationsFlow;
    }
    view def SubsystemBehaviorView :> StateTransitionView {
        satisfy requirement framedViewpoint : SubsystemBehaviorViewpoint;
        render Views::asTreeDiagram;
    }
    viewpoint def <'VP-06'> SafetyFailureViewpoint {
        doc /* 安全・故障の観点。主な定義書：SSD-FMEA-*・SSD-BEH-ORB-002・SSD-ANA-ORB-001・SSD-FDIR-ORB-001・SSD-HAZ-ORB-001・SSD-FMM-ORB-001・SSD-FMX-ECL-001・SSD-GNC-ORB-001・SSD-ETS-SYS-001・SSD-ACC-SYS-001・SSD-FMX-ORB-001・SSD-IFA-ORB-001・SSD-PRA-ORB-001 */
        subject v : Views::View;
        frame concern cn06 : FailureTolerance;
    }
    view def SafetyFailureView :> GeneralView {
        satisfy requirement framedViewpoint : SafetyFailureViewpoint;
        render Views::asTreeDiagram;
    }
    viewpoint def <'VP-07'> ResourcesMarginsViewpoint {
        doc /* 資源・マージンの観点。主な定義書：SSD-BUD-ORB-001・SSD-PAR-ORB-001・SSD-ANA-ORB-001・SSD-PRF-ORB-001・SSD-TRJ-ORB-001・SSD-TPM-SYS-001・SSD-PLB-ORB-001・SSD-LAV-ORB-001・SSD-MTY-ORB-001・SSD-DCN-ORB-001・SSD-DMG-ORB-001・SSD-ORG-ORB-001・SSD-CST-ORB-001・SSD-LND-ORB-001・SSD-LCC-ORB-001・SSD-WXC-ORB-001・SSD-XCP-ORB-001・SSD-RXN-ORB-001・SSD-WXK-ORB-001・SSD-LCO-ORB-001・SSD-IOA-ORB-001 */
        subject v : Views::View;
        frame concern cn07 : ResourceMargins;
    }
    view def ResourcesMarginsView :> GridView {
        satisfy requirement framedViewpoint : ResourcesMarginsViewpoint;
        render Views::asElementTable;
    }
    viewpoint def <'VP-08'> PhysicalViewpoint {
        doc /* 物理配置の観点。主な定義書：SSD-PHY-ORB-001・SSD-ALC-SYS-001 */
        subject v : Views::View;
        frame concern cn08 : PhysicalArrangement;
    }
    view def PhysicalView :> GridView {
        satisfy requirement framedViewpoint : PhysicalViewpoint;
        render Views::asElementTable;
    }
    viewpoint def <'VP-09'> VariantsViewpoint {
        doc /* 構成の違いの観点。主な定義書：SSD-VAR-ORB-001・SSD-IND-ORB-001・SSD-FLT-ORB-001・SSD-MTY-ORB-001・SSD-CFG-ORB-001・SSD-DCN-ORB-001 */
        subject v : Views::View;
        frame concern cn09 : ConfigurationVariants;
    }
    view def VariantsView :> GridView {
        satisfy requirement framedViewpoint : VariantsViewpoint;
        render Views::asElementTable;
    }
    viewpoint def <'VP-10'> SourceTraceViewpoint {
        doc /* 根拠の追跡の観点。主な定義書：SSD-*-REF-*・SSD-OPS-REF-001・002 */
        subject v : Views::View;
        frame concern cn10 : SourceTraceability;
    }
    view def SourceTraceView :> GridView {
        satisfy requirement framedViewpoint : SourceTraceViewpoint;
        render Views::asElementTable;
    }
    viewpoint def <'VP-11'> ModelManagementViewpoint {
        doc /* モデル管理の観点。主な定義書：SSD-SYS-IDX-001・SSD-MDL-SYS-001・SSD-VPT-SYS-001・SSD-MBS-SYS-001・SSD-GRD-SYS-001・SSD-PLN-SYS-001 */
        subject v : Views::View;
        frame concern cn11 : ModelConsistency;
    }
    view def ModelManagementView :> BrowserView {
        satisfy requirement framedViewpoint : ModelManagementViewpoint;
        render Views::asTreeDiagram;
    }
    viewpoint def <'VP-12'> TraceImpactViewpoint {
        doc /* トレース・影響の観点。主な定義書：SSD-TRC-SYS-001 */
        subject v : Views::View;
        frame concern cn12 : ChangeImpactCoverage;
    }
    view def TraceImpactView :> GridView {
        satisfy requirement framedViewpoint : TraceImpactViewpoint;
        render Views::asElementTable;
    }
    viewpoint def <'VP-13'> HumanSystemsViewpoint {
        doc /* 人間系の観点。主な定義書：SSD-HSI-SYS-001・SSD-EXP-ORB-001・SSD-TSK-ORB-001・SSD-HEA-ORB-001・SSD-CIF-ORB-001・SSD-HAB-ORB-001・SSD-EGR-ORB-001・SSD-HVM-SYS-001・SSD-ATM-ORB-001・SSD-EPB-EVA-001・SSD-HRS-ORB-001・SSD-MED-ORB-001 */
        subject v : Views::View;
        frame concern cn13 : HumanSystemIntegration;
        frame concern cn14 : HumanSystemConcern01;
        frame concern cn15 : HumanSystemConcern02;
        frame concern cn16 : HumanSystemConcern03;
        frame concern cn17 : HumanSystemConcern04;
        frame concern cn18 : HumanSystemConcern05;
        frame concern cn19 : HumanSystemConcern06;
        frame concern cn20 : HumanSystemConcern07;
        frame concern cn21 : HumanSystemConcern08;
    }
    view def HumanSystemsView :> GeneralView {
        satisfy requirement framedViewpoint : HumanSystemsViewpoint;
        render Views::asTreeDiagram;
    }
    // ---- ビュー（SSD-SYS-ARC-001 の図。晒す要素は図が描くモデルのパッケージ）
    view <'図1'> fig001 : CompositionView {
        doc /* 図1 システム構成（頁 p1-system） */
        expose SSD_BLK_SYS_001::*;
    }
    view <'図2'> fig002 : CompositionView {
        doc /* 図2 オービタ サブシステム構成（頁 p2-orbiter） */
        expose SSD_BLK_SYS_001::*;
    }
    view <'図3'> fig003 : CompositionView {
        doc /* 図3 ECLSS 機能構成（頁 p3-eclss） */
        expose SSD_BLK_SYS_001::*;
    }
    view <'図4'> fig004 : SourceTraceView {
        doc /* 図4 ECLSS 関連文書マトリクス（頁 p4-eclss-docs） */
        expose SSD_ALC_SYS_001::*;
    }
    view <'図5'> fig005 : ModelManagementView {
        doc /* 図5 文書・インタフェース一覧（頁 p5-register） */
        expose SSD_VPT_SYS_001::Conventions::*;
        expose SSD_MBS_SYS_001::*;
        expose SSD_GRD_SYS_001::*;
        expose SSD_PLN_SYS_001::*;
    }
    view <'図6'> fig006 : CompositionView {
        doc /* 図6 EPS 機能構成（頁 p6-eps） */
        expose SSD_BLK_SYS_001::*;
    }
    view <'図7'> fig007 : SourceTraceView {
        doc /* 図7 EPS 関連文書マトリクス（頁 p7-eps-docs） */
        expose SSD_ALC_SYS_001::*;
    }
    view <'図8'> fig008 : CompositionView {
        doc /* 図8 熱制御 機能構成（頁 p8-tcs） */
        expose SSD_BLK_SYS_001::*;
    }
    view <'図9'> fig009 : SourceTraceView {
        doc /* 図9 熱制御 関連文書マトリクス（頁 p9-tcs-docs） */
        expose SSD_ALC_SYS_001::*;
    }
    view <'図10'> fig010 : SourceTraceView {
        doc /* 図10 運用飛行規則 章構成（頁 p10-flight-rules） */
        expose SSD_ALC_SYS_001::*;
    }
    view <'図11'> fig011 : SourceTraceView {
        doc /* 図11 乗員運用マニュアル 節構成（頁 p11-scom） */
        expose SSD_ALC_SYS_001::*;
    }
    view <'図12'> fig012 : CompositionView {
        doc /* 図12 ARS 機能構成（頁 p12-ars） */
        expose SSD_BLK_SYS_001::*;
    }
    view <'図13'> fig013 : SourceTraceView {
        doc /* 図13 ARS 関連文書マトリクス（頁 p13-ars-docs） */
        expose SSD_ALC_SYS_001::*;
    }
    view <'図14'> fig014 : CompositionView {
        doc /* 図14 CO2・CO除去 機能構成（頁 p14-co2） */
        expose SSD_BLK_SYS_001::*;
    }
    view <'図15'> fig015 : SourceTraceView {
        doc /* 図15 CO2・CO除去 関連文書マトリクス（頁 p15-co2-docs） */
        expose SSD_ALC_SYS_001::*;
    }
    view <'図16'> fig016 : CompositionView {
        doc /* 図16 キャビン空気循環 機能構成（頁 p16-cac） */
        expose SSD_BLK_SYS_001::*;
    }
    view <'図17'> fig017 : SourceTraceView {
        doc /* 図17 キャビン空気循環 関連文書マトリクス（頁 p17-cac-docs） */
        expose SSD_ALC_SYS_001::*;
    }
    view <'図18'> fig018 : CompositionView {
        doc /* 図18 圧力制御系 機能構成（頁 p18-pcs） */
        expose SSD_BLK_SYS_001::*;
    }
    view <'図19'> fig019 : SourceTraceView {
        doc /* 図19 圧力制御系 関連文書マトリクス（頁 p19-pcs-docs） */
        expose SSD_ALC_SYS_001::*;
    }
    view <'図20'> fig020 : CompositionView {
        doc /* 図20 給水・廃水系 機能構成（頁 p20-h2o） */
        expose SSD_BLK_SYS_001::*;
    }
    view <'図21'> fig021 : SourceTraceView {
        doc /* 図21 給水・廃水系 関連文書マトリクス（頁 p21-h2o-docs） */
        expose SSD_ALC_SYS_001::*;
    }
    view <'図22'> fig022 : CompositionView {
        doc /* 図22 廃棄物収集系 機能構成（頁 p22-wcs） */
        expose SSD_BLK_SYS_001::*;
    }
    view <'図23'> fig023 : SourceTraceView {
        doc /* 図23 廃棄物収集系 関連文書マトリクス（頁 p23-wcs-docs） */
        expose SSD_ALC_SYS_001::*;
    }
    view <'図24'> fig024 : CompositionView {
        doc /* 図24 エアロック支援系 機能構成（頁 p24-als） */
        expose SSD_BLK_SYS_001::*;
    }
    view <'図25'> fig025 : SourceTraceView {
        doc /* 図25 エアロック支援系 関連文書マトリクス（頁 p25-als-docs） */
        expose SSD_ALC_SYS_001::*;
    }
    view <'図26'> fig026 : CompositionView {
        doc /* 図26 煙検知・消火系 機能構成（頁 p26-fds） */
        expose SSD_BLK_SYS_001::*;
    }
    view <'図27'> fig027 : SourceTraceView {
        doc /* 図27 煙検知・消火系 関連文書マトリクス（頁 p27-fds-docs） */
        expose SSD_ALC_SYS_001::*;
    }
    view <'図28'> fig028 : CompositionView {
        doc /* 図28 再生式CO2除去装置 機能構成（頁 p28-rcrs） */
        expose SSD_BLK_SYS_001::*;
    }
    view <'図29'> fig029 : SourceTraceView {
        doc /* 図29 再生式CO2除去装置 関連文書マトリクス（頁 p29-rcrs-docs） */
        expose SSD_ALC_SYS_001::*;
    }
    view <'図30'> fig030 : CompositionView {
        doc /* 図30 キャビン温湿度制御 機能構成（頁 p30-thc） */
        expose SSD_BLK_SYS_001::*;
    }
    view <'図31'> fig031 : SourceTraceView {
        doc /* 図31 キャビン温湿度制御 関連文書マトリクス（頁 p31-thc-docs） */
        expose SSD_ALC_SYS_001::*;
    }
    view <'図32'> fig032 : CompositionView {
        doc /* 図32 アビオニクスベイ空冷 機能構成（頁 p32-avb） */
        expose SSD_BLK_SYS_001::*;
    }
    view <'図33'> fig033 : SourceTraceView {
        doc /* 図33 アビオニクスベイ空冷 関連文書マトリクス（頁 p33-avb-docs） */
        expose SSD_ALC_SYS_001::*;
    }
    view <'図34'> fig034 : CompositionView {
        doc /* 図34 IMU空冷 機能構成（頁 p34-imu） */
        expose SSD_BLK_SYS_001::*;
    }
    view <'図35'> fig035 : SourceTraceView {
        doc /* 図35 IMU空冷 関連文書マトリクス（頁 p35-imu-docs） */
        expose SSD_ALC_SYS_001::*;
    }
    view <'図36'> fig036 : CompositionView {
        doc /* 図36 水冷却ループ 機能構成（頁 p36-wcl） */
        expose SSD_BLK_SYS_001::*;
    }
    view <'図37'> fig037 : SourceTraceView {
        doc /* 図37 水冷却ループ 関連文書マトリクス（頁 p37-wcl-docs） */
        expose SSD_ALC_SYS_001::*;
    }
    view <'図38'> fig038 : InterfacesView {
        doc /* 図38 オービタ N2 インタフェース行列（頁 p38-n2） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図39'> fig039 : OperationsView {
        doc /* 図39 フェーズ別 サブシステム稼働表（頁 p39-phase-matrix） */
        expose SSD_UC_ORB_001::*;
        expose SSD_BEH_ORB_001::*;
        expose SSD_BEH_ORB_003::*;
        expose SSD_BEH_ORB_004::*;
        expose SSD_MTY_ORB_001::*;
    }
    view <'図40'> fig040 : OperationsView {
        doc /* 図40 上昇シーケンス（頁 p40-ascent-seq） */
        expose SSD_UC_ORB_001::*;
        expose SSD_BEH_ORB_001::*;
        expose SSD_BEH_ORB_003::*;
        expose SSD_BEH_ORB_004::*;
        expose SSD_MTY_ORB_001::*;
    }
    view <'図41'> fig041 : InterfacesView {
        doc /* 図41 補助図 T-0 アンビリカルと ET・SRB（頁 p41-aux-ground） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図42'> fig042 : InterfacesView {
        doc /* 図42 補助図 データ・冷却・構造（頁 p42-aux-data） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図43'> fig043 : PhysicalView {
        doc /* 図43 オービタ区画・機器配置図（頁 p43-physical） */
        expose SSD_ALC_SYS_001::*;
    }
    view <'図44'> fig044 : ResourcesMarginsView {
        doc /* 図44 収支マージン要約（頁 p44-budget） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図45'> fig045 : SafetyFailureView {
        doc /* 図45 冗長度の重ね図（頁 p45-redundancy） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図46'> fig046 : CompositionView {
        doc /* 図46 GN&C 機能構成（頁 p46-gnc） */
        expose SSD_BLK_SYS_001::*;
    }
    view <'図47'> fig047 : SourceTraceView {
        doc /* 図47 GN&C 関連文書マトリクス（頁 p47-gnc-docs） */
        expose SSD_ALC_SYS_001::*;
    }
    view <'図48'> fig048 : CompositionView {
        doc /* 図48 DPS 機能構成（頁 p48-dps） */
        expose SSD_BLK_SYS_001::*;
    }
    view <'図49'> fig049 : SourceTraceView {
        doc /* 図49 DPS 関連文書マトリクス（頁 p49-dps-docs） */
        expose SSD_ALC_SYS_001::*;
    }
    view <'図50'> fig050 : CompositionView {
        doc /* 図50 MPS 機能構成（頁 p50-mps） */
        expose SSD_BLK_SYS_001::*;
    }
    view <'図51'> fig051 : SourceTraceView {
        doc /* 図51 MPS 関連文書マトリクス（頁 p51-mps-docs） */
        expose SSD_ALC_SYS_001::*;
    }
    view <'図52'> fig052 : CompositionView {
        doc /* 図52 OMS 機能構成（頁 p52-oms） */
        expose SSD_BLK_SYS_001::*;
    }
    view <'図53'> fig053 : SourceTraceView {
        doc /* 図53 OMS 関連文書マトリクス（頁 p53-oms-docs） */
        expose SSD_ALC_SYS_001::*;
    }
    view <'図54'> fig054 : CompositionView {
        doc /* 図54 RCS 機能構成（頁 p54-rcs） */
        expose SSD_BLK_SYS_001::*;
    }
    view <'図55'> fig055 : SourceTraceView {
        doc /* 図55 RCS 関連文書マトリクス（頁 p55-rcs-docs） */
        expose SSD_ALC_SYS_001::*;
    }
    view <'図56'> fig056 : CompositionView {
        doc /* 図56 APU/HYD 機能構成（頁 p56-apu） */
        expose SSD_BLK_SYS_001::*;
    }
    view <'図57'> fig057 : SourceTraceView {
        doc /* 図57 APU/HYD 関連文書マトリクス（頁 p57-apu-docs） */
        expose SSD_ALC_SYS_001::*;
    }
    view <'図58'> fig058 : CompositionView {
        doc /* 図58 C&T 機能構成（頁 p58-ct） */
        expose SSD_BLK_SYS_001::*;
    }
    view <'図59'> fig059 : SourceTraceView {
        doc /* 図59 C&T 関連文書マトリクス（頁 p59-ct-docs） */
        expose SSD_ALC_SYS_001::*;
    }
    view <'図60'> fig060 : CompositionView {
        doc /* 図60 EVA 機能構成（頁 p60-eva） */
        expose SSD_BLK_SYS_001::*;
    }
    view <'図61'> fig061 : SourceTraceView {
        doc /* 図61 EVA 関連文書マトリクス（頁 p61-eva-docs） */
        expose SSD_ALC_SYS_001::*;
    }
    view <'図62'> fig062 : CompositionView {
        doc /* 図62 C/W 機能構成（頁 p62-cw） */
        expose SSD_BLK_SYS_001::*;
    }
    view <'図63'> fig063 : SourceTraceView {
        doc /* 図63 C/W 関連文書マトリクス（頁 p63-cw-docs） */
        expose SSD_ALC_SYS_001::*;
    }
    view <'図64'> fig064 : CompositionView {
        doc /* 図64 CREW 機能構成（頁 p64-crew） */
        expose SSD_BLK_SYS_001::*;
    }
    view <'図65'> fig065 : SourceTraceView {
        doc /* 図65 CREW 関連文書マトリクス（頁 p65-crew-docs） */
        expose SSD_ALC_SYS_001::*;
    }
    view <'図66'> fig066 : CompositionView {
        doc /* 図66 PLS 機能構成（頁 p66-pls） */
        expose SSD_BLK_SYS_001::*;
    }
    view <'図67'> fig067 : SourceTraceView {
        doc /* 図67 PLS 関連文書マトリクス（頁 p67-pls-docs） */
        expose SSD_ALC_SYS_001::*;
    }
    view <'図68'> fig068 : CompositionView {
        doc /* 図68 MECH 機能構成（頁 p68-mech） */
        expose SSD_BLK_SYS_001::*;
    }
    view <'図69'> fig069 : SourceTraceView {
        doc /* 図69 MECH 関連文書マトリクス（頁 p69-mech-docs） */
        expose SSD_ALC_SYS_001::*;
    }
    view <'図70'> fig070 : CompositionView {
        doc /* 図70 STR 機能構成（頁 p70-str） */
        expose SSD_BLK_SYS_001::*;
    }
    view <'図71'> fig071 : SourceTraceView {
        doc /* 図71 STR 関連文書マトリクス（頁 p71-str-docs） */
        expose SSD_ALC_SYS_001::*;
    }
    view <'図72'> fig072 : CompositionView {
        doc /* 図72 ET 機能構成（頁 p72-et） */
        expose SSD_BLK_SYS_001::*;
    }
    view <'図73'> fig073 : SourceTraceView {
        doc /* 図73 ET 関連文書マトリクス（頁 p73-et-docs） */
        expose SSD_ALC_SYS_001::*;
    }
    view <'図74'> fig074 : CompositionView {
        doc /* 図74 SRB 機能構成（頁 p74-srb） */
        expose SSD_BLK_SYS_001::*;
    }
    view <'図75'> fig075 : SourceTraceView {
        doc /* 図75 SRB 関連文書マトリクス（頁 p75-srb-docs） */
        expose SSD_ALC_SYS_001::*;
    }
    view <'図76'> fig076 : OperationsView {
        doc /* 図76 ミッションフェーズ・アボート 状態遷移図（頁 p76-mode-sm） */
        expose SSD_UC_ORB_001::*;
        expose SSD_BEH_ORB_001::*;
        expose SSD_BEH_ORB_003::*;
        expose SSD_BEH_ORB_004::*;
        expose SSD_MTY_ORB_001::*;
    }
    view <'図77'> fig077 : OperationsView {
        doc /* 図77 飛行継続判断（Go/No-Go）状態遷移図（頁 p77-gonogo-sm） */
        expose SSD_UC_ORB_001::*;
        expose SSD_BEH_ORB_001::*;
        expose SSD_BEH_ORB_003::*;
        expose SSD_BEH_ORB_004::*;
        expose SSD_MTY_ORB_001::*;
    }
    view <'図78'> fig078 : ResourcesMarginsView {
        doc /* 図78 消耗品 パラメトリック図（頁 p78-par-consumables） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図79'> fig079 : ResourcesMarginsView {
        doc /* 図79 電力・反応剤・排熱 パラメトリック図（頁 p79-par-power） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図80'> fig080 : SafetyFailureView {
        doc /* 図80 MPS ヘリウム漏れ処置 活動図（頁 p80-act-he） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図81'> fig081 : SafetyFailureView {
        doc /* 図81 燃料電池の冷却喪失処置 活動図（頁 p81-act-fc） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図82'> fig082 : SafetyFailureView {
        doc /* 図82 火災処置 活動図（頁 p82-act-fire） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図83'> fig083 : OperationsView {
        doc /* 図83 軌道離脱〜着陸 シーケンス図（頁 p83-seq-deorbit） */
        expose SSD_UC_ORB_001::*;
        expose SSD_BEH_ORB_001::*;
        expose SSD_BEH_ORB_003::*;
        expose SSD_BEH_ORB_004::*;
        expose SSD_MTY_ORB_001::*;
    }
    view <'図84'> fig084 : OperationsView {
        doc /* 図84 上昇 シーケンス図（頁 p84-seq-ascent） */
        expose SSD_UC_ORB_001::*;
        expose SSD_BEH_ORB_001::*;
        expose SSD_BEH_ORB_003::*;
        expose SSD_BEH_ORB_004::*;
        expose SSD_MTY_ORB_001::*;
    }
    view <'図85'> fig085 : OperationsView {
        doc /* 図85 指令・テレメトリ経路 シーケンス図（頁 p85-seq-command） */
        expose SSD_UC_ORB_001::*;
        expose SSD_BEH_ORB_001::*;
        expose SSD_BEH_ORB_003::*;
        expose SSD_BEH_ORB_004::*;
        expose SSD_MTY_ORB_001::*;
    }
    view <'図86'> fig086 : SafetyFailureView {
        doc /* 図86 キャビン減圧処置 活動図（頁 p86-act-leak） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図87'> fig087 : OperationsView {
        doc /* 図87 EVA 準備〜再与圧 活動図（頁 p87-act-eva） */
        expose SSD_UC_ORB_001::*;
        expose SSD_BEH_ORB_001::*;
        expose SSD_BEH_ORB_003::*;
        expose SSD_BEH_ORB_004::*;
        expose SSD_MTY_ORB_001::*;
    }
    view <'図88'> fig088 : SafetyFailureView {
        doc /* 図88 ペイロードベイドア閉鎖不能処置 活動図（頁 p88-act-plbd） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図89'> fig089 : CompositionView {
        doc /* 図89 システム構成 ブロック定義図（頁 p89-bdd-structure） */
        expose SSD_BLK_SYS_001::*;
    }
    view <'図90'> fig090 : RequirementsVerificationView {
        doc /* 図90 要求の導出・充足 行列（頁 p90-req-matrix） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図91'> fig091 : PhysicalView {
        doc /* 図91 割付行列（系 × 区画）（頁 p91-alloc-matrix） */
        expose SSD_ALC_SYS_001::*;
    }
    view <'図92'> fig092 : ModelManagementView {
        doc /* 図92 モデルの構成 パッケージ図（頁 p92-model-packages） */
        expose SSD_VPT_SYS_001::Conventions::*;
        expose SSD_MBS_SYS_001::*;
        expose SSD_GRD_SYS_001::*;
        expose SSD_PLN_SYS_001::*;
    }
    view <'図93'> fig093 : OperationsView {
        doc /* 図93 運用のユースケース図（頁 p93-uc-mission） */
        expose SSD_UC_ORB_001::*;
        expose SSD_BEH_ORB_001::*;
        expose SSD_BEH_ORB_003::*;
        expose SSD_BEH_ORB_004::*;
        expose SSD_MTY_ORB_001::*;
    }
    view <'図94'> fig094 : OperationsView {
        doc /* 図94 ランデブー・ドッキング シーケンス図（頁 p94-seq-rndz） */
        expose SSD_UC_ORB_001::*;
        expose SSD_BEH_ORB_001::*;
        expose SSD_BEH_ORB_003::*;
        expose SSD_BEH_ORB_004::*;
        expose SSD_MTY_ORB_001::*;
    }
    view <'図95'> fig095 : OperationsView {
        doc /* 図95 最終秒読み〜RSLS アボート シーケンス図（頁 p95-seq-rsls） */
        expose SSD_UC_ORB_001::*;
        expose SSD_BEH_ORB_001::*;
        expose SSD_BEH_ORB_003::*;
        expose SSD_BEH_ORB_004::*;
        expose SSD_MTY_ORB_001::*;
    }
    view <'図96'> fig096 : OperationsView {
        doc /* 図96 RMS によるペイロード放出 活動図（頁 p96-act-deploy） */
        expose SSD_UC_ORB_001::*;
        expose SSD_BEH_ORB_001::*;
        expose SSD_BEH_ORB_003::*;
        expose SSD_BEH_ORB_004::*;
        expose SSD_MTY_ORB_001::*;
    }
    view <'図97'> fig097 : OperationsView {
        doc /* 図97 上昇アボートの選択 活動図（頁 p97-act-abort） */
        expose SSD_UC_ORB_001::*;
        expose SSD_BEH_ORB_001::*;
        expose SSD_BEH_ORB_003::*;
        expose SSD_BEH_ORB_004::*;
        expose SSD_MTY_ORB_001::*;
    }
    view <'図98'> fig098 : SubsystemBehaviorView {
        doc /* 図98 GPC 状態遷移図（頁 p98-sm-gpc） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図99'> fig099 : SubsystemBehaviorView {
        doc /* 図99 燃料電池 状態遷移図（頁 p99-sm-fc） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図100'> fig100 : SubsystemBehaviorView {
        doc /* 図100 APU 状態遷移図（頁 p100-sm-apu） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図101'> fig101 : SubsystemBehaviorView {
        doc /* 図101 RMS 状態遷移図（頁 p101-sm-rms） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図102'> fig102 : SubsystemBehaviorView {
        doc /* 図102 ATCS 排熱 状態遷移図（頁 p102-sm-atcs） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図103'> fig103 : SubsystemBehaviorView {
        doc /* 図103 系のモード × フェーズ 行列（頁 p103-mode-phase） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図104'> fig104 : ResourcesMarginsView {
        doc /* 図104 CO2 除去のトレードスタディ（頁 p104-trade-co2） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図105'> fig105 : ResourcesMarginsView {
        doc /* 図105 質量特性・Δv の解析（頁 p105-mass-dv） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図106'> fig106 : SafetyFailureView {
        doc /* 図106 故障の木 A（28 VDC 主電力の喪失）（頁 p106-fta-a） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図107'> fig107 : SafetyFailureView {
        doc /* 図107 故障の木 B（空力舵面の油圧の喪失）（頁 p107-fta-b） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図108'> fig108 : SafetyFailureView {
        doc /* 図108 故障の木 C（CO2 制御の喪失）（頁 p108-fta-c） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図109'> fig109 : VariantsView {
        doc /* 図109 機体・ミッションキットの構成行列（頁 p109-variants） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図110'> fig110 : RequirementsVerificationView {
        doc /* 図110 検証マトリクス（頁 p110-verification） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図111'> fig111 : ModelManagementView {
        doc /* 図111 ビューポイントと関係者の行列（頁 p111-viewpoints） */
        expose SSD_VPT_SYS_001::Conventions::*;
        expose SSD_MBS_SYS_001::*;
        expose SSD_GRD_SYS_001::*;
        expose SSD_PLN_SYS_001::*;
    }
    view <'図112'> fig112 : InterfacesView {
        doc /* 図112 EPS 発電・配電 内部ブロック図（頁 p112-ibd-eps） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図113'> fig113 : InterfacesView {
        doc /* 図113 ATCS 冷却ループ 内部ブロック図（頁 p113-ibd-atcs） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図114'> fig114 : InterfacesView {
        doc /* 図114 MPS 推進薬供給 内部ブロック図（頁 p114-ibd-mps） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図115'> fig115 : TraceImpactView {
        doc /* 図115 トレースの連鎖（要素の種類と関係）（頁 p115-trace-chain） */
        expose SSD_TRC_SYS_001::*;
    }
    view <'図116'> fig116 : TraceImpactView {
        doc /* 図116 系ごとのトレース網羅（頁 p116-trace-coverage） */
        expose SSD_TRC_SYS_001::*;
    }
    view <'図117'> fig117 : TraceImpactView {
        doc /* 図117 変更の影響分析（頁 p117-impact） */
        expose SSD_TRC_SYS_001::*;
    }
    view <'図118'> fig118 : SafetyFailureView {
        doc /* 図118 C/W 警告灯と検知・処置の対応（頁 p118-fdir-lights） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図119'> fig119 : SafetyFailureView {
        doc /* 図119 故障検知・処置の連鎖と網羅（頁 p119-fdir-chain） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図120'> fig120 : SafetyFailureView {
        doc /* 図120 ハザードのリスク行列（頁 p120-hazard-matrix） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図121'> fig121 : SafetyFailureView {
        doc /* 図121 ハザードの原因と管理策（頁 p121-hazard-bowtie） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図122'> fig122 : VariantsView {
        doc /* 図122 機体と飛行の個体・時間切片（頁 p122-individuals） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図123'> fig123 : VariantsView {
        doc /* 図123 飛行の実績と設計値（頁 p123-actuals） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図124'> fig124 : RequirementsVerificationView {
        doc /* 図124 要求の形式化の区分（頁 p124-req-formal） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図125'> fig125 : RequirementsVerificationView {
        doc /* 図125 要求の値による判定（頁 p125-req-evaluation） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図126'> fig126 : SafetyFailureView {
        doc /* 図126 故障モードから見た安全の連鎖（頁 p126-fmm-chain） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図127'> fig127 : SafetyFailureView {
        doc /* 図127 故障モードの網羅（系・原因ごと）（頁 p127-fmm-coverage） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図128'> fig128 : InterfacesView {
        doc /* 図128 DPS データバス網 内部ブロック図（頁 p128-ibd-dps） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図129'> fig129 : InterfacesView {
        doc /* 図129 APU・油圧 内部ブロック図（頁 p129-ibd-apu） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図130'> fig130 : InterfacesView {
        doc /* 図130 OMS・RCS 推進薬 内部ブロック図（頁 p130-ibd-prop） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図131'> fig131 : InterfacesView {
        doc /* 図131 C&T RF リンク 内部ブロック図（頁 p131-ibd-ct） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図132'> fig132 : VariantsView {
        doc /* 図132 飛行ごとの構成（機体・キット・特徴）（頁 p132-flight-config） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図133'> fig133 : RequirementsVerificationView {
        doc /* 図133 飛行試験の結果と要求（頁 p133-flight-tests） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図134'> fig134 : ResourcesMarginsView {
        doc /* 図134 標準ミッションの消耗品の残量（設計）（頁 p134-profile-design） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図135'> fig135 : ResourcesMarginsView {
        doc /* 図135 反応剤の残量の設計と実績（STS-1・114・125）（頁 p135-profile-actual） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図136'> fig136 : SubsystemBehaviorView {
        doc /* 図136 OMS 状態遷移図（頁 p136-sm-oms） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図137'> fig137 : SubsystemBehaviorView {
        doc /* 図137 RCS 状態遷移図（頁 p137-sm-rcs） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図138'> fig138 : SubsystemBehaviorView {
        doc /* 図138 MPS 状態遷移図（頁 p138-sm-mps） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図139'> fig139 : SubsystemBehaviorView {
        doc /* 図139 C&T 通信構成 状態遷移図（頁 p139-sm-ct） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図140'> fig140 : SubsystemBehaviorView {
        doc /* 図140 与圧系 状態遷移図（頁 p140-sm-pcs） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図141'> fig141 : SubsystemBehaviorView {
        doc /* 図141 ODS 状態遷移図（頁 p141-sm-ods） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図142'> fig142 : SubsystemBehaviorView {
        doc /* 図142 系のモード × フェーズ 行列（その2）（頁 p142-mode-phase-2） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図143'> fig143 : HumanSystemsView {
        doc /* 図143 人間系の基準の照合（章 × 判定）（頁 p143-hsi-coverage） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図144'> fig144 : HumanSystemsView {
        doc /* 図144 人間系の基準の値とシャトルの値（頁 p144-hsi-values） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図145'> fig145 : HumanSystemsView {
        doc /* 図145 乗員の曝露の量と基準（パラメトリック）（頁 p145-exp-params） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図146'> fig146 : HumanSystemsView {
        doc /* 図146 乗員の曝露のプロファイル（頁 p146-exp-profiles） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図147'> fig147 : HumanSystemsView {
        doc /* 図147 機能の分担（人・自動化・地上）（頁 p147-tsk-alloc） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図148'> fig148 : HumanSystemsView {
        doc /* 図148 作業分析：軌道離脱準備から着陸まで（頁 p148-tsk-deorbit） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図149'> fig149 : HumanSystemsView {
        doc /* 図149 作業分析：EVA の準備（頁 p149-tsk-eva） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図150'> fig150 : HumanSystemsView {
        doc /* 図150 作業 × 誤りの種類（頁 p150-hea-matrix） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図151'> fig151 : HumanSystemsView {
        doc /* 図151 誤りからハザードへの連鎖と管理策（頁 p151-hea-chain） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図152'> fig152 : HumanSystemsView {
        doc /* 図152 警報の階層の対応（シャトル × 3001）（頁 p152-cif-alerts） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図153'> fig153 : HumanSystemsView {
        doc /* 図153 表示・操作の盤と作業位置（頁 p153-cif-panels） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図154'> fig154 : HumanSystemsView {
        doc /* 図154 居住・医療の機能と 3001 の照合、乗員の1日（頁 p154-hab-funcs） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図155'> fig155 : HumanSystemsView {
        doc /* 図155 居住・医療のユースケース（頁 p155-hab-uc） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図156'> fig156 : HumanSystemsView {
        doc /* 図156 乗員区画のつながりと移動の経路（頁 p156-egr-paths） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図157'> fig157 : HumanSystemsView {
        doc /* 図157 非常退避・退出のモード × フェーズ（頁 p157-egr-modes） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図158'> fig158 : HumanSystemsView {
        doc /* 図158 人間系の評価方法と図表の対応（頁 p158-hvm-methods） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図159'> fig159 : InterfacesView {
        doc /* 図159 ARS キャビン空気ループ 内部ブロック図（頁 p159-ibd-ars-air） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図160'> fig160 : InterfacesView {
        doc /* 図160 ARS 水冷却ループ 内部ブロック図（頁 p160-ibd-ars-water） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図161'> fig161 : InterfacesView {
        doc /* 図161 PCS 酸素・窒素供給 内部ブロック図（頁 p161-ibd-pcs） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図162'> fig162 : InterfacesView {
        doc /* 図162 給水・廃水・WCS 内部ブロック図（頁 p162-ibd-water） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図163'> fig163 : HumanSystemsView {
        doc /* 図163 CO2 分圧の時間変化（LiOH・RCRS・除去なし）（頁 p163-atm-co2） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図164'> fig164 : HumanSystemsView {
        doc /* 図164 乗員室の全圧・酸素分圧（穴の減圧・PPO2 の周期）（頁 p164-atm-pressure） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図165'> fig165 : HumanSystemsView {
        doc /* 図165 乗員室の温度と湿度（定常・冷却の喪失）（頁 p165-atm-thermal） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図166'> fig166 : RequirementsVerificationView {
        doc /* 図166 ECLSS 要求の導出（L2 → L3）（頁 p166-rql-derivation） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図167'> fig167 : RequirementsVerificationView {
        doc /* 図167 ECLSS 下位の機能行の網羅（要求の割付・判断）（頁 p167-rql-coverage） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図168'> fig168 : SubsystemBehaviorView {
        doc /* 図168 ARS 状態遷移図（頁 p168-sm-ars） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図169'> fig169 : SubsystemBehaviorView {
        doc /* 図169 FDS 状態遷移図（頁 p169-sm-fds） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図170'> fig170 : SubsystemBehaviorView {
        doc /* 図170 給水・廃水系 状態遷移図（頁 p170-sm-water） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図171'> fig171 : SubsystemBehaviorView {
        doc /* 図171 WCS 状態遷移図（頁 p171-sm-wcs） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図172'> fig172 : SubsystemBehaviorView {
        doc /* 図172 ECLSS のモード × フェーズ 行列（頁 p172-mode-phase-3） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図173'> fig173 : SubsystemBehaviorView {
        doc /* 図173 LiOH キャニスタの交換 活動図（頁 p173-act-lioh） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図174'> fig174 : SubsystemBehaviorView {
        doc /* 図174 給水・廃水のダンプ 活動図（頁 p174-act-dump） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図175'> fig175 : SubsystemBehaviorView {
        doc /* 図175 水冷却ループの喪失の処置 活動図（頁 p175-act-water-loop） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図176'> fig176 : SafetyFailureView {
        doc /* 図176 ECLSS 機能の故障モード（ブロック × 検知・原因）（頁 p176-fmx-modes） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図177'> fig177 : SafetyFailureView {
        doc /* 図177 故障の木 X1（乗員室の圧力の喪失）（頁 p177-fta-x1） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図178'> fig178 : SafetyFailureView {
        doc /* 図178 故障の木 X2（CO2 除去の喪失）（頁 p178-fta-x2） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図179'> fig179 : InterfacesView {
        doc /* 図179 EMU の構造（ブロック定義）（頁 p179-emu-structure） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図180'> fig180 : InterfacesView {
        doc /* 図180 EMU 内部ブロック図（換気・冷却水・電力・通信）（頁 p180-ibd-emu） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図181'> fig181 : SubsystemBehaviorView {
        doc /* 図181 EMU 状態遷移図（頁 p181-sm-emu） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図182'> fig182 : SubsystemBehaviorView {
        doc /* 図182 エアロック 状態遷移図（頁 p182-sm-airlock） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図183'> fig183 : HumanSystemsView {
        doc /* 図183 EMU の消耗品の持続時間（代謝率との関係）（頁 p183-epb-consumables） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図184'> fig184 : HumanSystemsView {
        doc /* 図184 前呼吸の手順と組織の窒素（R 値）（頁 p184-epb-prebreathe） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図185'> fig185 : HumanSystemsView {
        doc /* 図185 居住の資源の量と標準ミッションの収支（頁 p185-hrs-budget） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図186'> fig186 : HumanSystemsView {
        doc /* 図186 収納の場所と容積（頁 p186-hrs-stowage） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図187'> fig187 : HumanSystemsView {
        doc /* 図187 医療システム（SOMS）の構成と役割（頁 p187-med-soms） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図188'> fig188 : HumanSystemsView {
        doc /* 図188 乗員の傷病の処置 活動図（頁 p188-act-medical） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図189'> fig189 : HumanSystemsView {
        doc /* 図189 減圧症の疑いの処置 活動図（頁 p189-act-dcs） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図190'> fig190 : HumanSystemsView {
        doc /* 図190 飛行中の医療の事象の実績（頁 p190-med-events） */
        expose SSD_HSI_SYS_001::*;
        expose SSD_EXP_ORB_001::*;
        expose SSD_TSK_ORB_001::*;
        expose SSD_HEA_ORB_001::*;
        expose SSD_CIF_ORB_001::*;
        expose SSD_HAB_ORB_001::*;
        expose SSD_EGR_ORB_001::*;
        expose SSD_HVM_SYS_001::*;
        expose SSD_ATM_ORB_001::*;
        expose SSD_EPB_EVA_001::*;
        expose SSD_HRS_ORB_001::*;
        expose SSD_MED_ORB_001::*;
    }
    view <'図191'> fig191 : InterfacesView {
        doc /* 図191 GN&C 航法・センサ 内部ブロック図（頁 p191-ibd-gnc-nav） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図192'> fig192 : InterfacesView {
        doc /* 図192 GN&C 飛行制御・駆動 内部ブロック図（頁 p192-ibd-gnc-fcs） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図193'> fig193 : SubsystemBehaviorView {
        doc /* 図193 GN&C の OPS・メジャーモード 状態遷移図（頁 p193-sm-gnc-modes） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図194'> fig194 : SubsystemBehaviorView {
        doc /* 図194 DAP のモード 状態遷移図（頁 p194-sm-dap） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図195'> fig195 : SubsystemBehaviorView {
        doc /* 図195 IMU 状態遷移図（頁 p195-sm-imu） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図196'> fig196 : SubsystemBehaviorView {
        doc /* 図196 再突入の航法センサの取り込み 状態遷移図（頁 p196-sm-nav-sensors） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図197'> fig197 : SafetyFailureView {
        doc /* 図197 GN&C の冗長管理（選択・検出・故障許容）（頁 p197-gnc-rm） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図198'> fig198 : SubsystemBehaviorView {
        doc /* 図198 センサの冗長管理による故障処置 活動図（頁 p198-act-rm-fdir） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図199'> fig199 : SubsystemBehaviorView {
        doc /* 図199 FCS チャネルの故障処置 活動図（頁 p199-act-fcs-channel） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図200'> fig200 : InterfacesView {
        doc /* 図200 ET 内部ブロック図（頁 p200-ibd-et） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図201'> fig201 : InterfacesView {
        doc /* 図201 SRB 内部ブロック図（頁 p201-ibd-srb） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図202'> fig202 : InterfacesView {
        doc /* 図202 TPS・受動熱制御 内部ブロック図（頁 p202-ibd-tps） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図203'> fig203 : SubsystemBehaviorView {
        doc /* 図203 SRB 状態遷移図（頁 p203-sm-srb） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図204'> fig204 : SubsystemBehaviorView {
        doc /* 図204 ET 状態遷移図（頁 p204-sm-et） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図205'> fig205 : SafetyFailureView {
        doc /* 図205 飛行中の TPS の点検と損傷の判断 活動図（頁 p205-act-tps-inspection） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図206'> fig206 : SafetyFailureView {
        doc /* 図206 51-L の事象の連鎖（頁 p206-acc-51l） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図207'> fig207 : SafetyFailureView {
        doc /* 図207 STS-107 の事象の連鎖（頁 p207-acc-107） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図208'> fig208 : SafetyFailureView {
        doc /* 図208 SRB・ET・TPS の機能の故障モード（頁 p208-acc-failure-modes） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図209'> fig209 : SafetyFailureView {
        doc /* 図209 故障の木 A1（上昇中の機体の喪失：SRB の継手）（頁 p209-fta-a1） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図210'> fig210 : SafetyFailureView {
        doc /* 図210 故障の木 A2（再突入中の機体の喪失：翼前縁の熱防護）（頁 p210-fta-a2） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図211'> fig211 : SafetyFailureView {
        doc /* 図211 事故調査の勧告と改修（教訓）（頁 p211-acc-lessons） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図212'> fig212 : RequirementsVerificationView {
        doc /* 図212 インタフェース要求の一覧（上位の IF）（頁 p212-irq-list） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図213'> fig213 : RequirementsVerificationView {
        doc /* 図213 上位の要求からインタフェース要求への導出（頁 p213-irq-derivation） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図214'> fig214 : InterfacesView {
        doc /* 図214 MECH 内部ブロック図（頁 p214-ibd-mech） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図215'> fig215 : InterfacesView {
        doc /* 図215 C/W 内部ブロック図（頁 p215-ibd-cw） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図216'> fig216 : InterfacesView {
        doc /* 図216 PLS 内部ブロック図（頁 p216-ibd-pls） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図217'> fig217 : InterfacesView {
        doc /* 図217 STR 内部ブロック図（頁 p217-ibd-str） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図218'> fig218 : InterfacesView {
        doc /* 図218 CREW 内部ブロック図（頁 p218-ibd-crew） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図219'> fig219 : SubsystemBehaviorView {
        doc /* 図219 降着装置・制動 状態遷移図（頁 p219-sm-landing-gear） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図220'> fig220 : SubsystemBehaviorView {
        doc /* 図220 ベントドア・ET アンビリカルドア 状態遷移図（頁 p220-sm-vent-doors） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図221'> fig221 : SubsystemBehaviorView {
        doc /* 図221 警報系（C/W）状態遷移図（頁 p221-sm-caution-warning） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図222'> fig222 : SubsystemBehaviorView {
        doc /* 図222 ペイロード保持ラッチ・ドッキング機構 状態遷移図（頁 p222-sm-payload-latches） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図223'> fig223 : SubsystemBehaviorView {
        doc /* 図223 脱出のモード 状態遷移図（頁 p223-sm-crew-escape） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図224'> fig224 : SubsystemBehaviorView {
        doc /* 図224 構造の運用の限界の判断 活動図（頁 p224-act-structural-limits） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図225'> fig225 : RequirementsVerificationView {
        doc /* 図225 L2 の要求から L3 の要求への導出（系ごとの数）（頁 p225-rql-sys-derivation） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図226'> fig226 : RequirementsVerificationView {
        doc /* 図226 機能ブロックごとの L3 の要求と機能行の対応（頁 p226-rql-sys-coverage） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図227'> fig227 : SafetyFailureView {
        doc /* 図227 機能の故障モード（GN&C・RCS・DPS・C/W）（頁 p227-fmx-orb-a） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図228'> fig228 : SafetyFailureView {
        doc /* 図228 機能の故障モード（C&T・EVA・CREW・PLS）（頁 p228-fmx-orb-b） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図229'> fig229 : SafetyFailureView {
        doc /* 図229 機能の故障モード（APU・MECH・STR・EPS・MPS）（頁 p229-fmx-orb-c） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図230'> fig230 : ResourcesMarginsView {
        doc /* 図230 上昇の質量と推力加速度の時間変化（頁 p230-trj-ascent） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図231'> fig231 : ResourcesMarginsView {
        doc /* 図231 再突入の高度・速度と動圧・減速度の時間変化（頁 p231-trj-entry） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図232'> fig232 : ResourcesMarginsView {
        doc /* 図232 上昇・再突入のモデルと実績・限界の比較（頁 p232-trj-compare） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図233'> fig233 : InterfacesView {
        doc /* 図233 ECLSS 電力（ARS 系の機器）内部ブロック図（頁 p233-ibd-eclss-pwra） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図234'> fig234 : InterfacesView {
        doc /* 図234 ECLSS 電力（ARS 以外の機器）内部ブロック図（頁 p234-ibd-eclss-pwrb） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図235'> fig235 : InterfacesView {
        doc /* 図235 ARS の補い 内部ブロック図（頁 p235-ibd-ars-extra） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図236'> fig236 : InterfacesView {
        doc /* 図236 エアロック支援系 内部ブロック図（頁 p236-ibd-als） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図237'> fig237 : InterfacesView {
        doc /* 図237 煙検知・消火ほか 内部ブロック図（頁 p237-ibd-fds） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図238'> fig238 : OperationsView {
        doc /* 図238 ARS 空気系の運転と監視 シーケンス図（頁 p238-seq-ars-air） */
        expose SSD_UC_ORB_001::*;
        expose SSD_BEH_ORB_001::*;
        expose SSD_BEH_ORB_003::*;
        expose SSD_BEH_ORB_004::*;
        expose SSD_MTY_ORB_001::*;
    }
    view <'図239'> fig239 : OperationsView {
        doc /* 図239 RCRS と水冷却ループの運転と監視 シーケンス図（頁 p239-seq-rcrs-wcl） */
        expose SSD_UC_ORB_001::*;
        expose SSD_BEH_ORB_001::*;
        expose SSD_BEH_ORB_003::*;
        expose SSD_BEH_ORB_004::*;
        expose SSD_MTY_ORB_001::*;
    }
    view <'図240'> fig240 : OperationsView {
        doc /* 図240 与圧・給水・廃棄物・エアロックの運転と表示 シーケンス図（頁 p240-seq-pcs-h2o） */
        expose SSD_UC_ORB_001::*;
        expose SSD_BEH_ORB_001::*;
        expose SSD_BEH_ORB_003::*;
        expose SSD_BEH_ORB_004::*;
        expose SSD_MTY_ORB_001::*;
    }
    view <'図241'> fig241 : OperationsView {
        doc /* 図241 煙検知と消火 シーケンス図（頁 p241-seq-fire） */
        expose SSD_UC_ORB_001::*;
        expose SSD_BEH_ORB_001::*;
        expose SSD_BEH_ORB_003::*;
        expose SSD_BEH_ORB_004::*;
        expose SSD_MTY_ORB_001::*;
    }
    view <'図242'> fig242 : OperationsView {
        doc /* 図242 キャビン温湿度の制御と監視 シーケンス図（頁 p242-seq-thc） */
        expose SSD_UC_ORB_001::*;
        expose SSD_BEH_ORB_001::*;
        expose SSD_BEH_ORB_003::*;
        expose SSD_BEH_ORB_004::*;
        expose SSD_MTY_ORB_001::*;
    }
    view <'図243'> fig243 : InterfacesView {
        doc /* 図243 EVA 支援（エアロック・工具・マスク・電池充電） 内部ブロック図（頁 p243-ibd-eva） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図244'> fig244 : OperationsView {
        doc /* 図244 APU・油圧の運転と監視 シーケンス図（頁 p244-seq-apu） */
        expose SSD_UC_ORB_001::*;
        expose SSD_BEH_ORB_001::*;
        expose SSD_BEH_ORB_003::*;
        expose SSD_BEH_ORB_004::*;
        expose SSD_MTY_ORB_001::*;
    }
    view <'図245'> fig245 : OperationsView {
        doc /* 図245 DPS の運用管理と MPS の乗員操作 シーケンス図（頁 p245-seq-dps-mps） */
        expose SSD_UC_ORB_001::*;
        expose SSD_BEH_ORB_001::*;
        expose SSD_BEH_ORB_003::*;
        expose SSD_BEH_ORB_004::*;
        expose SSD_MTY_ORB_001::*;
    }
    view <'図246'> fig246 : OperationsView {
        doc /* 図246 EVA の準備・減圧・再与圧・非常時の手順 シーケンス図（頁 p246-seq-eva） */
        expose SSD_UC_ORB_001::*;
        expose SSD_BEH_ORB_001::*;
        expose SSD_BEH_ORB_003::*;
        expose SSD_BEH_ORB_004::*;
        expose SSD_MTY_ORB_001::*;
    }
    view <'図247'> fig247 : OperationsView {
        doc /* 図247 OMS の乗員操作と表示 シーケンス図（頁 p247-seq-oms） */
        expose SSD_UC_ORB_001::*;
        expose SSD_BEH_ORB_001::*;
        expose SSD_BEH_ORB_003::*;
        expose SSD_BEH_ORB_004::*;
        expose SSD_MTY_ORB_001::*;
    }
    view <'図248'> fig248 : OperationsView {
        doc /* 図248 RCS の噴射器冗長管理と乗員操作 シーケンス図（頁 p248-seq-rcs） */
        expose SSD_UC_ORB_001::*;
        expose SSD_BEH_ORB_001::*;
        expose SSD_BEH_ORB_003::*;
        expose SSD_BEH_ORB_004::*;
        expose SSD_MTY_ORB_001::*;
    }
    view <'図249'> fig249 : ResourcesMarginsView {
        doc /* 図249 MOE・MOP・TPM の階層と閾値（頁 p249-tpm-tree） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図250'> fig250 : ResourcesMarginsView {
        doc /* 図250 TPM の飛行ごとの推移（着陸重量・APU の燃料・接地の対地速度）（頁 p250-tpm-trend） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図251'> fig251 : ResourcesMarginsView {
        doc /* 図251 測定指標の取れた飛行数と判定（頁 p251-tpm-coverage） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図252'> fig252 : RequirementsVerificationView {
        doc /* 図252 ECLSS の下位の IF のインタフェース要求の一覧（頁 p252-irq-ecl） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図253'> fig253 : RequirementsVerificationView {
        doc /* 図253 ECLSS 以外の下位の IF のインタフェース要求の一覧（頁 p253-irq-low） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図254'> fig254 : SubsystemBehaviorView {
        doc /* 図254 着陸後から打上げまでの地上処理 活動図（頁 p254-act-turnaround） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図255'> fig255 : SubsystemBehaviorView {
        doc /* 図255 地上の機体の状態 状態遷移図（頁 p255-sm-ground） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図256'> fig256 : SubsystemBehaviorView {
        doc /* 図256 地上処理の段と秒読みの節目（頁 p256-gnd-stages） */
        expose SSD_BEH_ORB_005::*;
        expose SSD_BEH_ORB_006::*;
        expose SSD_BEH_ORB_007::*;
        expose SSD_EMU_EVA_001::*;
        expose SSD_GNC_ORB_001::*;
        expose SSD_ETS_SYS_001::*;
        expose SSD_BEH_ORB_008::*;
        expose SSD_GND_ORB_001::*;
    }
    view <'図257'> fig257 : SafetyFailureView {
        doc /* 図257 飛行中異常の系ごとの件数と区分（頁 p257-ifa-system） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図258'> fig258 : SafetyFailureView {
        doc /* 図258 異常と故障モード・機能行のつなぎ（頁 p258-ifa-fm） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図259'> fig259 : SafetyFailureView {
        doc /* 図259 処置が設計・手順・規則を変えた異常（運用からの帰還）（頁 p259-ifa-feedback） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図260'> fig260 : SafetyFailureView {
        doc /* 図260 故障モードごとの実績（観測された異常の数）（頁 p260-ifa-fmcover） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図261'> fig261 : ResourcesMarginsView {
        doc /* 図261 ペイロード搭載・着陸の制約の一覧（頁 p261-plb-constraints） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図262'> fig262 : ResourcesMarginsView {
        doc /* 図262 緊急着陸の終局荷重係数（頁 p262-plb-loadfactors） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図263'> fig263 : ResourcesMarginsView {
        doc /* 図263 着陸重量の内訳（乾燥重量・貨物・残り）（頁 p263-plb-landing） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図264'> fig264 : SafetyFailureView {
        doc /* 図264 PRA の値（全体・フェーズ・主要シナリオ）（頁 p264-pra-values） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図265'> fig265 : SafetyFailureView {
        doc /* 図265 PRA の主要シナリオとハザード解析の対応・起こりやすさ（頁 p265-pra-compare） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図266'> fig266 : SafetyFailureView {
        doc /* 図266 PRA の上位 10件に現れないハザードと範囲の違い（頁 p266-pra-gaps） */
        expose SSD_BEH_ORB_002::*;
        expose SSD_ANA_ORB_001::*;
        expose SSD_FDIR_ORB_001::*;
        expose SSD_HAZ_ORB_001::*;
        expose SSD_FMM_ORB_001::*;
        expose SSD_FMX_ECL_001::*;
        expose SSD_GNC_ORB_001::*;
        expose SSD_ETS_SYS_001::*;
        expose SSD_ACC_SYS_001::*;
        expose SSD_FMX_ORB_001::*;
        expose SSD_IFA_ORB_001::*;
        expose SSD_PRA_ORB_001::*;
    }
    view <'図267'> fig267 : ModelManagementView {
        doc /* 図267 NASA-HDBK-1009A の作業成果物と本パッケージの対応（頁 p267-mbs-hdbk） */
        expose SSD_VPT_SYS_001::Conventions::*;
        expose SSD_MBS_SYS_001::*;
        expose SSD_GRD_SYS_001::*;
        expose SSD_PLN_SYS_001::*;
    }
    view <'図268'> fig268 : ModelManagementView {
        doc /* 図268 効果的なモデルの基準・性質（SEBoK）と本パッケージの評価（頁 p268-mbs-sebok） */
        expose SSD_VPT_SYS_001::Conventions::*;
        expose SSD_MBS_SYS_001::*;
        expose SSD_GRD_SYS_001::*;
        expose SSD_PLN_SYS_001::*;
    }
    view <'図269'> fig269 : ModelManagementView {
        doc /* 図269 MBSE グリッド（SE プロセス × SysML の柱）と図の分類（頁 p269-grd-grid） */
        expose SSD_VPT_SYS_001::Conventions::*;
        expose SSD_MBS_SYS_001::*;
        expose SSD_GRD_SYS_001::*;
        expose SSD_PLN_SYS_001::*;
    }
    view <'図270'> fig270 : ModelManagementView {
        doc /* 図270 MBSE 手法の工程との対応（Estefan 2008）と ISO/IEC/IEEE 42010（頁 p270-grd-methods） */
        expose SSD_VPT_SYS_001::Conventions::*;
        expose SSD_MBS_SYS_001::*;
        expose SSD_GRD_SYS_001::*;
        expose SSD_PLN_SYS_001::*;
    }
    view <'図271'> fig271 : ModelManagementView {
        doc /* 図271 モデルの構成（種別ごとの文書とパッケージ）（頁 p271-pln-struct） */
        expose SSD_VPT_SYS_001::Conventions::*;
        expose SSD_MBS_SYS_001::*;
        expose SSD_GRD_SYS_001::*;
        expose SSD_PLN_SYS_001::*;
    }
    view <'図272'> fig272 : ModelManagementView {
        doc /* 図272 モデルの更新の手順（10段階）（頁 p272-pln-steps） */
        expose SSD_VPT_SYS_001::Conventions::*;
        expose SSD_MBS_SYS_001::*;
        expose SSD_GRD_SYS_001::*;
        expose SSD_PLN_SYS_001::*;
    }
    view <'図273'> fig273 : ResourcesMarginsView {
        doc /* 図273 打上げ試行の原因の区分（Mission Report の実績）（頁 p273-lav-cause） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図274'> fig274 : ResourcesMarginsView {
        doc /* 図274 機体の系が原因の打上げ延期・スクラブ（機能ブロック別の実績）（頁 p274-lav-block） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図275'> fig275 : ResourcesMarginsView {
        doc /* 図275 飛行ごとの打上げ試行の実績（Mission Report にある分）（頁 p275-lav-flight） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図276'> fig276 : OperationsView {
        doc /* 図276 ミッション類型とユースケースの対応（頁 p276-mty-uc） */
        expose SSD_UC_ORB_001::*;
        expose SSD_BEH_ORB_001::*;
        expose SSD_BEH_ORB_003::*;
        expose SSD_BEH_ORB_004::*;
        expose SSD_MTY_ORB_001::*;
    }
    view <'図277'> fig277 : ResourcesMarginsView {
        doc /* 図277 ミッション類型ごとの飛行の実績（Mission Report にある分）（頁 p277-mty-flights） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図278'> fig278 : VariantsView {
        doc /* 図278 ミッション類型とキット（構成）の対応（頁 p278-mty-kits） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図279'> fig279 : VariantsView {
        doc /* 図279 初飛行・改修の記録（機能ブロック別の実績）（頁 p279-cfg-block） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図280'> fig280 : VariantsView {
        doc /* 図280 構成の変遷の時系列（年代別の実績）（頁 p280-cfg-years） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図281'> fig281 : VariantsView {
        doc /* 図281 初飛行・改修と機体・キット（構成）の対応（頁 p281-cfg-kits） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図282'> fig282 : ResourcesMarginsView {
        doc /* 図282 設計の決定と代替案・理由の記録（頁 p282-dcn-trade） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図283'> fig283 : ResourcesMarginsView {
        doc /* 図283 設計の決定の時系列（年代別の実績）（頁 p283-dcn-years） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図284'> fig284 : VariantsView {
        doc /* 図284 設計の決定と機能ブロック（構成）の対応（頁 p284-dcn-blocks） */
        expose SSD_VAR_ORB_001::*;
        expose SSD_IND_ORB_001::*;
        expose SSD_FLT_ORB_001::*;
        expose SSD_MTY_ORB_001::*;
        expose SSD_CFG_ORB_001::*;
        expose SSD_DCN_ORB_001::*;
    }
    view <'図285'> fig285 : RequirementsVerificationView {
        doc /* 図285 妥当性確認のマトリクス（期待・ケース・判定）（頁 p285-val-matrix） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図286'> fig286 : RequirementsVerificationView {
        doc /* 図286 妥当性確認の実績（期待の達成を飛行の記録から）（頁 p286-val-actual） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図287'> fig287 : RequirementsVerificationView {
        doc /* 図287 妥当性確認と検証の対応（頁 p287-val-ver） */
        expose SSD_RQM_SYS_001::*;
        expose SSD_VER_SYS_001::*;
        expose SSD_RQF_SYS_001::*;
        expose SSD_FLT_ORB_001::*;
        expose SSD_HSI_SYS_001::*;
        expose SSD_RQL_ECL_001::*;
        expose SSD_IRQ_SYS_001::*;
        expose SSD_RQL_SYS_001::*;
        expose SSD_IRQ_ECL_001::*;
        expose SSD_IRQ_LOW_001::*;
        expose SSD_VAL_ORB_001::*;
    }
    view <'図288'> fig288 : ResourcesMarginsView {
        doc /* 図288 飛行ごとの TPS 打痕の数の実績（着陸後の検査）（頁 p288-dmg-flight） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図289'> fig289 : ResourcesMarginsView {
        doc /* 図289 TPS 損傷の原因の区分（事象の件数と機能ブロック）（頁 p289-dmg-cause） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図290'> fig290 : ResourcesMarginsView {
        doc /* 図290 時期ごとの TPS 打痕の数の推移（頁 p290-dmg-period） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図291'> fig291 : ResourcesMarginsView {
        doc /* 図291 プログラム組織の構成（Level・センター・契約者・会議体）（頁 p291-org-structure） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図292'> fig292 : ResourcesMarginsView {
        doc /* 図292 打上げ可否の判断の流れ（Go/No-Go のゲートと審査）（頁 p292-org-gates） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図293'> fig293 : ResourcesMarginsView {
        doc /* 図293 飛行準備の認証の担当と要求（MOD の CoFR）（頁 p293-org-cofr） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図294'> fig294 : ResourcesMarginsView {
        doc /* 図294 費用の記録の一覧（種類・ドルの年・2010 年ドルへの換算）（頁 p294-cst-records） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図295'> fig295 : ResourcesMarginsView {
        doc /* 図295 物価の指数の推移（CPI-U・NNSI と 2010 年ドルへの換算係数）（頁 p295-cst-index） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図296'> fig296 : ResourcesMarginsView {
        doc /* 図296 1飛行あたりの費用と年間飛行数の関係（パラメトリックの式）（頁 p296-cst-param） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図297'> fig297 : ResourcesMarginsView {
        doc /* 図297 着陸の見送り・延期・着陸地の変更・延長の原因の区分（Mission Report の実績）（頁 p297-lnd-cause） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図298'> fig298 : ResourcesMarginsView {
        doc /* 図298 着陸地の変更の計画地と実際の着陸地（Mission Report の実績）（頁 p298-lnd-site） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図299'> fig299 : ResourcesMarginsView {
        doc /* 図299 飛行ごとの着陸の記録（Mission Report にある分の実績）（頁 p299-lnd-flight） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図300'> fig300 : ResourcesMarginsView {
        doc /* 図300 LCC 違反・免除の群ごとの件数（Mission Report の実績）（頁 p300-lcc-group） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図301'> fig301 : ResourcesMarginsView {
        doc /* 図301 限界値と測定値が本文にある LCC 違反・免除の記録（Mission Report の実績）（頁 p301-lcc-values） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図302'> fig302 : ResourcesMarginsView {
        doc /* 図302 飛行ごとの LCC 違反・免除の記録（Mission Report にある分の実績）（頁 p302-lcc-flight） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図303'> fig303 : ResourcesMarginsView {
        doc /* 図303 天候の基準の値：項目ごと・版ごとの件数（頁 p303-wxc-param） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図304'> fig304 : ResourcesMarginsView {
        doc /* 図304 天候の基準の値：2つの飛行規則の版を並べた対（頁 p304-wxc-pairs） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図305'> fig305 : ResourcesMarginsView {
        doc /* 図305 天候の基準の値：場面ごと・版ごとの規則の数（頁 p305-wxc-scene） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図306'> fig306 : ResourcesMarginsView {
        doc /* 図306 延長能力の値：飛行ごとの延長できた時間と平均電力（パラメトリック）（頁 p306-xcp-flight） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図307'> fig307 : ResourcesMarginsView {
        doc /* 図307 延長能力の時間と平均電力の関係（パラメトリック）（頁 p307-xcp-power） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図308'> fig308 : ResourcesMarginsView {
        doc /* 図308 延長能力の値：年代ごとの件数と時間の範囲（パラメトリック）（頁 p308-xcp-decade） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図309'> fig309 : ResourcesMarginsView {
        doc /* 図309 反応剤の消費の値：飛行ごとの燃料電池の酸素・水素・発電量（パラメトリック）（頁 p309-rxn-flight） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図310'> fig310 : ResourcesMarginsView {
        doc /* 図310 反応剤の消費の制約への束ね：1 kWh あたりの酸素・水素と質量比（パラメトリック）（頁 p310-rxn-bind） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図311'> fig311 : ResourcesMarginsView {
        doc /* 図311 反応剤の消費の値：年代ごとの件数と範囲（パラメトリック）（頁 p311-rxn-decade） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図312'> fig312 : ResourcesMarginsView {
        doc /* 図312 天候基準の制約ブロック：飛行規則の限界（パラメトリック図）（頁 p312-wxk-blocks） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図313'> fig313 : ResourcesMarginsView {
        doc /* 図313 天候基準の制約：飛行規則 1996・2002 年版の限界の値（パラメトリック）（頁 p313-wxk-limits） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図314'> fig314 : ResourcesMarginsView {
        doc /* 図314 天候基準の制約：2010 の雷の限界（パラメトリック）（頁 p314-wxk-lightning） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図315'> fig315 : ResourcesMarginsView {
        doc /* 図315 燃料電池の消費の制約ブロック（パラメトリック図）（頁 p315-rxn-par） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図316'> fig316 : InterfacesView {
        doc /* 図316 ECLSS 回路遮断器の割り当て：パネル×バスの配置（頁 p316-cba-panels） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図317'> fig317 : InterfacesView {
        doc /* 図317 ECLSS 回路遮断器の割り当て 内部ブロック図（頁 p317-cba-ibd） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図318'> fig318 : InterfacesView {
        doc /* 図318 ECLSS 回路遮断器の割り当て：境界・未突合の割付の記録（頁 p318-cba-gaps） */
        expose SSD_BLK_SYS_001::*;
        expose SSD_IBD_ORB_001::*;
        expose SSD_EMU_EVA_001::*;
        expose SSD_GNC_ORB_001::*;
        expose SSD_ETS_SYS_001::*;
        expose SSD_BEH_ORB_008::*;
        expose SSD_CBA_ECL_001::*;
    }
    view <'図319'> fig319 : ResourcesMarginsView {
        doc /* 図319 LCC 原典（NSTS 16007 Rev H）の構成：節ごとの項目の件数（頁 p319-lco-sections） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図320'> fig320 : ResourcesMarginsView {
        doc /* 図320 天候の基準の値：LCC 原典 WEA-01 の数値つき規則（頁 p320-lco-wea） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図321'> fig321 : ResourcesMarginsView {
        doc /* 図321 天候の基準の値：2010 の雷の基準と LCC 原典 WEA-01 §1.4 の数・単位の対（頁 p321-lco-lightning） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図322'> fig322 : ResourcesMarginsView {
        doc /* 図322 IOA 原資料の構成：サブシステム分析ワークシートの冊子ごとの件数（頁 p322-ioa-volumes） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図323'> fig323 : ResourcesMarginsView {
        doc /* 図323 IOA の件数の実績：分析ワークシートの頁数と中間報告 Table 1-1 の FMEA 件数の系ごとの対比（頁 p323-ioa-compare） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図324'> fig324 : ResourcesMarginsView {
        doc /* 図324 故障モードとIOA 原資料の対応：FMX の系ごとの故障モード数と IOA の分析冊子（頁 p324-ioa-fmx） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図325'> fig325 : ResourcesMarginsView {
        doc /* 図325 LCC 原典との結び：Mission Report の LCC 違反の記録と LCC の項目（SSID）の結び（頁 p325-lco-join） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図326'> fig326 : ResourcesMarginsView {
        doc /* 図326 IOA の危険度の分布：5フェーズが読めたワークシートの、系ごとの最も厳しい機器の危険度（頁 p326-ioa-dist-sys） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    view <'図327'> fig327 : ResourcesMarginsView {
        doc /* 図327 IOA の危険度の分布：フェーズごとの危険度の値の件数（頁 p327-ioa-dist-phase） */
        expose SSD_PAR_ORB_001::*;
        expose SSD_ANA_ORB_001::*;
        expose SSD_PRF_ORB_001::*;
        expose SSD_TRJ_ORB_001::*;
        expose SSD_TPM_SYS_001::*;
        expose SSD_PLB_ORB_001::*;
        expose SSD_LAV_ORB_001::*;
        expose SSD_MTY_ORB_001::*;
        expose SSD_DCN_ORB_001::*;
        expose SSD_DMG_ORB_001::*;
        expose SSD_ORG_ORB_001::*;
        expose SSD_CST_ORB_001::*;
        expose SSD_LND_ORB_001::*;
        expose SSD_LCC_ORB_001::*;
        expose SSD_WXC_ORB_001::*;
        expose SSD_XCP_ORB_001::*;
        expose SSD_RXN_ORB_001::*;
        expose SSD_WXK_ORB_001::*;
        expose SSD_LCO_ORB_001::*;
        expose SSD_IOA_ORB_001::*;
    }
    // ---- 表記の規約
    package Conventions {
        doc /* 文書の表の ID の形と、出典・文書番号の書き方 */
        metadata def IdConvention { attribute prefix : String; attribute form : String; attribute meaning : String; attribute example : String; attribute count : Integer; }
        metadata def SourceReference { doc /* 出典の公開 URL（頁つき）と照合語（その頁の抽出テキストにある語句） */ attribute url : String; attribute keywords : String[0..*]; }
        metadata def DocumentNumber { doc /* 要素を説明する文書の番号 */ attribute docNo : String; }
        @IdConvention { prefix = "SSD-"; form = "SSD-<種別>-<対象>-<3桁>"; meaning = "文書番号（SSD-種別-対象-連番）"; example = "SSD-FD-OMS-ENG-001"; count = 358; }
        @IdConvention { prefix = "F-"; form = "F-<系>-<下位>-<2桁>"; meaning = "機能行（機能説明書の機能の表）"; example = "F-OMS-ENG-01"; count = 2075; }
        @IdConvention { prefix = "IF-"; form = "IF-<系>-<番号>"; meaning = "インタフェース（所有の文書の IF の表）"; example = "IF-ORB-05"; count = 601; }
        @IdConvention { prefix = "REQ-"; form = "REQ-<系>-<2桁>"; meaning = "要求（要求書）"; example = "REQ-OMS-01"; count = 317; }
        @IdConvention { prefix = "PHY-"; form = "PHY-<系>-<2桁>"; meaning = "機器（物理構成表）"; example = "PHY-CT-01"; count = 138; }
        @IdConvention { prefix = "BUD-"; form = "BUD-<区分>-<2桁>"; meaning = "収支の行（収支表）"; example = "BUD-PWR-05"; count = 19; }
        @IdConvention { prefix = "PAR-"; form = "PAR-<2桁>"; meaning = "パラメータ（パラメトリック定義書）"; example = "PAR-01"; count = 26; }
        @IdConvention { prefix = "UC-"; form = "UC-<2桁>"; meaning = "ユースケース"; example = "UC-07"; count = 12; }
        @IdConvention { prefix = "VC-"; form = "VC-<要求の ID>"; meaning = "検証ケース"; example = "VC-REQ-OMS-01"; count = 212; }
        @IdConvention { prefix = "VF-・MK-"; form = "VF-<2桁>・MK-<2桁>"; meaning = "機体の特徴・ミッションキット"; example = "VF-05"; count = 31; }
        @IdConvention { prefix = "MS-・MC-・DV-・DE-"; form = "MS-・MC-・DV-・DE-<2桁>"; meaning = "質量特性・Δv の値と式"; example = "DV-04"; count = 60; }
        @IdConvention { prefix = "VP-・CN-・SH-"; form = "VP-<2桁>・CN-<2桁>・SH-<略号>"; meaning = "ビューポイント・関心事・関係者"; example = "VP-01"; count = 44; }
        @IdConvention { prefix = "EQ-・EB-・FL-・FI-"; form = "EQ-・EB-・FL-<図>-<2桁>・FI-<2桁>"; meaning = "内部ブロック図の部品・相手・流れ・流れる物"; example = "FL-EPS-03"; count = 2153; }
        @IdConvention { prefix = "TR-・GAP-・IMP-"; form = "TR-<2桁>・GAP-<2桁>[-<2桁>]・IMP-<2桁>"; meaning = "トレースの関係・切れ目・影響分析"; example = "GAP-06-01"; count = 142; }
        @IdConvention { prefix = "CW-・EM-・DT-・RS-・BU-"; form = "CW-・EM-・DT-・RS-・BU-<2桁>"; meaning = "C/W の警報・検知する故障・処置・警報の区分"; example = "CW-05"; count = 155; }
        @IdConvention { prefix = "HZ-・HC-・HM-"; form = "HZ-・HC-・HM-<2桁>"; meaning = "ハザード・原因・管理策"; example = "HZ-01"; count = 134; }
        @IdConvention { prefix = "AV-・SN-・AN-"; form = "AV-・SN-・AN-<2桁>"; meaning = "飛行の実績・スナップショット・異常"; example = "AV-05"; count = 59; }
        @IdConvention { prefix = "RF-・QL-・EV-"; form = "RF-<3桁>・QL-<2桁>・EV-<2桁>"; meaning = "要求の制約・定性の要求・値による判定"; example = "EV-13"; count = 433; }
        @IdConvention { prefix = "FLC-・FT-"; form = "FLC-<2桁>・FT-<飛行>-<2桁>"; meaning = "飛行の構成・飛行試験の結果"; example = "FT-1-01"; count = 104; }
        @IdConvention { prefix = "PFR-・PFD-・PFP-・PFS-・PFC-"; form = "PFR-・PFD-・PFP-・PFS-・PFC-<2桁>"; meaning = "消耗品の率・設計の枯渇・実績の点・予測・比較"; example = "PFD-01"; count = 115; }
        @IdConvention { prefix = "OMSS-・OMST-・RCSS-・RCST-・MPSS-・MPST-・CTSS-・CTST-・PCSS-・PCST-・ODSS-・ODST-"; form = "<系>S-・<系>T-<2桁>"; meaning = "系の状態・遷移（その2）"; example = "OMST-07"; count = 156; }
        @IdConvention { prefix = "HSI-"; form = "HSI-<3桁>"; meaning = "人間系の基準の照合"; example = "HSI-001"; count = 545; }
        @IdConvention { prefix = "EXP-・PRO-"; form = "EXP-<2桁>・PRO-<2桁>"; meaning = "曝露の量・曝露のプロファイル"; example = "EXP-03"; count = 20; }
        @IdConvention { prefix = "FA-・T1-・T2-"; form = "FA-<2桁>・T<作業>-<2桁>"; meaning = "機能の分担・作業の段"; example = "FA-03"; count = 65; }
        @IdConvention { prefix = "HT-・HE-"; form = "HT-<2桁>・HE-<2桁>"; meaning = "誤りの起こる作業・ヒューマンエラー"; example = "HE-01"; count = 47; }
        @IdConvention { prefix = "AL-・LM-・ST-・DC-"; form = "AL-STD-<数>・AL-SH-<数>・LM-<2桁>・ST-<2桁>・DC-<2桁>"; meaning = "警報の区分・区分の対応・作業位置・表示と操作の盤"; example = "DC-01"; count = 58; }
        @IdConvention { prefix = "HF-・CD-・UC-H・ACT-"; form = "HF-<2桁>・CD-<2桁>・UC-H<2桁>・ACT-<2桁>"; meaning = "居住・医療の機能・乗員の1日・居住のユースケース・アクタ"; example = "HF-04"; count = 44; }
        @IdConvention { prefix = "SP-・PA-・EG-"; form = "SP-<2桁>・PA-<2桁>・EG-<2桁>"; meaning = "与圧区画・移動の経路・非常退避のモード"; example = "PA-03"; count = 29; }
        @IdConvention { prefix = "EVM-・HCV-"; form = "EVM-<2桁>・HCV-<2桁>"; meaning = "人間系の評価方法・人間系の関心事"; example = "EVM-03"; count = 22; }
        @IdConvention { prefix = "ATM-P・ATM-M・ATM-S・ATM-V・ATM-E"; form = "ATM-<P|M|S|V|E><2桁>"; meaning = "キャビン大気のパラメータ・式・シナリオ・比較・照合"; example = "ATM-S01"; count = 52; }
        @IdConvention { prefix = "ARSS-・ARST-・FDSS-・FDST-・WATS-・WATT-・WCSS-・WCST-"; form = "<系>S-・<系>T-<2桁>"; meaning = "ECLSS の状態・遷移"; example = "ARST-06"; count = 101; }
        @IdConvention { prefix = "FMX-・FTX-"; form = "FMX-<ブロック>-<2桁>・FTX-<番号>"; meaning = "ECLSS の機能の故障モード・故障の木"; example = "FMX-PCS-01"; count = 258; }
        @IdConvention { prefix = "EMUS-・EMUT-・ALKS-・ALKT-"; form = "<系>S-・<系>T-<2桁>"; meaning = "EMU・エアロックの状態・遷移"; example = "EMUT-05"; count = 63; }
        @IdConvention { prefix = "EPB-P・EPB-M・EPB-R・EPB-E"; form = "EPB-<P|M|R|E><2桁>"; meaning = "EMU の消耗品・前呼吸のパラメータ・式・手順・照合"; example = "EPB-R01"; count = 32; }
        @IdConvention { prefix = "HBX-P・HBX-S・HBX-B・HBX-A・HBX-L"; form = "HBX-<P|S|B|A|L><2桁>"; meaning = "居住の資源の量・収納・収支・実績・基準"; example = "HBX-B01"; count = 106; }
        @IdConvention { prefix = "MED-K・MED-R・MED-T・MED-C・MDD-E"; form = "MED-<K|R|T|C><2桁>・MDD-E<2桁>"; meaning = "医療の構成・役割・訓練・PMC・事象"; example = "MED-K01"; count = 74; }
        @IdConvention { prefix = "GMMS-・GMMT-・DAPS-・DAPT-・IMUS-・IMUT-・NAVS-・NAVT-"; form = "<名前>S-・<名前>T-<2桁>"; meaning = "GN&C の状態・遷移"; example = "GMMT-03"; count = 149; }
        @IdConvention { prefix = "RM-"; form = "RM-<2桁>"; meaning = "GN&C の冗長管理の行"; example = "RM-01"; count = 20; }
        @IdConvention { prefix = "SRBS-・SRBT-・ETKS-・ETKT-"; form = "<名前>S-・<名前>T-<2桁>"; meaning = "SRB・ET の状態・遷移"; example = "SRBT-04"; count = 67; }
        @IdConvention { prefix = "AE-・FMA-・FTA-・AL-"; form = "AE-<事故>-<2桁>・FMA-<系>-<2桁>・FTA-A<番号>・AL-<事故>-<2桁>"; meaning = "事故の事象・故障モード・故障の木・教訓"; example = "AE-51L-01"; count = 105; }
        @IdConvention { prefix = "IRQ-・VC-IRQ-"; form = "IRQ-<SYS|ORB>-<IF の番号>・VC-IRQ-…"; meaning = "インタフェース要求・その検証ケース"; example = "IRQ-ORB-05"; count = 118; }
        @IdConvention { prefix = "LDGS-・LDGT-・VNTS-・VNTT-・CWSS-・CWST-・PRLS-・PRLT-・ESCS-・ESCT-"; form = "<名前>S-・<名前>T-<2桁>"; meaning = "MECH・C/W・PLS・CREW の状態・遷移"; example = "LDGT-03"; count = 179; }
        @IdConvention { prefix = "LRQ-・VC-LRQ-"; form = "LRQ-<系>-<2桁>・VC-LRQ-…"; meaning = "L3 の要求（ECLSS 以外の系）・その検証ケース"; example = "LRQ-GNC-01"; count = 914; }
        @IdConvention { prefix = "TRJ-P・TRJ-M・TRJ-S・TRJ-V・TRJ-E"; form = "TRJ-<P|M|S|V|E><2桁>"; meaning = "上昇・再突入のモデルのパラメータ・式・シナリオ・比較・照合"; example = "TRJ-S01"; count = 78; }
        @IdConvention { prefix = "ACR-"; form = "ACR-<3桁>"; meaning = "略語表の行（略称と正式名称）"; example = "ACR-001"; count = 0; }
        @IdConvention { prefix = "MOE・MOP・TPM"; form = "<MOE|MOP|TPM>-<2桁>"; meaning = "飛行実績の測定指標（MOE・MOP・TPM）"; example = "TPM-01"; count = 15; }
        @IdConvention { prefix = "IRQ-（下位 IF）・VC-IRQ-（下位 IF）"; form = "IRQ-<IF の接頭辞>-<IF の番号>・VC-IRQ-…"; meaning = "下位の IF のインタフェース要求・その検証ケース"; example = "IRQ-APU-08"; count = 1038; }
        @IdConvention { prefix = "GNDS-・GNDT-"; form = "GNDS-<2桁>・GNDT-<2桁>"; meaning = "地上の機体の状態・遷移"; example = "GNDT-01"; count = 26; }
        @IdConvention { prefix = "CMS-・CMT-"; form = "CMS-<2桁>・CMT-<2桁>"; meaning = "地上処理の段・秒読みの節目"; example = "CMS-01"; count = 16; }
        @IdConvention { prefix = "IFA-"; form = "IFA-<3桁>"; meaning = "飛行中異常（Mission Report の番号つき）"; example = "IFA-001"; count = 390; }
        @IdConvention { prefix = "PLB-"; form = "PLB-<2桁>"; meaning = "ペイロード搭載・着陸の制約"; example = "PLB-01"; count = 25; }
        @IdConvention { prefix = "PRA-"; form = "PRA-<2桁>"; meaning = "PRA の主要シナリオ・値"; example = "PRA-01"; count = 10; }
        @IdConvention { prefix = "MBS-"; form = "MBS-<2桁>"; meaning = "MBSE 実践の対応の項目"; example = "MBS-01"; count = 64; }
        @IdConvention { prefix = "GRD-"; form = "GRD-<2桁>"; meaning = "MBSE グリッド・手法対応の項目"; example = "GRD-01"; count = 37; }
        @IdConvention { prefix = "PLN-"; form = "PLN-<2桁>"; meaning = "モデル計画の項目"; example = "PLN-01"; count = 36; }
        @IdConvention { prefix = "LAV-"; form = "LAV-<3桁>"; meaning = "打上げ試行の記録"; example = "LAV-001"; count = 124; }
        @IdConvention { prefix = "MT-"; form = "MT-<2桁>"; meaning = "ミッション類型"; example = "MT-01"; count = 9; }
        @IdConvention { prefix = "MTF-"; form = "MTF-<3桁>"; meaning = "飛行ごとの目的の記録"; example = "MTF-001"; count = 132; }
        @IdConvention { prefix = "CPT-"; form = "CPT-<2桁>"; meaning = "運用概念の章立ての項目"; example = "CPT-01"; count = 15; }
        @IdConvention { prefix = "CFG-"; form = "CFG-<3桁>"; meaning = "初飛行・改修の記録"; example = "CFG-001"; count = 284; }
        @IdConvention { prefix = "DCN-"; form = "DCN-<3桁>"; meaning = "設計の決定の記録"; example = "DCN-001"; count = 19; }
        @IdConvention { prefix = "VEX-"; form = "VEX-<2桁>"; meaning = "関係者の期待"; example = "VEX-01"; count = 28; }
        @IdConvention { prefix = "VCS-"; form = "VCS-<2桁>"; meaning = "妥当性確認のケース"; example = "VCS-01"; count = 17; }
        @IdConvention { prefix = "DMG-"; form = "DMG-<3桁>"; meaning = "TPS 打痕の記録（飛行ごと）"; example = "DMG-001"; count = 112; }
        @IdConvention { prefix = "DME-"; form = "DME-<3桁>"; meaning = "TPS 損傷・デブリの事象"; example = "DME-001"; count = 272; }
        @IdConvention { prefix = "ORG-"; form = "ORG-<3桁>"; meaning = "プログラム組織の記録"; example = "ORG-001"; count = 79; }
        @IdConvention { prefix = "GAT-"; form = "GAT-<3桁>"; meaning = "認証のゲートの記録"; example = "GAT-001"; count = 50; }
        @IdConvention { prefix = "JDG-"; form = "JDG-<3桁>"; meaning = "打上げ・飛行の判断の事例"; example = "JDG-001"; count = 51; }
        @IdConvention { prefix = "CFR-"; form = "CFR-<2桁>"; meaning = "MOD の CoFR の表"; example = "CFR-01"; count = 3; }
        @IdConvention { prefix = "CST-"; form = "CST-<3桁>"; meaning = "費用の記録"; example = "CST-001"; count = 41; }
        @IdConvention { prefix = "XCV-"; form = "XCV-<2桁>"; meaning = "期待の金額の換算"; example = "XCV-01"; count = 14; }
        @IdConvention { prefix = "EQN-"; form = "EQN-<2桁>"; meaning = "パラメトリックの式"; example = "EQN-01"; count = 4; }
        @IdConvention { prefix = "LND-"; form = "LND-<3桁>"; meaning = "着陸の記録"; example = "LND-001"; count = 137; }
        @IdConvention { prefix = "LCC-"; form = "LCC-<3桁>"; meaning = "LCC 違反・免除の記録"; example = "LCC-001"; count = 112; }
        @IdConvention { prefix = "WXC-"; form = "WXC-<3桁>"; meaning = "天候の基準の記録"; example = "WXC-001"; count = 267; }
        @IdConvention { prefix = "XCP-"; form = "XCP-<3桁>"; meaning = "延長能力の記録"; example = "XCP-001"; count = 96; }
        @IdConvention { prefix = "RXN-"; form = "RXN-<3桁>"; meaning = "反応剤の消費の記録"; example = "RXN-001"; count = 108; }
        @IdConvention { prefix = "WXK-"; form = "WXK-<3桁>"; meaning = "天候基準の制約"; example = "WXK-001"; count = 87; }
        @IdConvention { prefix = "WXL-"; form = "WXL-<3桁>"; meaning = "天候の限界の値"; example = "WXL-001"; count = 168; }
        @IdConvention { prefix = "CBA-"; form = "CBA-<3桁>"; meaning = "回路遮断器の割り当ての行"; example = "CBA-001"; count = 84; }
        @IdConvention { prefix = "LCO-"; form = "LCO-<3桁>"; meaning = "LCC 原典の項目の行"; example = "LCO-001"; count = 699; }
        @IdConvention { prefix = "LWR-"; form = "LWR-<3桁>"; meaning = "LCC 原典の天候の規則の行"; example = "LWR-001"; count = 57; }
        @IdConvention { prefix = "IOA-"; form = "IOA-<2桁>"; meaning = "IOA 原資料の冊子の行"; example = "IOA-01"; count = 16; }
        @IdConvention { prefix = "IOW-"; form = "IOW-<3桁>"; meaning = "IOA ワークシートの見本の行"; example = "IOW-001"; count = 20; }
    }
}
