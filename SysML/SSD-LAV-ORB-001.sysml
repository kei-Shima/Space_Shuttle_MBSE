// SysML v2 テキスト：打上げ可用性定義書（打上げ試行のスクラブ・延期の記録と原因の区分）
// SSD-LAV-ORB-001 打上げ可用性定義書（打上げ試行のスクラブ・延期の記録と原因の区分） の表から生成（lib/build_docs_cu.py・rev_cu/cudata.py）。根拠の頁は SSD-LAV-ORB-001 にある。
package SSD_LAV_ORB_001 {
    doc /* SSD-LAV-ORB-001 打上げ可用性定義書（打上げ試行のスクラブ・延期の記録と原因の区分）。打上げ試行（スクラブ・延期）の記録を part def LaunchAttempt の使用として持つ。飛行・日付・種別・原因の区分・機能ブロックは文字列の属性。要求への関係（導出・充足・検証）は張らず、トレースの外に置く。 */
    private import ScalarValues::*;
    part def LaunchAttempt {
        doc /* 打上げ試行（スクラブ・延期）の記録。Mission Report 本文にある分で、打上げ試行の全数ではない。区分・機能ブロックは本書の判断（PLAN_CU 追記1〜3） */
        attribute flight : String;
        attribute attemptDate : String;
        attribute dateBasis : String;
        attribute kind : String;
        attribute causeCategory : String;
        attribute block : String;
    }
    part <'LAV-001'> lav_001 : LaunchAttempt { doc /* STS-1 DPS PASS/BFS timing problem */ :>> flight = "STS-1"; :>> attemptDate = "1981-04-10"; :>> dateBasis = "本文"; :>> kind = "スクラブ"; :>> causeCategory = "機体の系"; :>> block = "DPS"; }
    part <'LAV-002'> lav_002 : LaunchAttempt { doc /* STS-2 hold at T-31 seconds for out-of-tolerance measurements */ :>> flight = "STS-2"; :>> attemptDate = "1981-11-04"; :>> dateBasis = "本文"; :>> kind = "スクラブ"; :>> causeCategory = "地上設備・地上要員"; :>> block = ""; }
    part <'LAV-003'> lav_003 : LaunchAttempt { doc /* STS-2 lubrication oil pressures on auxiliary power units 1 and 3;  */ :>> flight = "STS-2"; :>> attemptDate = ""; :>> dateBasis = "本文"; :>> kind = "延期"; :>> causeCategory = "機体の系"; :>> block = "APU"; }
    part <'LAV-004'> lav_004 : LaunchAttempt { doc /* STS-9  */ :>> flight = "STS-9"; :>> attemptDate = ""; :>> dateBasis = "本文"; :>> kind = "延期"; :>> causeCategory = "原因の記載なし"; :>> block = ""; }
    part <'LAV-005'> lav_005 : LaunchAttempt { doc /* STS-27 winds aloft were higher than the limits (on two occurrences) */ :>> flight = "STS-27"; :>> attemptDate = ""; :>> dateBasis = "本文"; :>> kind = "延期"; :>> causeCategory = "天候"; :>> block = ""; }
    part <'LAV-006'> lav_006 : LaunchAttempt { doc /* STS-30 failure of the engine 1 liquid hydrogen recirculation pump;  */ :>> flight = "STS-30"; :>> attemptDate = "1989-04-28"; :>> dateBasis = "本文"; :>> kind = "スクラブ"; :>> causeCategory = "機体の系"; :>> block = "MPS"; }
    part <'LAV-007'> lav_007 : LaunchAttempt { doc /* STS-31 APU-1 chamber pressure and turbine speed were abnormal at AP */ :>> flight = "STS-31"; :>> attemptDate = "1990-04-10"; :>> dateBasis = "本文"; :>> kind = "スクラブ"; :>> causeCategory = "機体の系"; :>> block = "APU"; }
    part <'LAV-008'> lav_008 : LaunchAttempt { doc /* STS-32 problems in preparing launch pad 39A */ :>> flight = "STS-32"; :>> attemptDate = "1989-12-18"; :>> dateBasis = "予定日"; :>> kind = "延期"; :>> causeCategory = "地上設備・地上要員"; :>> block = ""; }
    part <'LAV-009'> lav_009 : LaunchAttempt { doc /* STS-32 unsatisfactory weather conditions in the Return to Launch Si */ :>> flight = "STS-32"; :>> attemptDate = "1990-01-08"; :>> dateBasis = "本文"; :>> kind = "スクラブ"; :>> causeCategory = "天候"; :>> block = ""; }
    part <'LAV-010'> lav_010 : LaunchAttempt { doc /* STS-34 unsatisfactory weather at the return-to-launch-site (RTLS) r */ :>> flight = "STS-34"; :>> attemptDate = "1989-10-17"; :>> dateBasis = "本文"; :>> kind = "スクラブ"; :>> causeCategory = "天候"; :>> block = ""; }
    part <'LAV-011'> lav_011 : LaunchAttempt { doc /* STS-35 hydrogen leak detected in the region of the 17-inch disconne */ :>> flight = "STS-35"; :>> attemptDate = "1990-05-29"; :>> dateBasis = "本文"; :>> kind = "スクラブ"; :>> causeCategory = "機体の系"; :>> block = "MPS"; }
    part <'LAV-012'> lav_012 : LaunchAttempt { doc /* STS-35 broad-band X-ray telescope encountered a communications prob */ :>> flight = "STS-35"; :>> attemptDate = "1990-08-30"; :>> dateBasis = "本文"; :>> kind = "スクラブ"; :>> causeCategory = "ペイロード・ミッション都合"; :>> block = ""; }
    part <'LAV-013'> lav_013 : LaunchAttempt { doc /* STS-35 unacceptable concentration of hydrogen in the Orbiter aft co */ :>> flight = "STS-35"; :>> attemptDate = "1990-09-05"; :>> dateBasis = "本文"; :>> kind = "スクラブ"; :>> causeCategory = "機体の系"; :>> block = "MPS"; }
    part <'LAV-014'> lav_014 : LaunchAttempt { doc /* STS-35 leak detectors sensed aft compartment hydrogen concentration */ :>> flight = "STS-35"; :>> attemptDate = "1990-09-17"; :>> dateBasis = "本文"; :>> kind = "スクラブ"; :>> causeCategory = "機体の系"; :>> block = "MPS"; }
    part <'LAV-015'> lav_015 : LaunchAttempt { doc /* STS-36 Commander's physical condition was not acceptable for flight */ :>> flight = "STS-36"; :>> attemptDate = "1990-02-22"; :>> dateBasis = "本文"; :>> kind = "延期"; :>> causeCategory = "その他"; :>> block = ""; }
    part <'LAV-016'> lav_016 : LaunchAttempt { doc /* STS-36 second 24-hour delay: crew member still not well, and weathe */ :>> flight = "STS-36"; :>> attemptDate = "1990-02-23"; :>> dateBasis = "逆算"; :>> kind = "延期"; :>> causeCategory = "天候"; :>> block = ""; }
    part <'LAV-017'> lav_017 : LaunchAttempt { doc /* STS-36 third 24-hour delay: predicted unacceptable weather for laun */ :>> flight = "STS-36"; :>> attemptDate = "1990-02-24"; :>> dateBasis = "逆算"; :>> kind = "延期"; :>> causeCategory = "天候"; :>> block = ""; }
    part <'LAV-018'> lav_018 : LaunchAttempt { doc /* STS-36 range safety backup computer failure announced at T-1 minute */ :>> flight = "STS-36"; :>> attemptDate = "1990-02-25"; :>> dateBasis = "逆算"; :>> kind = "スクラブ"; :>> causeCategory = "機体の系"; :>> block = "MPS"; }
    part <'LAV-019'> lav_019 : LaunchAttempt { doc /* STS-36 unacceptable weather conditions at the Return to Launch Site */ :>> flight = "STS-36"; :>> attemptDate = "1990-02-26"; :>> dateBasis = "本文"; :>> kind = "スクラブ"; :>> causeCategory = "天候"; :>> block = ""; }
    part <'LAV-020'> lav_020 : LaunchAttempt { doc /* STS-39 failure of the transducer that measures main engine 3 high p */ :>> flight = "STS-39"; :>> attemptDate = "1991-04-23"; :>> dateBasis = "本文"; :>> kind = "スクラブ"; :>> causeCategory = "機体の系"; :>> block = "MPS"; }
    part <'LAV-021'> lav_021 : LaunchAttempt { doc /* STS-40 failure of multiplexer/demultiplexer (MDM) FA2; failure of g */ :>> flight = "STS-40"; :>> attemptDate = "1991-05-22"; :>> dateBasis = "本文"; :>> kind = "延期"; :>> causeCategory = "機体の系"; :>> block = "DPS"; }
    part <'LAV-022'> lav_022 : LaunchAttempt { doc /* STS-40 scrubbed prior to the T-20 minute hold because of an inertia */ :>> flight = "STS-40"; :>> attemptDate = "1991-06-01"; :>> dateBasis = "本文"; :>> kind = "スクラブ"; :>> causeCategory = "機体の系"; :>> block = "GNC"; }
    part <'LAV-023'> lav_023 : LaunchAttempt { doc /* STS-41D GPC-5 (backup flight system software) exhibited two memory p */ :>> flight = "STS-41D"; :>> attemptDate = "1984-06-25"; :>> dateBasis = "本文"; :>> kind = "スクラブ"; :>> causeCategory = "機体の系"; :>> block = "DPS"; }
    part <'LAV-024'> lav_024 : LaunchAttempt { doc /* STS-41D irregular operation of the main fuel valve on SSME-3 resulte */ :>> flight = "STS-41D"; :>> attemptDate = "1984-06-26"; :>> dateBasis = "本文"; :>> kind = "スクラブ"; :>> causeCategory = "機体の系"; :>> block = "MPS"; }
    part <'LAV-025'> lav_025 : LaunchAttempt { doc /* STS-41D timing problem between the flight software and the MEC (mast */ :>> flight = "STS-41D"; :>> attemptDate = "1984-08-29"; :>> dateBasis = "本文"; :>> kind = "延期"; :>> causeCategory = "機体の系"; :>> block = "DPS"; }
    part <'LAV-026'> lav_026 : LaunchAttempt { doc /* STS-43 SSME 3 controller went to halt when an unrecoverable channel */ :>> flight = "STS-43"; :>> attemptDate = "1991-07-24"; :>> dateBasis = "本文"; :>> kind = "スクラブ"; :>> causeCategory = "機体の系"; :>> block = "MPS"; }
    part <'LAV-027'> lav_027 : LaunchAttempt { doc /* STS-43 crosswinds at the RTLS Shuttle Landing Facility exceeding th */ :>> flight = "STS-43"; :>> attemptDate = "1991-08-01"; :>> dateBasis = "本文"; :>> kind = "スクラブ"; :>> causeCategory = "天候"; :>> block = ""; }
    part <'LAV-028'> lav_028 : LaunchAttempt { doc /* STS-44 scrubbed because of erratic operation of the inertial upper  */ :>> flight = "STS-44"; :>> attemptDate = "1991-11-19"; :>> dateBasis = "本文"; :>> kind = "スクラブ"; :>> causeCategory = "ペイロード・ミッション都合"; :>> block = ""; }
    part <'LAV-029'> lav_029 : LaunchAttempt { doc /* STS-45 troubleshooting activities for the LO2 and LH2 concentration */ :>> flight = "STS-45"; :>> attemptDate = "1992-03-23"; :>> dateBasis = "本文"; :>> kind = "スクラブ"; :>> causeCategory = "機体の系"; :>> block = "MPS"; }
    part <'LAV-030'> lav_030 : LaunchAttempt { doc /* STS-51 anomaly in the mobile launch platform (MLP): system B ET ven */ :>> flight = "STS-51"; :>> attemptDate = "1993-07-17"; :>> dateBasis = "本文"; :>> kind = "スクラブ"; :>> causeCategory = "地上設備・地上要員"; :>> block = ""; }
    part <'LAV-031'> lav_031 : LaunchAttempt { doc /* STS-51 GLS detected out-of-specification underspeed (65,000 rpm vs  */ :>> flight = "STS-51"; :>> attemptDate = "1993-07-24"; :>> dateBasis = "本文"; :>> kind = "スクラブ"; :>> causeCategory = "機体の系"; :>> block = "SRB"; }
    part <'LAV-032'> lav_032 : LaunchAttempt { doc /* STS-51 debris field (Perseid meteoroid shower) of Comet Swift-Tuttl */ :>> flight = "STS-51"; :>> attemptDate = "1993-08-02"; :>> dateBasis = "予定日"; :>> kind = "延期"; :>> causeCategory = "その他"; :>> block = ""; }
    part <'LAV-033'> lav_033 : LaunchAttempt { doc /* STS-51 on-pad abort at T-3 s because of a miscompare in the turbine */ :>> flight = "STS-51"; :>> attemptDate = "1993-08-12"; :>> dateBasis = "本文"; :>> kind = "スクラブ"; :>> causeCategory = "機体の系"; :>> block = "MPS"; }
    part <'LAV-034'> lav_034 : LaunchAttempt { doc /* STS-51 delayed two days to verify that none of the 2N3421 transisto */ :>> flight = "STS-51"; :>> attemptDate = "1993-09-10"; :>> dateBasis = "予定日"; :>> kind = "延期"; :>> causeCategory = "ペイロード・ミッション都合"; :>> block = ""; }
    part <'LAV-035'> lav_035 : LaunchAttempt { doc /* STS-51A scrubbed during the planned hold at T-20 minutes because pre */ :>> flight = "STS-51A"; :>> attemptDate = "1984-11-07"; :>> dateBasis = "本文"; :>> kind = "スクラブ"; :>> causeCategory = "天候"; :>> block = ""; }
    part <'LAV-036'> lav_036 : LaunchAttempt { doc /* STS-51C expected cold temperatures might cause ice formations on the */ :>> flight = "STS-51C"; :>> attemptDate = "1985-01-23"; :>> dateBasis = "本文"; :>> kind = "延期"; :>> causeCategory = "天候"; :>> block = ""; }
    part <'LAV-037'> lav_037 : LaunchAttempt { doc /* STS-51I the launch was scrubbed because thunderstorms had formed and */ :>> flight = "STS-51I"; :>> attemptDate = "1985-08-24"; :>> dateBasis = "本文"; :>> kind = "スクラブ"; :>> causeCategory = "天候"; :>> block = ""; }
    part <'LAV-038'> lav_038 : LaunchAttempt { doc /* STS-51I a GPC (general purpose computer) 5 bite fault occurred; BFS  */ :>> flight = "STS-51I"; :>> attemptDate = "1985-08-25"; :>> dateBasis = "本文"; :>> kind = "スクラブ"; :>> causeCategory = "機体の系"; :>> block = "DPS"; }
    part <'LAV-039'> lav_039 : LaunchAttempt { doc /* STS-55 on-pad abort about 3 seconds prior to the planned lift-off;  */ :>> flight = "STS-55"; :>> attemptDate = "1993-03-22"; :>> dateBasis = "本文"; :>> kind = "スクラブ"; :>> causeCategory = "機体の系"; :>> block = "MPS"; }
    part <'LAV-040'> lav_040 : LaunchAttempt { doc /* STS-55 approximately 9 hours before the planned launch an IMU 2 pla */ :>> flight = "STS-55"; :>> attemptDate = "1993-04-24"; :>> dateBasis = "本文"; :>> kind = "スクラブ"; :>> causeCategory = "機体の系"; :>> block = "GNC"; }
    part <'LAV-041'> lav_041 : LaunchAttempt { doc /* STS-56 aborted at T-11 seconds: hydrogen high-point bleed valve clo */ :>> flight = "STS-56"; :>> attemptDate = "1993-04-06"; :>> dateBasis = "本文"; :>> kind = "スクラブ"; :>> causeCategory = "機体の系"; :>> block = "MPS"; }
    part <'LAV-042'> lav_042 : LaunchAttempt { doc /* STS-57 unacceptable weather at the three trans-Atlantic abort landi */ :>> flight = "STS-57"; :>> attemptDate = "1993-06-20"; :>> dateBasis = "本文"; :>> kind = "スクラブ"; :>> causeCategory = "天候"; :>> block = ""; }
    part <'LAV-043'> lav_043 : LaunchAttempt { doc /* STS-58 countdown was stopped at T-31 seconds because of a Range Saf */ :>> flight = "STS-58"; :>> attemptDate = "1993-10-14"; :>> dateBasis = "本文"; :>> kind = "スクラブ"; :>> causeCategory = "LCC・レンジ(運用の判断)"; :>> block = ""; }
    part <'LAV-044'> lav_044 : LaunchAttempt { doc /* STS-58 scrubbed because the Orbiter S-band transponder 2 failed, an */ :>> flight = "STS-58"; :>> attemptDate = "1993-10-15"; :>> dateBasis = "本文"; :>> kind = "スクラブ"; :>> causeCategory = "機体の系"; :>> block = "CT"; }
    part <'LAV-045'> lav_045 : LaunchAttempt { doc /* STS-59 crosswinds at the Shuttle Landing Facility (SLF) were in exc */ :>> flight = "STS-59"; :>> attemptDate = "1994-04-08"; :>> dateBasis = "本文"; :>> kind = "スクラブ"; :>> causeCategory = "天候"; :>> block = ""; }
    part <'LAV-046'> lav_046 : LaunchAttempt { doc /* STS-61 crosswind at the Shuttle Landing Facility (SLF) exceeded the */ :>> flight = "STS-61"; :>> attemptDate = "1993-12-01"; :>> dateBasis = "本文"; :>> kind = "スクラブ"; :>> causeCategory = "天候"; :>> block = ""; }
    part <'LAV-047'> lav_047 : LaunchAttempt { doc /* STS-61C countdown was behind schedule because of Orbiter closeout wo */ :>> flight = "STS-61C"; :>> attemptDate = "1985-12-18"; :>> dateBasis = "本文"; :>> kind = "延期"; :>> causeCategory = "地上設備・地上要員"; :>> block = ""; }
    part <'LAV-048'> lav_048 : LaunchAttempt { doc /* STS-61C turbine overspeed problem in the SRB hydraulic power unit */ :>> flight = "STS-61C"; :>> attemptDate = "1985-12-19"; :>> dateBasis = "本文"; :>> kind = "延期"; :>> causeCategory = "機体の系"; :>> block = "SRB"; }
    part <'LAV-049'> lav_049 : LaunchAttempt { doc /* STS-61C  */ :>> flight = "STS-61C"; :>> attemptDate = "1986-01-04"; :>> dateBasis = "本文"; :>> kind = "延期"; :>> causeCategory = "原因の記載なし"; :>> block = ""; }
    part <'LAV-050'> lav_050 : LaunchAttempt { doc /* STS-61C MPS liquid-oxygen replenish valve closed indication not rece */ :>> flight = "STS-61C"; :>> attemptDate = "1986-01-06"; :>> dateBasis = "本文"; :>> kind = "スクラブ"; :>> causeCategory = "機体の系"; :>> block = "MPS"; }
    part <'LAV-051'> lav_051 : LaunchAttempt { doc /* STS-61C unacceptable weather conditions at Kennedy Space Center (KSC */ :>> flight = "STS-61C"; :>> attemptDate = "1986-01-07"; :>> dateBasis = "本文"; :>> kind = "スクラブ"; :>> causeCategory = "天候"; :>> block = ""; }
    part <'LAV-052'> lav_052 : LaunchAttempt { doc /* STS-61C unacceptable weather again at KSC */ :>> flight = "STS-61C"; :>> attemptDate = "1986-01-10"; :>> dateBasis = "本文"; :>> kind = "スクラブ"; :>> causeCategory = "天候"; :>> block = ""; }
    part <'LAV-053'> lav_053 : LaunchAttempt { doc /* STS-62 24-hour weather forecast on March 2 indicated adverse weathe */ :>> flight = "STS-62"; :>> attemptDate = "1994-03-03"; :>> dateBasis = "本文"; :>> kind = "延期"; :>> causeCategory = "天候"; :>> block = ""; }
    part <'LAV-054'> lav_054 : LaunchAttempt { doc /* STS-63 launch was delayed (to Feb 3) because inertial measurement u */ :>> flight = "STS-63"; :>> attemptDate = "1995-02-02"; :>> dateBasis = "本文"; :>> kind = "スクラブ"; :>> causeCategory = "機体の系"; :>> block = "GNC"; }
    part <'LAV-055'> lav_055 : LaunchAttempt { doc /* STS-68 SSME 3 high pressure oxidizer turbine (HPOT) discharge tempe */ :>> flight = "STS-68"; :>> attemptDate = "1994-08-18"; :>> dateBasis = "本文"; :>> kind = "スクラブ"; :>> causeCategory = "機体の系"; :>> block = "MPS"; }
    part <'LAV-056'> lav_056 : LaunchAttempt { doc /* STS-69 rescheduled to repair the SRB nozzle */ :>> flight = "STS-69"; :>> attemptDate = "1995-08-03"; :>> dateBasis = "予定日"; :>> kind = "延期"; :>> causeCategory = "機体の系"; :>> block = "SRB"; }
    part <'LAV-057'> lav_057 : LaunchAttempt { doc /* STS-69 fuel cell 2 anomaly: condenser exit temperature for fuel cel */ :>> flight = "STS-69"; :>> attemptDate = "1995-08-31"; :>> dateBasis = "本文"; :>> kind = "スクラブ"; :>> causeCategory = "機体の系"; :>> block = "EPS"; }
    part <'LAV-058'> lav_058 : LaunchAttempt { doc /* STS-71 ET propellant loading could not be performed due to lightnin */ :>> flight = "STS-71"; :>> attemptDate = "1995-06-23"; :>> dateBasis = "本文"; :>> kind = "スクラブ"; :>> causeCategory = "天候"; :>> block = ""; }
    part <'LAV-059'> lav_059 : LaunchAttempt { doc /* STS-71 scrubbed near the end of the T-9 minute hold because of unac */ :>> flight = "STS-71"; :>> attemptDate = "1995-06-24"; :>> dateBasis = "本文"; :>> kind = "スクラブ"; :>> causeCategory = "天候"; :>> block = ""; }
    part <'LAV-060'> lav_060 : LaunchAttempt { doc /* STS-73 hydrogen leak through the Space Shuttle main engine (SSME) 1 */ :>> flight = "STS-73"; :>> attemptDate = "1995-09-28"; :>> dateBasis = "本文"; :>> kind = "スクラブ"; :>> causeCategory = "機体の系"; :>> block = "MPS"; }
    part <'LAV-061'> lav_061 : LaunchAttempt { doc /* STS-73 weather effects from Hurricane Opal resulted in a decision a */ :>> flight = "STS-73"; :>> attemptDate = "1995-10-05"; :>> dateBasis = "本文"; :>> kind = "延期"; :>> causeCategory = "天候"; :>> block = ""; }
    part <'LAV-062'> lav_062 : LaunchAttempt { doc /* STS-73 hydraulic fluid had been inadvertently drained from hydrauli */ :>> flight = "STS-73"; :>> attemptDate = "1995-10-06"; :>> dateBasis = "本文"; :>> kind = "スクラブ"; :>> causeCategory = "地上設備・地上要員"; :>> block = ""; }
    part <'LAV-063'> lav_063 : LaunchAttempt { doc /* STS-73 master events controller 1 (MEC 1) built-in test equipment ( */ :>> flight = "STS-73"; :>> attemptDate = "1995-10-07"; :>> dateBasis = "本文"; :>> kind = "スクラブ"; :>> causeCategory = "機体の系"; :>> block = "EPS"; }
    part <'LAV-064'> lav_064 : LaunchAttempt { doc /* STS-73 rescheduled to October 15 to allow additional time to inspec */ :>> flight = "STS-73"; :>> attemptDate = "1995-10-14"; :>> dateBasis = "本文"; :>> kind = "延期"; :>> causeCategory = "機体の系"; :>> block = "MPS"; }
    part <'LAV-065'> lav_065 : LaunchAttempt { doc /* STS-73 time of launch delayed one hour because weather conditions w */ :>> flight = "STS-73"; :>> attemptDate = "1995-10-15"; :>> dateBasis = "本文"; :>> kind = "スクラブ"; :>> causeCategory = "天候"; :>> block = ""; }
    part <'LAV-066'> lav_066 : LaunchAttempt { doc /* STS-73 The Atlas launch was delayed and the STS-73 launch was resch */ :>> flight = "STS-73"; :>> attemptDate = "1995-10-19"; :>> dateBasis = "本文"; :>> kind = "延期"; :>> causeCategory = "LCC・レンジ(運用の判断)"; :>> block = ""; }
    part <'LAV-067'> lav_067 : LaunchAttempt { doc /* STS-74 unacceptable weather at the TransAtlantic Abort Landing (TAL */ :>> flight = "STS-74"; :>> attemptDate = "1995-11-11"; :>> dateBasis = "本文"; :>> kind = "スクラブ"; :>> causeCategory = "天候"; :>> block = ""; }
    part <'LAV-068'> lav_068 : LaunchAttempt { doc /* STS-76 a one-day launch delay due to weather */ :>> flight = "STS-76"; :>> attemptDate = ""; :>> dateBasis = "本文"; :>> kind = "延期"; :>> causeCategory = "天候"; :>> block = ""; }
    part <'LAV-069'> lav_069 : LaunchAttempt { doc /* STS-83 requirement to install thermal protection around the floodli */ :>> flight = "STS-83"; :>> attemptDate = "1997-04-03"; :>> dateBasis = "予定日"; :>> kind = "延期"; :>> causeCategory = "機体の系"; :>> block = "CREW"; }
    part <'LAV-070'> lav_070 : LaunchAttempt { doc /* STS-88 master alarm for a Launch Commit Criteria (LCC) violation at */ :>> flight = "STS-88"; :>> attemptDate = "1998-12-03"; :>> dateBasis = "本文"; :>> kind = "スクラブ"; :>> causeCategory = "機体の系"; :>> block = "APU"; }
    part <'LAV-071'> lav_071 : LaunchAttempt { doc /* STS-92 scrubbed prior to loading cryogenics into the External Tank  */ :>> flight = "STS-92"; :>> attemptDate = "2000-10-05"; :>> dateBasis = "本文"; :>> kind = "スクラブ"; :>> causeCategory = "機体の系"; :>> block = "ET"; }
    part <'LAV-072'> lav_072 : LaunchAttempt { doc /* STS-92 scrubbed prior to tanking because the winds were too high to */ :>> flight = "STS-92"; :>> attemptDate = "2000-10-09"; :>> dateBasis = "本文"; :>> kind = "スクラブ"; :>> causeCategory = "天候"; :>> block = ""; }
    part <'LAV-073'> lav_073 : LaunchAttempt { doc /* STS-92 scrubbed prior to picking up the countdown at T-20 minutes:  */ :>> flight = "STS-92"; :>> attemptDate = "2000-10-10"; :>> dateBasis = "本文"; :>> kind = "スクラブ"; :>> causeCategory = "地上設備・地上要員"; :>> block = ""; }
    part <'LAV-074'> lav_074 : LaunchAttempt { doc /* STS-93 hazardous gas sample reading from Orbiter aft compartment at */ :>> flight = "STS-93"; :>> attemptDate = "1999-07-20"; :>> dateBasis = "本文"; :>> kind = "スクラブ"; :>> causeCategory = "地上設備・地上要員"; :>> block = ""; }
    part <'LAV-075'> lav_075 : LaunchAttempt { doc /* STS-93 unfavorable weather in the launch area; lightning within the */ :>> flight = "STS-93"; :>> attemptDate = "1999-07-22"; :>> dateBasis = "本文"; :>> kind = "スクラブ"; :>> causeCategory = "天候"; :>> block = ""; }
    part <'LAV-076'> lav_076 : LaunchAttempt { doc /* STS-98 postflight STS-97 Solid Rocket Booster (SRB) in-flight anoma */ :>> flight = "STS-98"; :>> attemptDate = "2000-12-14"; :>> dateBasis = "本文"; :>> kind = "延期"; :>> causeCategory = "機体の系"; :>> block = "SRB"; }
    part <'LAV-077'> lav_077 : LaunchAttempt { doc /* STS-99 scrubbed because of unacceptable weather conditions at the l */ :>> flight = "STS-99"; :>> attemptDate = "2000-01-31"; :>> dateBasis = "本文"; :>> kind = "スクラブ"; :>> causeCategory = "天候"; :>> block = ""; }
    part <'LAV-078'> lav_078 : LaunchAttempt { doc /* STS-101 scrubbed because of excessive crosswinds at Kennedy Space Ce */ :>> flight = "STS-101"; :>> attemptDate = "2000-04-24"; :>> dateBasis = "本文"; :>> kind = "スクラブ"; :>> causeCategory = "天候"; :>> block = ""; }
    part <'LAV-079'> lav_079 : LaunchAttempt { doc /* STS-101 second launch attempt was scrubbed prior to the T-20 minute  */ :>> flight = "STS-101"; :>> attemptDate = "2000-04-25"; :>> dateBasis = "本文"; :>> kind = "スクラブ"; :>> causeCategory = "天候"; :>> block = ""; }
    part <'LAV-080'> lav_080 : LaunchAttempt { doc /* STS-101 third launch attempt was scrubbed because of excessive cross */ :>> flight = "STS-101"; :>> attemptDate = "2000-04-26"; :>> dateBasis = "本文"; :>> kind = "スクラブ"; :>> causeCategory = "天候"; :>> block = ""; }
    part <'LAV-081'> lav_081 : LaunchAttempt { doc /* STS-105 scrubbed during the T-9 minute hold because of unacceptable  */ :>> flight = "STS-105"; :>> attemptDate = "2001-08-09"; :>> dateBasis = "本文"; :>> kind = "スクラブ"; :>> causeCategory = "天候"; :>> block = ""; }
    part <'LAV-082'> lav_082 : LaunchAttempt { doc /* STS-108 Progress resupply vehicle was not hard-docked to the ISS (a  */ :>> flight = "STS-108"; :>> attemptDate = "2001-11-29"; :>> dateBasis = "本文"; :>> kind = "スクラブ"; :>> causeCategory = "ペイロード・ミッション都合"; :>> block = ""; }
    part <'LAV-083'> lav_083 : LaunchAttempt { doc /* STS-108 scrubbed during the T-9 minute hold because of unacceptable  */ :>> flight = "STS-108"; :>> attemptDate = "2001-12-04"; :>> dateBasis = "本文"; :>> kind = "スクラブ"; :>> causeCategory = "天候"; :>> block = ""; }
    part <'LAV-084'> lav_084 : LaunchAttempt { doc /* STS-109 acceptable weather conditions were not predicted; temperatur */ :>> flight = "STS-109"; :>> attemptDate = "2002-02-28"; :>> dateBasis = "本文"; :>> kind = "スクラブ"; :>> causeCategory = "天候"; :>> block = ""; }
    part <'LAV-085'> lav_085 : LaunchAttempt { doc /* STS-110 early in External Tank hydrogen loading in fast-fill mode a  */ :>> flight = "STS-110"; :>> attemptDate = "2002-04-04"; :>> dateBasis = "本文"; :>> kind = "スクラブ"; :>> causeCategory = "地上設備・地上要員"; :>> block = ""; }
    part <'LAV-086'> lav_086 : LaunchAttempt { doc /* STS-111 adverse weather in the launch area; countdown stopped while  */ :>> flight = "STS-111"; :>> attemptDate = "2002-05-30"; :>> dateBasis = "本文"; :>> kind = "スクラブ"; :>> causeCategory = "天候"; :>> block = ""; }
    part <'LAV-087'> lav_087 : LaunchAttempt { doc /* STS-111 adverse weather was again predicted (MMT rescheduled launch  */ :>> flight = "STS-111"; :>> attemptDate = "2002-05-31"; :>> dateBasis = "本文"; :>> kind = "延期"; :>> causeCategory = "天候"; :>> block = ""; }
    part <'LAV-088'> lav_088 : LaunchAttempt { doc /* STS-111 a leaking gaseous nitrogen (GN) regulator in the orbital man */ :>> flight = "STS-111"; :>> attemptDate = "2002-06-03"; :>> dateBasis = "本文"; :>> kind = "延期"; :>> causeCategory = "機体の系"; :>> block = "OMS"; }
    part <'LAV-089'> lav_089 : LaunchAttempt { doc /* STS-112 Hurricane Lili entered the Gulf of Mexico; path uncertain; d */ :>> flight = "STS-112"; :>> attemptDate = "2002-10-02"; :>> dateBasis = "本文"; :>> kind = "延期"; :>> causeCategory = "天候"; :>> block = ""; }
    part <'LAV-090'> lav_090 : LaunchAttempt { doc /* STS-113 high oxygen concentration in the payload bay (midbody oxygen */ :>> flight = "STS-113"; :>> attemptDate = "2002-11-10"; :>> dateBasis = "本文"; :>> kind = "スクラブ"; :>> causeCategory = "機体の系"; :>> block = "ECLSS"; }
    part <'LAV-091'> lav_091 : LaunchAttempt { doc /* STS-113 launch rescheduled for November 22, 2002, so that the Canadi */ :>> flight = "STS-113"; :>> attemptDate = "2002-11-17"; :>> dateBasis = "本文"; :>> kind = "延期"; :>> causeCategory = "機体の系"; :>> block = "PLS"; }
    part <'LAV-092'> lav_092 : LaunchAttempt { doc /* STS-113 countdown stopped during the T-9 minute hold because of adve */ :>> flight = "STS-113"; :>> attemptDate = "2002-11-22"; :>> dateBasis = "本文"; :>> kind = "スクラブ"; :>> causeCategory = "天候"; :>> block = ""; }
    part <'LAV-093'> lav_093 : LaunchAttempt { doc /* STS-114 ET liquid hydrogen (LH2) engine cutoff (ECO) sensor indicati */ :>> flight = "STS-114"; :>> attemptDate = "2005-07-13"; :>> dateBasis = "本文"; :>> kind = "スクラブ"; :>> causeCategory = "機体の系"; :>> block = "MPS"; }
    part <'LAV-094'> lav_094 : LaunchAttempt { doc /* STS-115 a lightning bolt struck the pad and a small power transient  */ :>> flight = "STS-115"; :>> attemptDate = "2006-08-27"; :>> dateBasis = "本文"; :>> kind = "スクラブ"; :>> causeCategory = "天候"; :>> block = ""; }
    part <'LAV-095'> lav_095 : LaunchAttempt { doc /* STS-115 Hurricane Ernesto threatened the East coast of Florida; deci */ :>> flight = "STS-115"; :>> attemptDate = "2006-08-29"; :>> dateBasis = "本文"; :>> kind = "延期"; :>> causeCategory = "天候"; :>> block = ""; }
    part <'LAV-096'> lav_096 : LaunchAttempt { doc /* STS-115 power to the Fuel Cell 1 Coolant Pump alternating current (A */ :>> flight = "STS-115"; :>> attemptDate = "2006-09-06"; :>> dateBasis = "本文"; :>> kind = "スクラブ"; :>> causeCategory = "機体の系"; :>> block = "EPS"; }
    part <'LAV-097'> lav_097 : LaunchAttempt { doc /* STS-115 Liquid Hydrogen (LH2) Engine Cutoff (ECO) sensor no. 3 indic */ :>> flight = "STS-115"; :>> attemptDate = "2006-09-08"; :>> dateBasis = "本文"; :>> kind = "スクラブ"; :>> causeCategory = "機体の系"; :>> block = "MPS"; }
    part <'LAV-098'> lav_098 : LaunchAttempt { doc /* STS-116 Range Safety weather violation (cloud cover) throughout the  */ :>> flight = "STS-116"; :>> attemptDate = "2006-12-07"; :>> dateBasis = "本文"; :>> kind = "スクラブ"; :>> causeCategory = "天候"; :>> block = ""; }
    part <'LAV-099'> lav_099 : LaunchAttempt { doc /* STS-117 a hail storm passed over the launch pad on February 26, 2007 */ :>> flight = "STS-117"; :>> attemptDate = "2007-03-15"; :>> dateBasis = "予定日"; :>> kind = "延期"; :>> causeCategory = "天候"; :>> block = ""; }
    part <'LAV-100'> lav_100 : LaunchAttempt { doc /* STS-118 repeated weather events, mostly lightning events, impacted v */ :>> flight = "STS-118"; :>> attemptDate = "2007-08-07"; :>> dateBasis = "本文"; :>> kind = "延期"; :>> causeCategory = "天候"; :>> block = ""; }
    part <'LAV-101'> lav_101 : LaunchAttempt { doc /* STS-119 postponed at the February 3 Agency Flight Readiness Review ( */ :>> flight = "STS-119"; :>> attemptDate = "2009-02-12"; :>> dateBasis = "本文"; :>> kind = "延期"; :>> causeCategory = "機体の系"; :>> block = "MPS"; }
    part <'LAV-102'> lav_102 : LaunchAttempt { doc /* STS-119 Liquid Hydrogen (LH2) leakage in the area of the Ground Umbi */ :>> flight = "STS-119"; :>> attemptDate = "2009-03-11"; :>> dateBasis = "本文"; :>> kind = "スクラブ"; :>> causeCategory = "機体の系"; :>> block = "ET"; }
    part <'LAV-103'> lav_103 : LaunchAttempt { doc /* STS-121 scrubbed for 24 hr to July 2nd during the T-9 min hold becau */ :>> flight = "STS-121"; :>> attemptDate = "2006-07-01"; :>> dateBasis = "本文"; :>> kind = "スクラブ"; :>> causeCategory = "天候"; :>> block = ""; }
    part <'LAV-104'> lav_104 : LaunchAttempt { doc /* STS-121 scrubbed because of unacceptable weather conditions; 48-hr t */ :>> flight = "STS-121"; :>> attemptDate = "2006-07-02"; :>> dateBasis = "本文"; :>> kind = "スクラブ"; :>> causeCategory = "天候"; :>> block = ""; }
    part <'LAV-105'> lav_105 : LaunchAttempt { doc /* STS-122 scrubbed for 48 hr to December 8th during ET cryogenic loadi */ :>> flight = "STS-122"; :>> attemptDate = "2007-12-06"; :>> dateBasis = "本文"; :>> kind = "スクラブ"; :>> causeCategory = "機体の系"; :>> block = "MPS"; }
    part <'LAV-106'> lav_106 : LaunchAttempt { doc /* STS-122 second launch attempt was scrubbed during fast fill loading  */ :>> flight = "STS-122"; :>> attemptDate = "2007-12-09"; :>> dateBasis = "本文"; :>> kind = "スクラブ"; :>> causeCategory = "機体の系"; :>> block = "MPS"; }
    part <'LAV-107'> lav_107 : LaunchAttempt { doc /* STS-125 A-Side of the SIC&DH had failed in September of 2008, which  */ :>> flight = "STS-125"; :>> attemptDate = "2008-10-11"; :>> dateBasis = "本文"; :>> kind = "延期"; :>> causeCategory = "ペイロード・ミッション都合"; :>> block = ""; }
    part <'LAV-108'> lav_108 : LaunchAttempt { doc /* STS-127 Liquid Hydrogen (LH2) leakage in the area of the Ground Umbi */ :>> flight = "STS-127"; :>> attemptDate = "2009-06-13"; :>> dateBasis = "本文"; :>> kind = "スクラブ"; :>> causeCategory = "機体の系"; :>> block = "ET"; }
    part <'LAV-109'> lav_109 : LaunchAttempt { doc /* STS-127 scrubbed during ET tanking due to another leak at the GUCP */ :>> flight = "STS-127"; :>> attemptDate = "2009-06-17"; :>> dateBasis = "本文"; :>> kind = "スクラブ"; :>> causeCategory = "機体の系"; :>> block = "ET"; }
    part <'LAV-110'> lav_110 : LaunchAttempt { doc /* STS-127 lightning strikes detected in the vicinity of Pad A across t */ :>> flight = "STS-127"; :>> attemptDate = "2009-07-11"; :>> dateBasis = "本文"; :>> kind = "スクラブ"; :>> causeCategory = "天候"; :>> block = ""; }
    part <'LAV-111'> lav_111 : LaunchAttempt { doc /* STS-127 scrubbed during the T-9 min hold due to Return to Launch Sit */ :>> flight = "STS-127"; :>> attemptDate = "2009-07-12"; :>> dateBasis = "本文"; :>> kind = "スクラブ"; :>> causeCategory = "天候"; :>> block = ""; }
    part <'LAV-112'> lav_112 : LaunchAttempt { doc /* STS-127 scrubbed during the T-9 min hold due to lightning within 20  */ :>> flight = "STS-127"; :>> attemptDate = "2009-07-13"; :>> dateBasis = "本文"; :>> kind = "スクラブ"; :>> causeCategory = "天候"; :>> block = ""; }
    part <'LAV-113'> lav_113 : LaunchAttempt { doc /* STS-127 Weather violations late in the count caused the 5th attempt  */ :>> flight = "STS-127"; :>> attemptDate = "2009-07-14"; :>> dateBasis = "本文"; :>> kind = "スクラブ"; :>> causeCategory = "天候"; :>> block = ""; }
    part <'LAV-114'> lav_114 : LaunchAttempt { doc /* STS-128 scrubbed during the T-9 minute hold due to thunderstorms wit */ :>> flight = "STS-128"; :>> attemptDate = "2009-08-25"; :>> dateBasis = "本文"; :>> kind = "スクラブ"; :>> causeCategory = "天候"; :>> block = ""; }
    part <'LAV-115'> lav_115 : LaunchAttempt { doc /* STS-128 LH2 inboard fill-and-drain valve closed-position indicator d */ :>> flight = "STS-128"; :>> attemptDate = "2009-08-26"; :>> dateBasis = "本文"; :>> kind = "スクラブ"; :>> causeCategory = "機体の系"; :>> block = "MPS"; }
    part <'LAV-116'> lav_116 : LaunchAttempt { doc /* STS-128 Mission Management Team decided to delay the launch an addit */ :>> flight = "STS-128"; :>> attemptDate = "2009-08-27"; :>> dateBasis = "本文"; :>> kind = "延期"; :>> causeCategory = "機体の系"; :>> block = "MPS"; }
    part <'LAV-117'> lav_117 : LaunchAttempt { doc /* STS-130 scrubbed because of unfavorable range weather and Return to  */ :>> flight = "STS-130"; :>> attemptDate = "2010-02-07"; :>> dateBasis = "本文"; :>> kind = "スクラブ"; :>> causeCategory = "天候"; :>> block = ""; }
    part <'LAV-118'> lav_118 : LaunchAttempt { doc /* STS-133 repairs on the right Orbital Maneuvering System (OMS) pod; h */ :>> flight = "STS-133"; :>> attemptDate = "2010-11-01"; :>> dateBasis = "本文"; :>> kind = "延期"; :>> causeCategory = "機体の系"; :>> block = "OMS"; }
    part <'LAV-119'> lav_119 : LaunchAttempt { doc /* STS-133 evaluate the condition of the backup controller for SSME 3,  */ :>> flight = "STS-133"; :>> attemptDate = "2010-11-03"; :>> dateBasis = "本文"; :>> kind = "スクラブ"; :>> causeCategory = "機体の系"; :>> block = "MPS"; }
    part <'LAV-120'> lav_120 : LaunchAttempt { doc /* STS-133 unacceptable weather conditions (rain, low clouds, high cros */ :>> flight = "STS-133"; :>> attemptDate = "2010-11-04"; :>> dateBasis = "本文"; :>> kind = "スクラブ"; :>> causeCategory = "天候"; :>> block = ""; }
    part <'LAV-121'> lav_121 : LaunchAttempt { doc /* STS-133 hydrogen leak in the Ground Umbilical Carrier Plate (GUCP) [ */ :>> flight = "STS-133"; :>> attemptDate = "2010-11-05"; :>> dateBasis = "本文"; :>> kind = "スクラブ"; :>> causeCategory = "機体の系"; :>> block = "ET"; }
    part <'LAV-122'> lav_122 : LaunchAttempt { doc /* STS-133 analysis and repair of the cracked ET stringers (cracks foun */ :>> flight = "STS-133"; :>> attemptDate = "2010-11-30"; :>> dateBasis = "本文"; :>> kind = "延期"; :>> causeCategory = "機体の系"; :>> block = "ET"; }
    part <'LAV-123'> lav_123 : LaunchAttempt { doc /* STS-133 more extensive analysis required to build flight rationale f */ :>> flight = "STS-133"; :>> attemptDate = "2010-12-03"; :>> dateBasis = "本文"; :>> kind = "延期"; :>> causeCategory = "機体の系"; :>> block = "ET"; }
    part <'LAV-124'> lav_124 : LaunchAttempt { doc /* STS-134 scrubbed because of a Launch Commit Criteria (LCC) violation */ :>> flight = "STS-134"; :>> attemptDate = "2011-04-29"; :>> dateBasis = "本文"; :>> kind = "スクラブ"; :>> causeCategory = "機体の系"; :>> block = "APU"; }
}
