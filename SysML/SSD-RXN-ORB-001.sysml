// SysML v2 テキスト：反応剤消費実績定義書（燃料電池の酸素・水素の消費と発電量）
// SSD-RXN-ORB-001 反応剤消費実績定義書（燃料電池の酸素・水素の消費と発電量） の表から生成（lib/build_docs_dg.py・rev_dg/rxndata.py）。根拠の頁は SSD-RXN-ORB-001 にある。
package SSD_RXN_ORB_001 {
    doc /* SSD-RXN-ORB-001 反応剤消費実績定義書（燃料電池の酸素・水素の消費と発電量）。飛行ごとの燃料電池の消費を part def ReactantUse の使用として持ち、定義的な制約 constraint def FuelCellConsumption に束ねる（bind）。値は本文のまま、比は本書の計算。設計値との等式は主張せず、要求への関係（導出・充足・検証）は張らず、トレースの外に置く。 */
    private import ScalarValues::*;
    constraint def FuelCellConsumption {
        doc /* 燃料電池の消費の定義的な式（作り方から真になる）。1 kWh あたりの酸素・水素と質量比を、酸素・水素・発電量から出す。設計値（0.7・0.09 lbm/kWh）との等式は主張しない（SSD-PAR-ORB-001 の ReactantBudget にある） */
        in attribute o2Lbm : ScalarValues::Real; in attribute h2Lbm : ScalarValues::Real; in attribute energyKwh : ScalarValues::Real;
        out attribute o2PerKwh : ScalarValues::Real; out attribute h2PerKwh : ScalarValues::Real; out attribute massRatio : ScalarValues::Real;
        o2PerKwh == o2Lbm / energyKwh and h2PerKwh == h2Lbm / energyKwh and massRatio == o2Lbm / h2Lbm
    }
    part def ReactantUse {
        doc /* 1飛行の燃料電池の反応剤の消費。値は本文のとおり（lbm・kWh）。1 kWh あたりの量・質量比は本書の計算。判定は付けない */
        attribute flightName : String;
        attribute launchDate : String;
        attribute o2Lbm : ScalarValues::Real;
        attribute h2Lbm : ScalarValues::Real;
        attribute energyKwh : ScalarValues::Real;
        attribute waterLbm : ScalarValues::Real;
        attribute avgPowerKw : ScalarValues::Real;
        attribute o2PerKwh : ScalarValues::Real;
        attribute h2PerKwh : ScalarValues::Real;
        attribute massRatio : ScalarValues::Real;
        attribute isCounted : ScalarValues::Boolean;
        assert constraint consumption : FuelCellConsumption;
        bind consumption.o2Lbm = o2Lbm;
        bind consumption.h2Lbm = h2Lbm;
        bind consumption.energyKwh = energyKwh;
        bind consumption.o2PerKwh = o2PerKwh;
        bind consumption.h2PerKwh = h2PerKwh;
        bind consumption.massRatio = massRatio;
    }
    part <'RXN-001'> rxn_001 : ReactantUse { doc /* STS-26 */ :>> flightName = "STS-26"; :>> launchDate = "1988-09-29"; :>> o2Lbm = 890.0; :>> h2Lbm = 110.0; :>> energyKwh = 1320.0; :>> waterLbm = 1000.0; :>> isCounted = true; }
    part <'RXN-002'> rxn_002 : ReactantUse { doc /* STS-27 */ :>> flightName = "STS-27"; :>> launchDate = "1988-12-02"; :>> o2Lbm = 1100.0; :>> h2Lbm = 130.0; :>> energyKwh = 1540.0; :>> isCounted = false; }
    part <'RXN-003'> rxn_003 : ReactantUse { doc /* STS-28 */ :>> flightName = "STS-28"; :>> launchDate = "1989-08-08"; :>> o2Lbm = 1126.5; :>> h2Lbm = 144.9; :>> energyKwh = 1694.0; :>> waterLbm = 1271.0; :>> isCounted = false; }
    part <'RXN-004'> rxn_004 : ReactantUse { doc /* STS-29 */ :>> flightName = "STS-29"; :>> launchDate = "1989-03-13"; :>> o2Lbm = 1095.0; :>> h2Lbm = 138.0; :>> energyKwh = 1613.0; :>> waterLbm = 1233.0; :>> avgPowerKw = 13.5; :>> isCounted = false; }
    part <'RXN-005'> rxn_005 : ReactantUse { doc /* STS-30 */ :>> flightName = "STS-30"; :>> launchDate = "1989-05-04"; :>> o2Lbm = 932.0; :>> h2Lbm = 117.5; :>> energyKwh = 1366.0; :>> waterLbm = 1050.0; :>> avgPowerKw = 14.1; :>> isCounted = false; }
    part <'RXN-006'> rxn_006 : ReactantUse { doc /* STS-31 */ :>> flightName = "STS-31"; :>> launchDate = "1990-04-24"; :>> o2Lbm = 1193.7; :>> h2Lbm = 150.0; :>> energyKwh = 1740.0; :>> waterLbm = 1344.1; :>> avgPowerKw = 14.4; :>> isCounted = false; }
    part <'RXN-007'> rxn_007 : ReactantUse { doc /* STS-32 */ :>> flightName = "STS-32"; :>> launchDate = "1990-01-09"; :>> h2Lbm = 308.1; :>> energyKwh = 3565.0; :>> waterLbm = 2754.4; :>> avgPowerKw = 13.7; :>> isCounted = false; }
    part <'RXN-008'> rxn_008 : ReactantUse { doc /* STS-34 */ :>> flightName = "STS-34"; :>> launchDate = "1989-10-18"; :>> o2Lbm = 1136.0; :>> h2Lbm = 142.0; :>> energyKwh = 1626.0; :>> waterLbm = 1278.0; :>> avgPowerKw = 13.6; :>> isCounted = false; }
    part <'RXN-009'> rxn_009 : ReactantUse { doc /* STS-35 */ :>> flightName = "STS-35"; :>> launchDate = "1990-12-02"; :>> o2Lbm = 2549.0; :>> h2Lbm = 321.0; :>> energyKwh = 3606.0; :>> waterLbm = 2870.0; :>> avgPowerKw = 16.8; :>> isCounted = true; }
    part <'RXN-010'> rxn_010 : ReactantUse { doc /* STS-36 */ :>> flightName = "STS-36"; :>> launchDate = "1990-02-28"; :>> o2Lbm = 1016.7; :>> h2Lbm = 128.1; :>> energyKwh = 1467.0; :>> waterLbm = 1144.8; :>> avgPowerKw = 13.6; :>> isCounted = true; }
    part <'RXN-011'> rxn_011 : ReactantUse { doc /* STS-37 */ :>> flightName = "STS-37"; :>> launchDate = "1991-04-05"; :>> o2Lbm = 1559.0; :>> h2Lbm = 187.0; :>> energyKwh = 2165.0; :>> waterLbm = 1627.0; :>> avgPowerKw = 15.1; :>> isCounted = true; }
    part <'RXN-012'> rxn_012 : ReactantUse { doc /* STS-38 */ :>> flightName = "STS-38"; :>> launchDate = "1990-11-15"; :>> o2Lbm = 1079.0; :>> h2Lbm = 135.0; :>> energyKwh = 1570.0; :>> waterLbm = 1214.0; :>> avgPowerKw = 13.3; :>> isCounted = true; }
    part <'RXN-013'> rxn_013 : ReactantUse { doc /* STS-39 */ :>> flightName = "STS-39"; :>> launchDate = "1991-04-28"; :>> o2Lbm = 2115.0; :>> h2Lbm = 266.4; :>> energyKwh = 3083.0; :>> waterLbm = 2381.0; :>> isCounted = false; }
    part <'RXN-014'> rxn_014 : ReactantUse { doc /* STS-40 */ :>> flightName = "STS-40"; :>> launchDate = "1991-06-05"; :>> h2Lbm = 325.9; :>> energyKwh = 3720.0; :>> waterLbm = 2913.0; :>> isCounted = false; }
    part <'RXN-015'> rxn_015 : ReactantUse { doc /* STS-41 */ :>> flightName = "STS-41"; :>> launchDate = ""; :>> o2Lbm = 1016.0; :>> h2Lbm = 128.0; :>> energyKwh = 1495.0; :>> waterLbm = 1144.0; :>> avgPowerKw = 15.3; :>> isCounted = true; }
    part <'RXN-016'> rxn_016 : ReactantUse { doc /* STS-42 */ :>> flightName = "STS-42"; :>> launchDate = "1992-01-22"; :>> o2Lbm = 2310.0; :>> h2Lbm = 291.0; :>> energyKwh = 3317.0; :>> waterLbm = 2601.0; :>> avgPowerKw = 17.2; :>> isCounted = false; }
    part <'RXN-017'> rxn_017 : ReactantUse { doc /* STS-43 */ :>> flightName = "STS-43"; :>> launchDate = "1991-08-02"; :>> o2Lbm = 2109.0; :>> h2Lbm = 266.0; :>> energyKwh = 3062.0; :>> waterLbm = 2375.0; :>> avgPowerKw = 14.4; :>> isCounted = true; }
    part <'RXN-018'> rxn_018 : ReactantUse { doc /* STS-44 */ :>> flightName = "STS-44"; :>> launchDate = "1991-11-24"; :>> o2Lbm = 1453.0; :>> h2Lbm = 183.0; :>> energyKwh = 2138.0; :>> waterLbm = 1636.0; :>> avgPowerKw = 12.8; :>> isCounted = true; }
    part <'RXN-019'> rxn_019 : ReactantUse { doc /* STS-45 */ :>> flightName = "STS-45"; :>> launchDate = "1992-03-24"; :>> o2Lbm = 2291.0; :>> h2Lbm = 289.0; :>> energyKwh = 3378.0; :>> waterLbm = 2580.0; :>> avgPowerKw = 15.8; :>> isCounted = false; }
    part <'RXN-020'> rxn_020 : ReactantUse { doc /* STS-46 */ :>> flightName = "STS-46"; :>> launchDate = "1992-07-31"; :>> o2Lbm = 2054.0; :>> h2Lbm = 258.7; :>> energyKwh = 2987.0; :>> waterLbm = 2312.8; :>> avgPowerKw = 15.6; :>> isCounted = true; }
    part <'RXN-021'> rxn_021 : ReactantUse { doc /* STS-47 */ :>> flightName = "STS-47"; :>> launchDate = "1992-09-12"; :>> h2Lbm = 281.1; :>> energyKwh = 3249.7; :>> waterLbm = 2511.0; :>> avgPowerKw = 17.1; :>> isCounted = false; }
    part <'RXN-022'> rxn_022 : ReactantUse { doc /* STS-48 */ :>> flightName = "STS-48"; :>> launchDate = "1991-09-12"; :>> o2Lbm = 1296.0; :>> h2Lbm = 163.2; :>> energyKwh = 1891.0; :>> waterLbm = 1459.0; :>> avgPowerKw = 14.7; :>> isCounted = true; }
    part <'RXN-023'> rxn_023 : ReactantUse { doc /* STS-49 */ :>> flightName = "STS-49"; :>> launchDate = "1992-05-07"; :>> o2Lbm = 1942.1; :>> h2Lbm = 244.6; :>> energyKwh = 2877.6; :>> waterLbm = 2186.7; :>> avgPowerKw = 13.49; :>> isCounted = true; }
    part <'RXN-024'> rxn_024 : ReactantUse { doc /* STS-50 */ :>> flightName = "STS-50"; :>> launchDate = "1992-06-25"; :>> o2Lbm = 4364.9; :>> h2Lbm = 549.7; :>> energyKwh = 6204.7; :>> waterLbm = 4914.6; :>> avgPowerKw = 18.7; :>> isCounted = true; }
    part <'RXN-025'> rxn_025 : ReactantUse { doc /* STS-51 */ :>> flightName = "STS-51"; :>> launchDate = "1993-09-12"; :>> o2Lbm = 2239.0; :>> h2Lbm = 282.0; :>> energyKwh = 3249.0; :>> waterLbm = 2521.0; :>> avgPowerKw = 13.8; :>> isCounted = true; }
    part <'RXN-026'> rxn_026 : ReactantUse { doc /* STS-52 */ :>> flightName = "STS-52"; :>> launchDate = "1992-10-22"; :>> o2Lbm = 2386.0; :>> h2Lbm = 300.5; :>> energyKwh = 3514.6; :>> waterLbm = 2686.5; :>> avgPowerKw = 14.83; :>> isCounted = true; }
    part <'RXN-027'> rxn_027 : ReactantUse { doc /* STS-53 */ :>> flightName = "STS-53"; :>> launchDate = "1992-12-02"; :>> o2Lbm = 1640.4; :>> h2Lbm = 206.6; :>> energyKwh = 2382.9; :>> waterLbm = 1847.0; :>> avgPowerKw = 13.6; :>> isCounted = true; }
    part <'RXN-028'> rxn_028 : ReactantUse { doc /* STS-54 */ :>> flightName = "STS-54"; :>> launchDate = "1993-01-13"; :>> h2Lbm = 176.9; :>> energyKwh = 2061.8; :>> waterLbm = 1581.5; :>> isCounted = false; }
    part <'RXN-029'> rxn_029 : ReactantUse { doc /* STS-55 */ :>> flightName = "STS-55"; :>> launchDate = "1993-04-26"; :>> o2Lbm = 2950.5; :>> h2Lbm = 371.6; :>> energyKwh = 4296.0; :>> waterLbm = 3322.1; :>> avgPowerKw = 17.9; :>> isCounted = true; }
    part <'RXN-030'> rxn_030 : ReactantUse { doc /* STS-56 */ :>> flightName = "STS-56"; :>> launchDate = "1993-04-08"; :>> h2Lbm = 304.2; :>> energyKwh = 3497.0; :>> waterLbm = 2719.6; :>> isCounted = false; }
    part <'RXN-031'> rxn_031 : ReactantUse { doc /* STS-57 */ :>> flightName = "STS-57"; :>> launchDate = "1993-06-21"; :>> o2Lbm = 2422.0; :>> h2Lbm = 305.0; :>> energyKwh = 3518.0; :>> waterLbm = 2727.0; :>> avgPowerKw = 14.7; :>> isCounted = true; }
    part <'RXN-032'> rxn_032 : ReactantUse { doc /* STS-58 */ :>> flightName = "STS-58"; :>> launchDate = "1993-10-18"; :>> o2Lbm = 4208.0; :>> h2Lbm = 530.0; :>> energyKwh = 6085.0; :>> waterLbm = 4738.0; :>> avgPowerKw = 18.1; :>> isCounted = true; }
    part <'RXN-033'> rxn_033 : ReactantUse { doc /* STS-59 */ :>> flightName = "STS-59"; :>> launchDate = "1994-04-09"; :>> o2Lbm = 2811.0; :>> h2Lbm = 354.0; :>> energyKwh = 4069.0; :>> waterLbm = 3165.0; :>> avgPowerKw = 15.1; :>> isCounted = true; }
    part <'RXN-034'> rxn_034 : ReactantUse { doc /* STS-60 */ :>> flightName = "STS-60"; :>> launchDate = "1994-02-03"; :>> o2Lbm = 2090.0; :>> h2Lbm = 263.3; :>> energyKwh = 3029.0; :>> waterLbm = 2353.0; :>> avgPowerKw = 15.2; :>> isCounted = true; }
    part <'RXN-035'> rxn_035 : ReactantUse { doc /* STS-61 */ :>> flightName = "STS-61"; :>> launchDate = "1993-12-02"; :>> o2Lbm = 2520.0; :>> h2Lbm = 317.0; :>> energyKwh = 3666.0; :>> waterLbm = 2837.0; :>> avgPowerKw = 14.1; :>> isCounted = true; }
    part <'RXN-036'> rxn_036 : ReactantUse { doc /* STS-62 */ :>> flightName = "STS-62"; :>> launchDate = "1994-03-04"; :>> o2Lbm = 3739.0; :>> h2Lbm = 471.0; :>> energyKwh = 5408.0; :>> waterLbm = 4210.0; :>> avgPowerKw = 16.1; :>> isCounted = true; }
    part <'RXN-037'> rxn_037 : ReactantUse { doc /* STS-63 */ :>> flightName = "STS-63"; :>> launchDate = "1995-02-03"; :>> o2Lbm = 2161.0; :>> h2Lbm = 272.0; :>> energyKwh = 3142.0; :>> waterLbm = 2433.0; :>> avgPowerKw = 15.8; :>> isCounted = true; }
    part <'RXN-038'> rxn_038 : ReactantUse { doc /* STS-64 */ :>> flightName = "STS-64"; :>> launchDate = ""; :>> o2Lbm = 2502.0; :>> h2Lbm = 315.0; :>> energyKwh = 3660.0; :>> waterLbm = 2817.0; :>> avgPowerKw = 13.9; :>> isCounted = true; }
    part <'RXN-039'> rxn_039 : ReactantUse { doc /* STS-65 */ :>> flightName = "STS-65"; :>> launchDate = "1994-07-08"; :>> o2Lbm = 4706.0; :>> h2Lbm = 593.0; :>> energyKwh = 6660.0; :>> waterLbm = 5299.0; :>> avgPowerKw = 18.8; :>> isCounted = true; }
    part <'RXN-040'> rxn_040 : ReactantUse { doc /* STS-66 */ :>> flightName = "STS-66"; :>> launchDate = "1994-11-03"; :>> o2Lbm = 2857.0; :>> h2Lbm = 360.0; :>> energyKwh = 4164.0; :>> waterLbm = 3217.0; :>> avgPowerKw = 15.9; :>> isCounted = true; }
    part <'RXN-041'> rxn_041 : ReactantUse { doc /* STS-67 */ :>> flightName = "STS-67"; :>> launchDate = "1995-03-02"; :>> o2Lbm = 5037.0; :>> h2Lbm = 634.0; :>> energyKwh = 7241.0; :>> waterLbm = 5671.0; :>> avgPowerKw = 18.1; :>> isCounted = true; }
    part <'RXN-042'> rxn_042 : ReactantUse { doc /* STS-68 */ :>> flightName = "STS-68"; :>> launchDate = "1994-09-30"; :>> o2Lbm = 2933.0; :>> h2Lbm = 369.0; :>> energyKwh = 4260.0; :>> waterLbm = 3302.0; :>> avgPowerKw = 15.8; :>> isCounted = true; }
    part <'RXN-043'> rxn_043 : ReactantUse { doc /* STS-69 */ :>> flightName = "STS-69"; :>> launchDate = "1995-09-07"; :>> o2Lbm = 2680.0; :>> h2Lbm = 338.0; :>> energyKwh = 3884.0; :>> waterLbm = 3018.0; :>> avgPowerKw = 14.9; :>> isCounted = true; }
    part <'RXN-044'> rxn_044 : ReactantUse { doc /* STS-70 */ :>> flightName = "STS-70"; :>> launchDate = ""; :>> o2Lbm = 1916.0; :>> h2Lbm = 241.0; :>> energyKwh = 2816.0; :>> isCounted = true; }
    part <'RXN-045'> rxn_045 : ReactantUse { doc /* STS-71 */ :>> flightName = "STS-71"; :>> launchDate = "1995-06-27"; :>> o2Lbm = 2724.0; :>> h2Lbm = 343.0; :>> energyKwh = 3942.0; :>> waterLbm = 3066.0; :>> avgPowerKw = 16.7; :>> isCounted = true; }
    part <'RXN-046'> rxn_046 : ReactantUse { doc /* STS-72 */ :>> flightName = "STS-72"; :>> launchDate = "1996-01-11"; :>> o2Lbm = 2048.0; :>> h2Lbm = 258.0; :>> energyKwh = 2964.0; :>> waterLbm = 2305.0; :>> avgPowerKw = 13.8; :>> isCounted = true; }
    part <'RXN-047'> rxn_047 : ReactantUse { doc /* STS-73 */ :>> flightName = "STS-73"; :>> launchDate = "1995-10-20"; :>> o2Lbm = 5179.0; :>> h2Lbm = 652.0; :>> energyKwh = 7446.0; :>> waterLbm = 5831.0; :>> avgPowerKw = 19.5; :>> isCounted = true; }
    part <'RXN-048'> rxn_048 : ReactantUse { doc /* STS-74 */ :>> flightName = "STS-74"; :>> launchDate = "1995-11-12"; :>> o2Lbm = 2155.0; :>> h2Lbm = 271.0; :>> energyKwh = 3120.0; :>> waterLbm = 2426.0; :>> avgPowerKw = 15.9; :>> isCounted = true; }
    part <'RXN-049'> rxn_049 : ReactantUse { doc /* STS-75 */ :>> flightName = "STS-75"; :>> launchDate = "1996-02-22"; :>> o2Lbm = 4326.0; :>> h2Lbm = 545.0; :>> energyKwh = 6291.0; :>> waterLbm = 4871.0; :>> avgPowerKw = 16.7; :>> isCounted = true; }
    part <'RXN-050'> rxn_050 : ReactantUse { doc /* STS-76 */ :>> flightName = "STS-76"; :>> launchDate = "1996-03-22"; :>> o2Lbm = 2438.0; :>> h2Lbm = 307.0; :>> energyKwh = 3525.0; :>> waterLbm = 2745.0; :>> avgPowerKw = 15.9; :>> isCounted = true; }
    part <'RXN-051'> rxn_051 : ReactantUse { doc /* STS-77 */ :>> flightName = "STS-77"; :>> launchDate = "1996-05-19"; :>> o2Lbm = 2745.0; :>> h2Lbm = 346.0; :>> energyKwh = 3924.0; :>> waterLbm = 3091.0; :>> avgPowerKw = 16.3; :>> isCounted = true; }
    part <'RXN-052'> rxn_052 : ReactantUse { doc /* STS-78 */ :>> flightName = "STS-78"; :>> launchDate = "1996-06-20"; :>> o2Lbm = 5320.0; :>> h2Lbm = 670.0; :>> energyKwh = 7675.0; :>> waterLbm = 5990.0; :>> avgPowerKw = 18.9; :>> isCounted = true; }
    part <'RXN-053'> rxn_053 : ReactantUse { doc /* STS-80 */ :>> flightName = "STS-80"; :>> launchDate = "1996-11-19"; :>> o2Lbm = 3989.0; :>> h2Lbm = 502.0; :>> energyKwh = 5856.0; :>> waterLbm = 4492.0; :>> avgPowerKw = 13.8; :>> isCounted = true; }
    part <'RXN-054'> rxn_054 : ReactantUse { doc /* STS-81 */ :>> flightName = "STS-81"; :>> launchDate = "1997-01-12"; :>> o2Lbm = 2671.0; :>> h2Lbm = 336.0; :>> energyKwh = 3862.0; :>> waterLbm = 3007.0; :>> avgPowerKw = 15.8; :>> isCounted = true; }
    part <'RXN-055'> rxn_055 : ReactantUse { doc /* STS-82 */ :>> flightName = "STS-82"; :>> launchDate = "1997-02-11"; :>> o2Lbm = 2507.0; :>> h2Lbm = 316.0; :>> energyKwh = 3676.0; :>> waterLbm = 2823.0; :>> avgPowerKw = 15.3; :>> isCounted = true; }
    part <'RXN-056'> rxn_056 : ReactantUse { doc /* STS-83 */ :>> flightName = "STS-83"; :>> launchDate = "1997-04-04"; :>> o2Lbm = 1201.0; :>> h2Lbm = 151.0; :>> energyKwh = 1709.0; :>> waterLbm = 1352.0; :>> avgPowerKw = 17.9; :>> isCounted = true; }
    part <'RXN-057'> rxn_057 : ReactantUse { doc /* STS-84 */ :>> flightName = "STS-84"; :>> launchDate = "1997-05-15"; :>> o2Lbm = 2443.0; :>> h2Lbm = 308.0; :>> energyKwh = 3548.0; :>> waterLbm = 2750.0; :>> avgPowerKw = 16.0; :>> isCounted = true; }
    part <'RXN-058'> rxn_058 : ReactantUse { doc /* STS-85 */ :>> flightName = "STS-85"; :>> launchDate = "1997-08-07"; :>> o2Lbm = 2945.0; :>> h2Lbm = 371.0; :>> energyKwh = 4308.0; :>> waterLbm = 3316.0; :>> avgPowerKw = 15.1; :>> isCounted = true; }
    part <'RXN-059'> rxn_059 : ReactantUse { doc /* STS-86 */ :>> flightName = "STS-86"; :>> launchDate = "1997-09-25"; :>> o2Lbm = 2706.0; :>> h2Lbm = 341.0; :>> energyKwh = 3950.0; :>> waterLbm = 3047.0; :>> isCounted = false; }
    part <'RXN-060'> rxn_060 : ReactantUse { doc /* STS-87 */ :>> flightName = "STS-87"; :>> launchDate = "1997-11-19"; :>> o2Lbm = 4296.0; :>> h2Lbm = 541.0; :>> energyKwh = 6198.0; :>> waterLbm = 4837.0; :>> avgPowerKw = 16.5; :>> isCounted = false; }
    part <'RXN-061'> rxn_061 : ReactantUse { doc /* STS-88 */ :>> flightName = "STS-88"; :>> launchDate = "1998-12-04"; :>> o2Lbm = 2780.0; :>> h2Lbm = 350.0; :>> energyKwh = 4025.0; :>> waterLbm = 3130.0; :>> avgPowerKw = 14.2; :>> isCounted = true; }
    part <'RXN-062'> rxn_062 : ReactantUse { doc /* STS-89 */ :>> flightName = "STS-89"; :>> launchDate = "1998-01-22"; :>> o2Lbm = 2294.0; :>> h2Lbm = 289.0; :>> energyKwh = 3328.0; :>> waterLbm = 2583.0; :>> avgPowerKw = 15.7; :>> isCounted = true; }
    part <'RXN-063'> rxn_063 : ReactantUse { doc /* STS-90 */ :>> flightName = "STS-90"; :>> launchDate = ""; :>> o2Lbm = 4830.0; :>> h2Lbm = 608.0; :>> energyKwh = 6889.0; :>> waterLbm = 5438.0; :>> avgPowerKw = 18.0; :>> isCounted = true; }
    part <'RXN-064'> rxn_064 : ReactantUse { doc /* STS-91 */ :>> flightName = "STS-91"; :>> launchDate = ""; :>> o2Lbm = 2717.0; :>> h2Lbm = 342.0; :>> energyKwh = 3946.0; :>> waterLbm = 3059.0; :>> avgPowerKw = 16.7; :>> isCounted = true; }
    part <'RXN-065'> rxn_065 : ReactantUse { doc /* STS-92 */ :>> flightName = "STS-92"; :>> launchDate = "2000-10-11"; :>> o2Lbm = 2942.0; :>> h2Lbm = 370.0; :>> energyKwh = 4313.0; :>> waterLbm = 3312.0; :>> avgPowerKw = 14.8; :>> isCounted = true; }
    part <'RXN-066'> rxn_066 : ReactantUse { doc /* STS-93 */ :>> flightName = "STS-93"; :>> launchDate = "1999-07-23"; :>> o2Lbm = 1053.0; :>> h2Lbm = 133.0; :>> energyKwh = 1528.0; :>> waterLbm = 1186.0; :>> avgPowerKw = 12.9; :>> isCounted = true; }
    part <'RXN-067'> rxn_067 : ReactantUse { doc /* STS-94 */ :>> flightName = "STS-94"; :>> launchDate = ""; :>> o2Lbm = 5300.0; :>> h2Lbm = 667.0; :>> energyKwh = 7611.0; :>> waterLbm = 5967.0; :>> avgPowerKw = 20.2; :>> isCounted = true; }
    part <'RXN-068'> rxn_068 : ReactantUse { doc /* STS-95 */ :>> flightName = "STS-95"; :>> launchDate = "1998-10-29"; :>> o2Lbm = 2652.0; :>> h2Lbm = 334.0; :>> energyKwh = 3818.0; :>> waterLbm = 2986.0; :>> avgPowerKw = 17.9; :>> isCounted = true; }
    part <'RXN-069'> rxn_069 : ReactantUse { doc /* STS-96 */ :>> flightName = "STS-96"; :>> launchDate = "1999-05-27"; :>> o2Lbm = 2500.0; :>> h2Lbm = 315.0; :>> energyKwh = 3648.0; :>> isCounted = false; }
    part <'RXN-070'> rxn_070 : ReactantUse { doc /* STS-97 */ :>> flightName = "STS-97"; :>> launchDate = "2000-11-30"; :>> o2Lbm = 2387.0; :>> h2Lbm = 301.0; :>> energyKwh = 3464.0; :>> waterLbm = 2688.0; :>> avgPowerKw = 13.3; :>> isCounted = true; }
    part <'RXN-071'> rxn_071 : ReactantUse { doc /* STS-98 */ :>> flightName = "STS-98"; :>> launchDate = "2001-02-07"; :>> o2Lbm = 2981.0; :>> h2Lbm = 375.0; :>> energyKwh = 4356.0; :>> waterLbm = 3357.0; :>> avgPowerKw = 14.1; :>> isCounted = true; }
    part <'RXN-072'> rxn_072 : ReactantUse { doc /* STS-99 */ :>> flightName = "STS-99"; :>> launchDate = "2000-02-11"; :>> o2Lbm = 3021.0; :>> h2Lbm = 380.0; :>> energyKwh = 4378.0; :>> waterLbm = 3401.0; :>> avgPowerKw = 16.2; :>> isCounted = true; }
    part <'RXN-073'> rxn_073 : ReactantUse { doc /* STS-100 */ :>> flightName = "STS-100"; :>> launchDate = "2001-04-19"; :>> o2Lbm = 2627.0; :>> h2Lbm = 331.0; :>> energyKwh = 3847.0; :>> waterLbm = 2958.0; :>> avgPowerKw = 13.5; :>> isCounted = true; }
    part <'RXN-074'> rxn_074 : ReactantUse { doc /* STS-101 */ :>> flightName = "STS-101"; :>> launchDate = "2000-05-19"; :>> o2Lbm = 2583.0; :>> h2Lbm = 325.0; :>> energyKwh = 3765.0; :>> waterLbm = 2908.0; :>> avgPowerKw = 15.9; :>> isCounted = true; }
    part <'RXN-075'> rxn_075 : ReactantUse { doc /* STS-102 */ :>> flightName = "STS-102"; :>> launchDate = "2001-03-08"; :>> o2Lbm = 2884.0; :>> h2Lbm = 363.0; :>> energyKwh = 4243.0; :>> waterLbm = 3247.0; :>> avgPowerKw = 13.8; :>> isCounted = true; }
    part <'RXN-076'> rxn_076 : ReactantUse { doc /* STS-103 */ :>> flightName = "STS-103"; :>> launchDate = "1999-12-19"; :>> o2Lbm = 2041.0; :>> h2Lbm = 257.0; :>> energyKwh = 2982.0; :>> waterLbm = 2298.0; :>> avgPowerKw = 15.6; :>> isCounted = true; }
    part <'RXN-077'> rxn_077 : ReactantUse { doc /* STS-104 */ :>> flightName = "STS-104"; :>> launchDate = "2001-07-12"; :>> o2Lbm = 2908.0; :>> h2Lbm = 366.0; :>> energyKwh = 4249.0; :>> waterLbm = 3274.0; :>> avgPowerKw = 13.9; :>> isCounted = true; }
    part <'RXN-078'> rxn_078 : ReactantUse { doc /* STS-105 */ :>> flightName = "STS-105"; :>> launchDate = "2001-08-10"; :>> o2Lbm = 2703.0; :>> h2Lbm = 340.0; :>> energyKwh = 3972.0; :>> waterLbm = 3043.0; :>> avgPowerKw = 13.9; :>> isCounted = true; }
    part <'RXN-079'> rxn_079 : ReactantUse { doc /* STS-106 */ :>> flightName = "STS-106"; :>> launchDate = "2000-09-08"; :>> o2Lbm = 2881.0; :>> h2Lbm = 363.0; :>> energyKwh = 4204.0; :>> waterLbm = 3244.0; :>> avgPowerKw = 14.8; :>> isCounted = true; }
    part <'RXN-080'> rxn_080 : ReactantUse { doc /* STS-107 */ :>> flightName = "STS-107"; :>> launchDate = "2003-01-16"; :>> o2Lbm = 4505.0; :>> h2Lbm = 567.0; :>> energyKwh = 6440.0; :>> waterLbm = 5072.0; :>> avgPowerKw = 16.8; :>> isCounted = true; }
    part <'RXN-081'> rxn_081 : ReactantUse { doc /* STS-108 */ :>> flightName = "STS-108"; :>> launchDate = "2001-12-05"; :>> o2Lbm = 2687.0; :>> h2Lbm = 338.0; :>> energyKwh = 3912.0; :>> waterLbm = 3025.0; :>> avgPowerKw = 13.8; :>> isCounted = true; }
    part <'RXN-082'> rxn_082 : ReactantUse { doc /* STS-109 */ :>> flightName = "STS-109"; :>> launchDate = "2002-03-01"; :>> o2Lbm = 2659.0; :>> h2Lbm = 335.0; :>> energyKwh = 3858.0; :>> waterLbm = 2994.0; :>> avgPowerKw = 14.7; :>> isCounted = true; }
    part <'RXN-083'> rxn_083 : ReactantUse { doc /* STS-110 */ :>> flightName = "STS-110"; :>> launchDate = "2002-04-08"; :>> o2Lbm = 2416.0; :>> h2Lbm = 304.0; :>> energyKwh = 3521.0; :>> waterLbm = 2720.0; :>> avgPowerKw = 13.6; :>> isCounted = true; }
    part <'RXN-084'> rxn_084 : ReactantUse { doc /* STS-111 */ :>> flightName = "STS-111"; :>> launchDate = "2002-06-05"; :>> o2Lbm = 3094.0; :>> h2Lbm = 390.0; :>> energyKwh = 4525.0; :>> waterLbm = 3484.0; :>> avgPowerKw = 13.6; :>> isCounted = true; }
    part <'RXN-085'> rxn_085 : ReactantUse { doc /* STS-112 */ :>> flightName = "STS-112"; :>> launchDate = "2002-10-07"; :>> o2Lbm = 2377.0; :>> h2Lbm = 299.0; :>> energyKwh = 3481.0; :>> waterLbm = 2676.0; :>> avgPowerKw = 13.4; :>> isCounted = true; }
    part <'RXN-086'> rxn_086 : ReactantUse { doc /* STS-113 */ :>> flightName = "STS-113"; :>> launchDate = "2002-11-23"; :>> o2Lbm = 2954.0; :>> h2Lbm = 372.0; :>> energyKwh = 4316.0; :>> waterLbm = 3326.0; :>> avgPowerKw = 13.0; :>> isCounted = true; }
    part <'RXN-087'> rxn_087 : ReactantUse { doc /* STS-114 */ :>> flightName = "STS-114"; :>> launchDate = "2005-07-26"; :>> o2Lbm = 3076.0; :>> h2Lbm = 387.0; :>> energyKwh = 4526.0; :>> waterLbm = 3463.0; :>> avgPowerKw = 13.6; :>> isCounted = true; }
    part <'RXN-088'> rxn_088 : ReactantUse { doc /* STS-115 */ :>> flightName = "STS-115"; :>> launchDate = "2006-09-09"; :>> o2Lbm = 2595.0; :>> h2Lbm = 327.0; :>> energyKwh = 3810.0; :>> waterLbm = 2922.0; :>> avgPowerKw = 13.5; :>> isCounted = true; }
    part <'RXN-089'> rxn_089 : ReactantUse { doc /* STS-116 */ :>> flightName = "STS-116"; :>> launchDate = "2006-12-09"; :>> o2Lbm = 3001.0; :>> h2Lbm = 378.0; :>> energyKwh = 4384.0; :>> waterLbm = 3379.0; :>> avgPowerKw = 14.2; :>> isCounted = true; }
    part <'RXN-090'> rxn_090 : ReactantUse { doc /* STS-117 */ :>> flightName = "STS-117"; :>> launchDate = "2007-06-08"; :>> o2Lbm = 2901.0; :>> h2Lbm = 365.0; :>> energyKwh = 4269.0; :>> waterLbm = 3267.0; :>> avgPowerKw = 12.8; :>> isCounted = true; }
    part <'RXN-091'> rxn_091 : ReactantUse { doc /* STS-118 */ :>> flightName = "STS-118"; :>> launchDate = "2007-08-08"; :>> o2Lbm = 2088.0; :>> h2Lbm = 263.0; :>> energyKwh = 3061.0; :>> waterLbm = 2351.0; :>> avgPowerKw = 10.0; :>> isCounted = true; }
    part <'RXN-092'> rxn_092 : ReactantUse { doc /* STS-119 */ :>> flightName = "STS-119"; :>> launchDate = "2009-03-15"; :>> o2Lbm = 2211.0; :>> h2Lbm = 278.0; :>> energyKwh = 3272.0; :>> waterLbm = 2490.0; :>> avgPowerKw = 10.6; :>> isCounted = true; }
    part <'RXN-093'> rxn_093 : ReactantUse { doc /* STS-120 */ :>> flightName = "STS-120"; :>> launchDate = "2007-10-23"; :>> o2Lbm = 2517.0; :>> h2Lbm = 317.0; :>> energyKwh = 3711.0; :>> waterLbm = 2833.0; :>> avgPowerKw = 10.24; :>> isCounted = true; }
    part <'RXN-094'> rxn_094 : ReactantUse { doc /* STS-121 */ :>> flightName = "STS-121"; :>> launchDate = "2006-07-04"; :>> o2Lbm = 2836.0; :>> h2Lbm = 357.0; :>> energyKwh = 4172.0; :>> waterLbm = 3193.0; :>> avgPowerKw = 13.6; :>> isCounted = true; }
    part <'RXN-095'> rxn_095 : ReactantUse { doc /* STS-122 */ :>> flightName = "STS-122"; :>> launchDate = "2008-02-07"; :>> o2Lbm = 2827.0; :>> h2Lbm = 356.0; :>> energyKwh = 4126.0; :>> waterLbm = 3183.0; :>> avgPowerKw = 13.5; :>> isCounted = true; }
    part <'RXN-096'> rxn_096 : ReactantUse { doc /* STS-123 */ :>> flightName = "STS-123"; :>> launchDate = "2008-03-11"; :>> o2Lbm = 2378.0; :>> h2Lbm = 299.0; :>> energyKwh = 3507.0; :>> waterLbm = 2677.0; :>> avgPowerKw = 9.3; :>> isCounted = true; }
    part <'RXN-097'> rxn_097 : ReactantUse { doc /* STS-124 */ :>> flightName = "STS-124"; :>> launchDate = "2008-05-31"; :>> o2Lbm = 2206.0; :>> h2Lbm = 278.0; :>> energyKwh = 3265.0; :>> waterLbm = 2484.0; :>> avgPowerKw = 9.9; :>> isCounted = true; }
    part <'RXN-098'> rxn_098 : ReactantUse { doc /* STS-125 */ :>> flightName = "STS-125"; :>> launchDate = "2009-05-11"; :>> o2Lbm = 3198.0; :>> h2Lbm = 403.0; :>> energyKwh = 4630.0; :>> waterLbm = 3601.0; :>> avgPowerKw = 15.0; :>> isCounted = true; }
    part <'RXN-099'> rxn_099 : ReactantUse { doc /* STS-126 */ :>> flightName = "STS-126"; :>> launchDate = "2008-11-14"; :>> o2Lbm = 2446.0; :>> h2Lbm = 308.0; :>> energyKwh = 3619.0; :>> waterLbm = 2754.0; :>> avgPowerKw = 9.5; :>> isCounted = true; }
    part <'RXN-100'> rxn_100 : ReactantUse { doc /* STS-127 */ :>> flightName = "STS-127"; :>> launchDate = "2009-07-15"; :>> o2Lbm = 2441.0; :>> h2Lbm = 307.0; :>> energyKwh = 3621.0; :>> waterLbm = 2749.0; :>> avgPowerKw = 9.6; :>> isCounted = true; }
    part <'RXN-101'> rxn_101 : ReactantUse { doc /* STS-128 */ :>> flightName = "STS-128"; :>> launchDate = "2009-08-28"; :>> o2Lbm = 2159.0; :>> h2Lbm = 272.0; :>> energyKwh = 3206.0; :>> waterLbm = 2431.0; :>> avgPowerKw = 9.6; :>> isCounted = true; }
    part <'RXN-102'> rxn_102 : ReactantUse { doc /* STS-129 */ :>> flightName = "STS-129"; :>> launchDate = "2009-11-16"; :>> o2Lbm = 2520.0; :>> h2Lbm = 317.0; :>> energyKwh = 3669.0; :>> waterLbm = 2838.0; :>> avgPowerKw = 14.2; :>> isCounted = true; }
    part <'RXN-103'> rxn_103 : ReactantUse { doc /* STS-130 */ :>> flightName = "STS-130"; :>> launchDate = "2010-02-08"; :>> o2Lbm = 2054.0; :>> h2Lbm = 259.0; :>> energyKwh = 3044.0; :>> waterLbm = 2313.0; :>> avgPowerKw = 9.2; :>> isCounted = true; }
    part <'RXN-104'> rxn_104 : ReactantUse { doc /* STS-131 */ :>> flightName = "STS-131"; :>> launchDate = "2010-04-05"; :>> o2Lbm = 2239.0; :>> h2Lbm = 282.0; :>> energyKwh = 3317.0; :>> waterLbm = 2521.0; :>> avgPowerKw = 9.1; :>> isCounted = true; }
    part <'RXN-105'> rxn_105 : ReactantUse { doc /* STS-132 */ :>> flightName = "STS-132"; :>> launchDate = "2010-05-14"; :>> o2Lbm = 2673.0; :>> h2Lbm = 337.0; :>> energyKwh = 3896.0; :>> waterLbm = 3009.0; :>> avgPowerKw = 13.8; :>> isCounted = true; }
    part <'RXN-106'> rxn_106 : ReactantUse { doc /* STS-133 */ :>> flightName = "STS-133"; :>> launchDate = "2011-02-24"; :>> o2Lbm = 1886.0; :>> h2Lbm = 238.0; :>> energyKwh = 2791.0; :>> waterLbm = 2124.0; :>> avgPowerKw = 9.1; :>> isCounted = true; }
    part <'RXN-107'> rxn_107 : ReactantUse { doc /* STS-134 */ :>> flightName = "STS-134"; :>> launchDate = "2011-05-16"; :>> o2Lbm = 2317.0; :>> h2Lbm = 292.0; :>> energyKwh = 3409.0; :>> waterLbm = 2609.0; :>> avgPowerKw = 9.0; :>> isCounted = true; }
    part <'RXN-108'> rxn_108 : ReactantUse { doc /* STS-135 */ :>> flightName = "STS-135"; :>> launchDate = "2011-07-08"; :>> o2Lbm = 2856.0; :>> h2Lbm = 360.0; :>> energyKwh = 4159.0; :>> waterLbm = 3216.0; :>> avgPowerKw = 13.6; :>> isCounted = true; }
}
