// SysML v2 テキスト：着陸可用性定義書（着陸の見送り・延期・着陸地の変更・機内の延長の記録と原因の区分）
// SSD-LND-ORB-001 着陸可用性定義書（着陸の見送り・延期・着陸地の変更・機内の延長の記録と原因の区分） の表から生成（lib/build_docs_dc.py・rev_dc/lnddata.py）。根拠の頁は SSD-LND-ORB-001 にある。
package SSD_LND_ORB_001 {
    doc /* SSD-LND-ORB-001 着陸可用性定義書（着陸の見送り・延期・着陸地の変更・機内の延長の記録と原因の区分）。着陸の見送り・延期・着陸地の変更・機内の延長の記録を part def LandingEvent の使用として持つ。飛行・日付・種別・計画と実際の着陸地・原因の区分は属性。要求への関係（導出・充足・検証）は張らず、トレースの外に置く。 */
    private import ScalarValues::*;
    part def LandingEvent {
        doc /* 着陸の見送り・延期・着陸地の変更、または機内で決めた延長の記録。Mission Report 本文にある分で、着陸の全数ではない。区分は本書の判断（PLAN_DC 追記1〜4） */
        attribute flight : String;
        attribute eventDate : String;
        attribute dateBasis : String;
        attribute kind : String;
        attribute inFlightExtension : ScalarValues::Boolean;
        attribute plannedSite : String;
        attribute actualSite : String;
        attribute causeCategory : String;
    }
    part <'LND-001'> lnd_001 : LandingEvent { doc /* STS-3 adverse (wet) lakebed runway conditions */ :>> flight = "STS-3"; :>> eventDate = ""; :>> dateBasis = "日付なし"; :>> kind = "着陸地の変更"; :>> inFlightExtension = false; :>> plannedSite = "Edwards"; :>> actualSite = "White Sands"; :>> causeCategory = "天候"; }
    part <'LND-002'> lnd_002 : LandingEvent { doc /* STS-3 weather conditions at the Northrup strip */ :>> flight = "STS-3"; :>> eventDate = ""; :>> dateBasis = "日付なし"; :>> kind = "延期"; :>> inFlightExtension = false; :>> plannedSite = "Northrup"; :>> actualSite = ""; :>> causeCategory = "天候"; }
    part <'LND-003'> lnd_003 : LandingEvent { doc /* STS-4  */ :>> flight = "STS-4"; :>> eventDate = ""; :>> dateBasis = "日付なし"; :>> kind = "見送り"; :>> inFlightExtension = false; :>> plannedSite = ""; :>> actualSite = ""; :>> causeCategory = "原因の記載なし"; }
    part <'LND-004'> lnd_004 : LandingEvent { doc /* STS-7 Poor weather conditions at KSC */ :>> flight = "STS-7"; :>> eventDate = "1983-06-24"; :>> dateBasis = "本文の通日・日付から担当が換算"; :>> kind = "見送り"; :>> inFlightExtension = false; :>> plannedSite = "KSC"; :>> actualSite = ""; :>> causeCategory = "天候"; }
    part <'LND-005'> lnd_005 : LandingEvent { doc /* STS-7 weather conditions did not improve adequately to allow a lan */ :>> flight = "STS-7"; :>> eventDate = "1983-06-24"; :>> dateBasis = "本文の通日・日付から担当が換算"; :>> kind = "着陸地の変更"; :>> inFlightExtension = false; :>> plannedSite = "KSC"; :>> actualSite = "Edwards"; :>> causeCategory = "天候"; }
    part <'LND-006'> lnd_006 : LandingEvent { doc /* STS-9 Because of the GPC and IMU failures and analysis required, t */ :>> flight = "STS-9"; :>> eventDate = "1983-12-08"; :>> dateBasis = "本文の通日・日付から担当が換算"; :>> kind = "見送り"; :>> inFlightExtension = false; :>> plannedSite = ""; :>> actualSite = "Edwards"; :>> causeCategory = "機体の系"; }
    part <'LND-007'> lnd_007 : LandingEvent { doc /* STS-9 Because of this lower usage, adequate consumables remained t */ :>> flight = "STS-9"; :>> eventDate = ""; :>> dateBasis = "日付なし"; :>> kind = "延期"; :>> inFlightExtension = true; :>> plannedSite = ""; :>> actualSite = ""; :>> causeCategory = "ミッション都合"; }
    part <'LND-008'> lnd_008 : LandingEvent { doc /* STS-32 GPC 5 (BFS software resident) registered illegal engage inpu */ :>> flight = "STS-32"; :>> eventDate = "1990-01-20"; :>> dateBasis = "本文の通日・日付から担当が換算"; :>> kind = "見送り"; :>> inFlightExtension = false; :>> plannedSite = "Edwards"; :>> actualSite = ""; :>> causeCategory = "機体の系"; }
    part <'LND-009'> lnd_009 : LandingEvent { doc /* STS-32 unacceptable weather (fog) at the primary landing site, Edwa */ :>> flight = "STS-32"; :>> eventDate = ""; :>> dateBasis = "日付なし"; :>> kind = "延期"; :>> inFlightExtension = false; :>> plannedSite = "Edwards"; :>> actualSite = ""; :>> causeCategory = "天候"; }
    part <'LND-010'> lnd_010 : LandingEvent { doc /* STS-33 weather conditions unacceptable at that time (text continues */ :>> flight = "STS-33"; :>> eventDate = "1989-11-27"; :>> dateBasis = "本文"; :>> kind = "見送り"; :>> inFlightExtension = false; :>> plannedSite = ""; :>> actualSite = "Edwards"; :>> causeCategory = "天候"; }
    part <'LND-011'> lnd_011 : LandingEvent { doc /* STS-33 unacceptable wind conditions at the landing sites */ :>> flight = "STS-33"; :>> eventDate = ""; :>> dateBasis = "日付なし"; :>> kind = "延期"; :>> inFlightExtension = false; :>> plannedSite = ""; :>> actualSite = "Edwards"; :>> causeCategory = "天候"; }
    part <'LND-012'> lnd_012 : LandingEvent { doc /* STS-37 fog */ :>> flight = "STS-37"; :>> eventDate = "1991-04-11"; :>> dateBasis = "本文の通日・日付から担当が換算"; :>> kind = "見送り"; :>> inFlightExtension = false; :>> plannedSite = "Edwards"; :>> actualSite = "Edwards"; :>> causeCategory = "天候"; }
    part <'LND-013'> lnd_013 : LandingEvent { doc /* STS-37  */ :>> flight = "STS-37"; :>> eventDate = ""; :>> dateBasis = "日付なし"; :>> kind = "見送り"; :>> inFlightExtension = false; :>> plannedSite = "Edwards"; :>> actualSite = "Edwards"; :>> causeCategory = "原因の記載なし"; }
    part <'LND-014'> lnd_014 : LandingEvent { doc /* STS-37 high winds at the primary landing site */ :>> flight = "STS-37"; :>> eventDate = ""; :>> dateBasis = "日付なし"; :>> kind = "延期"; :>> inFlightExtension = false; :>> plannedSite = "Edwards"; :>> actualSite = "Edwards"; :>> causeCategory = "天候"; }
    part <'LND-015'> lnd_015 : LandingEvent { doc /* STS-38 headwinds exceeded the flight rule limit of 25 kts on runway */ :>> flight = "STS-38"; :>> eventDate = ""; :>> dateBasis = "日付なし"; :>> kind = "見送り"; :>> inFlightExtension = false; :>> plannedSite = "Edwards"; :>> actualSite = ""; :>> causeCategory = "天候"; }
    part <'LND-016'> lnd_016 : LandingEvent { doc /* STS-38 Excessive crosswinds as well as winds varying from the forec */ :>> flight = "STS-38"; :>> eventDate = ""; :>> dateBasis = "日付なし"; :>> kind = "見送り"; :>> inFlightExtension = false; :>> plannedSite = "Edwards"; :>> actualSite = ""; :>> causeCategory = "天候"; }
    part <'LND-017'> lnd_017 : LandingEvent { doc /* STS-38 Excessive crosswinds as well as winds varying from the forec */ :>> flight = "STS-38"; :>> eventDate = ""; :>> dateBasis = "日付なし"; :>> kind = "延期"; :>> inFlightExtension = false; :>> plannedSite = "Edwards"; :>> actualSite = ""; :>> causeCategory = "天候"; }
    part <'LND-018'> lnd_018 : LandingEvent { doc /* STS-38 forecast unfavorable winds on all runways at Edwards; very f */ :>> flight = "STS-38"; :>> eventDate = ""; :>> dateBasis = "日付なし"; :>> kind = "着陸地の変更"; :>> inFlightExtension = false; :>> plannedSite = "Edwards"; :>> actualSite = "KSC"; :>> causeCategory = "天候"; }
    part <'LND-019'> lnd_019 : LandingEvent { doc /* STS-39 weather conditions (high winds) at Edwards Air Force Base */ :>> flight = "STS-39"; :>> eventDate = "1991-05-06"; :>> dateBasis = "本文"; :>> kind = "着陸地の変更"; :>> inFlightExtension = false; :>> plannedSite = "Edwards"; :>> actualSite = "KSC"; :>> causeCategory = "天候"; }
    part <'LND-020'> lnd_020 : LandingEvent { doc /* STS-41C unsatisfactory weather that was headed toward the Shuttle La */ :>> flight = "STS-41C"; :>> eventDate = "1984-04-13"; :>> dateBasis = "本文の通日・日付から担当が換算"; :>> kind = "見送り"; :>> inFlightExtension = false; :>> plannedSite = "KSC"; :>> actualSite = ""; :>> causeCategory = "天候"; }
    part <'LND-021'> lnd_021 : LandingEvent { doc /* STS-41C weather evaluations; weather at Edwards ideal */ :>> flight = "STS-41C"; :>> eventDate = "1984-04-13"; :>> dateBasis = "本文"; :>> kind = "着陸地の変更"; :>> inFlightExtension = false; :>> plannedSite = "KSC"; :>> actualSite = "Edwards"; :>> causeCategory = "天候"; }
    part <'LND-022'> lnd_022 : LandingEvent { doc /* STS-41C SMM retrieval problems during flight day 3 operations */ :>> flight = "STS-41C"; :>> eventDate = ""; :>> dateBasis = "日付なし"; :>> kind = "延期"; :>> inFlightExtension = true; :>> plannedSite = ""; :>> actualSite = ""; :>> causeCategory = "ミッション都合"; }
    part <'LND-023'> lnd_023 : LandingEvent { doc /* STS-45 so that additional scientific data could be obtained */ :>> flight = "STS-45"; :>> eventDate = ""; :>> dateBasis = "日付なし"; :>> kind = "延期"; :>> inFlightExtension = true; :>> plannedSite = ""; :>> actualSite = ""; :>> causeCategory = "ミッション都合"; }
    part <'LND-024'> lnd_024 : LandingEvent { doc /* STS-46 potentially unsatisfactory weather at KSC */ :>> flight = "STS-46"; :>> eventDate = "1992-08-08"; :>> dateBasis = "本文"; :>> kind = "見送り"; :>> inFlightExtension = false; :>> plannedSite = "KSC"; :>> actualSite = "KSC"; :>> causeCategory = "天候"; }
    part <'LND-025'> lnd_025 : LandingEvent { doc /* STS-46 Because of the 24-hour delay in the EURECA deployment, the M */ :>> flight = "STS-46"; :>> eventDate = ""; :>> dateBasis = "日付なし"; :>> kind = "延期"; :>> inFlightExtension = true; :>> plannedSite = ""; :>> actualSite = ""; :>> causeCategory = "ミッション都合"; }
    part <'LND-026'> lnd_026 : LandingEvent { doc /* STS-47 potentially unsatisfactory weather at KSC */ :>> flight = "STS-47"; :>> eventDate = "1992-09-20"; :>> dateBasis = "本文の通日・日付から担当が換算"; :>> kind = "見送り"; :>> inFlightExtension = false; :>> plannedSite = "KSC"; :>> actualSite = ""; :>> causeCategory = "天候"; }
    part <'LND-027'> lnd_027 : LandingEvent { doc /* STS-48 evaluation of weather conditions at the Shuttle Landing Faci */ :>> flight = "STS-48"; :>> eventDate = "1991-09-18"; :>> dateBasis = "本文の通日・日付から担当が換算"; :>> kind = "見送り"; :>> inFlightExtension = false; :>> plannedSite = "KSC"; :>> actualSite = ""; :>> causeCategory = "天候"; }
    part <'LND-028'> lnd_028 : LandingEvent { doc /* STS-48 weather continued to be unfavorable at the primary landing s */ :>> flight = "STS-48"; :>> eventDate = "1991-09-18"; :>> dateBasis = "本文の通日・日付から担当が換算"; :>> kind = "着陸地の変更"; :>> inFlightExtension = false; :>> plannedSite = "KSC"; :>> actualSite = "Edwards"; :>> causeCategory = "天候"; }
    part <'LND-029'> lnd_029 : LandingEvent { doc /* STS-49 additional EVA’s required to capture the INTELSAT satellite */ :>> flight = "STS-49"; :>> eventDate = "1992-05-14"; :>> dateBasis = "延長前の計画の着陸日"; :>> kind = "延期"; :>> inFlightExtension = true; :>> plannedSite = ""; :>> actualSite = ""; :>> causeCategory = "ミッション都合"; }
    part <'LND-030'> lnd_030 : LandingEvent { doc /* STS-50 unsatisfactory weather conditions at Edwards Air Force Base */ :>> flight = "STS-50"; :>> eventDate = "1992-07-08"; :>> dateBasis = "本文の通日・日付から担当が換算"; :>> kind = "見送り"; :>> inFlightExtension = false; :>> plannedSite = "Edwards"; :>> actualSite = ""; :>> causeCategory = "天候"; }
    part <'LND-031'> lnd_031 : LandingEvent { doc /* STS-50 unsatisfactory weather conditions at Edwards Air Force Base */ :>> flight = "STS-50"; :>> eventDate = "1992-07-08"; :>> dateBasis = "本文"; :>> kind = "延期"; :>> inFlightExtension = false; :>> plannedSite = "Edwards"; :>> actualSite = ""; :>> causeCategory = "天候"; }
    part <'LND-032'> lnd_032 : LandingEvent { doc /* STS-50 weather remained unsatisfactory at Edwards Air Force Base */ :>> flight = "STS-50"; :>> eventDate = "1992-07-09"; :>> dateBasis = "本文の通日・日付から担当が換算"; :>> kind = "着陸地の変更"; :>> inFlightExtension = false; :>> plannedSite = "Edwards"; :>> actualSite = "KSC"; :>> causeCategory = "天候"; }
    part <'LND-033'> lnd_033 : LandingEvent { doc /* STS-51 unacceptable forecast and observed weather at the Shuttle La */ :>> flight = "STS-51"; :>> eventDate = "1993-09-21"; :>> dateBasis = "本文の通日・日付から担当が換算"; :>> kind = "見送り"; :>> inFlightExtension = false; :>> plannedSite = "KSC"; :>> actualSite = "KSC"; :>> causeCategory = "天候"; }
    part <'LND-034'> lnd_034 : LandingEvent { doc /* STS-51 unacceptable forecast and observed weather at the Shuttle La */ :>> flight = "STS-51"; :>> eventDate = "1993-09-21"; :>> dateBasis = "本文の通日・日付から担当が換算"; :>> kind = "延期"; :>> inFlightExtension = false; :>> plannedSite = "KSC"; :>> actualSite = "KSC"; :>> causeCategory = "天候"; }
    part <'LND-035'> lnd_035 : LandingEvent { doc /* STS-51D unsatisfactory weather rainshower in the landing area */ :>> flight = "STS-51D"; :>> eventDate = "1985-04-19"; :>> dateBasis = "本文の通日・日付から担当が換算"; :>> kind = "見送り"; :>> inFlightExtension = false; :>> plannedSite = ""; :>> actualSite = ""; :>> causeCategory = "天候"; }
    part <'LND-036'> lnd_036 : LandingEvent { doc /* STS-51D switch lever on SYNCOM IV satellite may not have been activa */ :>> flight = "STS-51D"; :>> eventDate = ""; :>> dateBasis = "日付なし"; :>> kind = "延期"; :>> inFlightExtension = true; :>> plannedSite = ""; :>> actualSite = ""; :>> causeCategory = "ミッション都合"; }
    part <'LND-037'> lnd_037 : LandingEvent { doc /* STS-53 Weather conditions at the Shuttle Landing Facility (SLF) wer */ :>> flight = "STS-53"; :>> eventDate = "1992-12-09"; :>> dateBasis = "本文"; :>> kind = "着陸地の変更"; :>> inFlightExtension = false; :>> plannedSite = "KSC"; :>> actualSite = "Edwards"; :>> causeCategory = "天候"; }
    part <'LND-038'> lnd_038 : LandingEvent { doc /* STS-55 unacceptable weather at the Shuttle Launch Facility at KSC */ :>> flight = "STS-55"; :>> eventDate = "1993-05-06"; :>> dateBasis = "本文の通日・日付から担当が換算"; :>> kind = "着陸地の変更"; :>> inFlightExtension = false; :>> plannedSite = "KSC"; :>> actualSite = "Edwards"; :>> causeCategory = "天候"; }
    part <'LND-039'> lnd_039 : LandingEvent { doc /* STS-56 unacceptable weather conditions at KSC */ :>> flight = "STS-56"; :>> eventDate = "1993-04-16"; :>> dateBasis = "本文"; :>> kind = "延期"; :>> inFlightExtension = false; :>> plannedSite = "KSC"; :>> actualSite = ""; :>> causeCategory = "天候"; }
    part <'LND-040'> lnd_040 : LandingEvent { doc /* STS-57 unsatisfactory weather at the Shuttle Landing Facility */ :>> flight = "STS-57"; :>> eventDate = "1993-06-29"; :>> dateBasis = "本文の通日・日付から担当が換算"; :>> kind = "見送り"; :>> inFlightExtension = false; :>> plannedSite = "KSC"; :>> actualSite = ""; :>> causeCategory = "天候"; }
    part <'LND-041'> lnd_041 : LandingEvent { doc /* STS-57 unsatisfactory weather; weather did not improve */ :>> flight = "STS-57"; :>> eventDate = "1993-06-29"; :>> dateBasis = "本文"; :>> kind = "延期"; :>> inFlightExtension = false; :>> plannedSite = "KSC"; :>> actualSite = "KSC"; :>> causeCategory = "天候"; }
    part <'LND-042'> lnd_042 : LandingEvent { doc /* STS-57 weather was again unacceptable for landing */ :>> flight = "STS-57"; :>> eventDate = "1993-06-30"; :>> dateBasis = "本文"; :>> kind = "延期"; :>> inFlightExtension = false; :>> plannedSite = "KSC"; :>> actualSite = "KSC"; :>> causeCategory = "天候"; }
    part <'LND-043'> lnd_043 : LandingEvent { doc /* STS-59 cloud conditions in the SLF area */ :>> flight = "STS-59"; :>> eventDate = "1994-04-19"; :>> dateBasis = "本文"; :>> kind = "見送り"; :>> inFlightExtension = false; :>> plannedSite = "KSC"; :>> actualSite = ""; :>> causeCategory = "天候"; }
    part <'LND-044'> lnd_044 : LandingEvent { doc /* STS-59 unfavorable and dynamic weather conditions in the landing ar */ :>> flight = "STS-59"; :>> eventDate = "1994-04-19"; :>> dateBasis = "本文"; :>> kind = "延期"; :>> inFlightExtension = false; :>> plannedSite = "KSC"; :>> actualSite = ""; :>> causeCategory = "天候"; }
    part <'LND-045'> lnd_045 : LandingEvent { doc /* STS-59 no-go weather conditions at KSC */ :>> flight = "STS-59"; :>> eventDate = "1994-04-20"; :>> dateBasis = "本文"; :>> kind = "着陸地の変更"; :>> inFlightExtension = false; :>> plannedSite = "KSC"; :>> actualSite = "Edwards"; :>> causeCategory = "天候"; }
    part <'LND-046'> lnd_046 : LandingEvent { doc /* STS-60 the weather conditions at the KSC Shuttle Landing Facility ( */ :>> flight = "STS-60"; :>> eventDate = "1994-02-11"; :>> dateBasis = "本文"; :>> kind = "見送り"; :>> inFlightExtension = false; :>> plannedSite = "KSC"; :>> actualSite = "KSC"; :>> causeCategory = "天候"; }
    part <'LND-047'> lnd_047 : LandingEvent { doc /* STS-61C unacceptable weather resulted in scheduling the landing for  */ :>> flight = "STS-61C"; :>> eventDate = "1986-01-16"; :>> dateBasis = "本文"; :>> kind = "延期"; :>> inFlightExtension = false; :>> plannedSite = "KSC"; :>> actualSite = ""; :>> causeCategory = "天候"; }
    part <'LND-048'> lnd_048 : LandingEvent { doc /* STS-61C Again unacceptable weather played a role in delaying the lan */ :>> flight = "STS-61C"; :>> eventDate = "1986-01-17"; :>> dateBasis = "本文"; :>> kind = "延期"; :>> inFlightExtension = false; :>> plannedSite = "KSC"; :>> actualSite = ""; :>> causeCategory = "天候"; }
    part <'LND-049'> lnd_049 : LandingEvent { doc /* STS-61C the weather was again determined to be unacceptable */ :>> flight = "STS-61C"; :>> eventDate = "1986-01-18"; :>> dateBasis = "本文"; :>> kind = "着陸地の変更"; :>> inFlightExtension = false; :>> plannedSite = "KSC"; :>> actualSite = "Edwards"; :>> causeCategory = "天候"; }
    part <'LND-050'> lnd_050 : LandingEvent { doc /* STS-64 thunderstorms within 30 miles and lightning being observed ( */ :>> flight = "STS-64"; :>> eventDate = "1994-09-19"; :>> dateBasis = "本文"; :>> kind = "延期"; :>> inFlightExtension = false; :>> plannedSite = "KSC"; :>> actualSite = ""; :>> causeCategory = "天候"; }
    part <'LND-051'> lnd_051 : LandingEvent { doc /* STS-64 unacceptable weather conditions at the Shuttle Landing Facil */ :>> flight = "STS-64"; :>> eventDate = "1994-09-20"; :>> dateBasis = "本文"; :>> kind = "着陸地の変更"; :>> inFlightExtension = false; :>> plannedSite = "KSC"; :>> actualSite = "Edwards"; :>> causeCategory = "天候"; }
    part <'LND-052'> lnd_052 : LandingEvent { doc /* STS-65 the landing was waived because of rain within 30 miles of th */ :>> flight = "STS-65"; :>> eventDate = "1994-07-22"; :>> dateBasis = "本文の通日・日付から担当が換算"; :>> kind = "延期"; :>> inFlightExtension = false; :>> plannedSite = "KSC"; :>> actualSite = "KSC"; :>> causeCategory = "天候"; }
    part <'LND-053'> lnd_053 : LandingEvent { doc /* STS-66 The weather at KSC was becoming worse because of a tropical  */ :>> flight = "STS-66"; :>> eventDate = "1994-11-14"; :>> dateBasis = "本文"; :>> kind = "見送り"; :>> inFlightExtension = false; :>> plannedSite = "KSC"; :>> actualSite = ""; :>> causeCategory = "天候"; }
    part <'LND-054'> lnd_054 : LandingEvent { doc /* STS-66 The weather at KSC was becoming worse because of a tropical  */ :>> flight = "STS-66"; :>> eventDate = "1994-11-14"; :>> dateBasis = "本文"; :>> kind = "着陸地の変更"; :>> inFlightExtension = false; :>> plannedSite = "KSC"; :>> actualSite = "Edwards"; :>> causeCategory = "天候"; }
    part <'LND-055'> lnd_055 : LandingEvent { doc /* STS-67 unfavorable weather at the Shuttle Landing Facility (SLF) */ :>> flight = "STS-67"; :>> eventDate = "1995-03-17"; :>> dateBasis = "本文"; :>> kind = "延期"; :>> inFlightExtension = false; :>> plannedSite = "KSC"; :>> actualSite = ""; :>> causeCategory = "天候"; }
    part <'LND-056'> lnd_056 : LandingEvent { doc /* STS-67 unacceptable weather again forced cancellation of the landin */ :>> flight = "STS-67"; :>> eventDate = "1995-03-18"; :>> dateBasis = "本文"; :>> kind = "着陸地の変更"; :>> inFlightExtension = false; :>> plannedSite = "KSC"; :>> actualSite = "Edwards"; :>> causeCategory = "天候"; }
    part <'LND-057'> lnd_057 : LandingEvent { doc /* STS-68 dynamic weather at KSC that was trending toward unacceptable */ :>> flight = "STS-68"; :>> eventDate = "1994-10-11"; :>> dateBasis = "本文"; :>> kind = "見送り"; :>> inFlightExtension = false; :>> plannedSite = "KSC"; :>> actualSite = ""; :>> causeCategory = "天候"; }
    part <'LND-058'> lnd_058 : LandingEvent { doc /* STS-68 dynamic weather at KSC trending toward unacceptable landing  */ :>> flight = "STS-68"; :>> eventDate = "1994-10-11"; :>> dateBasis = "本文"; :>> kind = "着陸地の変更"; :>> inFlightExtension = false; :>> plannedSite = "KSC"; :>> actualSite = "Edwards"; :>> causeCategory = "天候"; }
    part <'LND-059'> lnd_059 : LandingEvent { doc /* STS-70 ground fog */ :>> flight = "STS-70"; :>> eventDate = "1995-07-21"; :>> dateBasis = "本文の通日・日付から担当が換算"; :>> kind = "見送り"; :>> inFlightExtension = false; :>> plannedSite = "KSC"; :>> actualSite = ""; :>> causeCategory = "天候"; }
    part <'LND-060'> lnd_060 : LandingEvent { doc /* STS-70 ground fog */ :>> flight = "STS-70"; :>> eventDate = "1995-07-21"; :>> dateBasis = "本文"; :>> kind = "延期"; :>> inFlightExtension = false; :>> plannedSite = "KSC"; :>> actualSite = "KSC"; :>> causeCategory = "天候"; }
    part <'LND-061'> lnd_061 : LandingEvent { doc /* STS-70 marginal weather conditions */ :>> flight = "STS-70"; :>> eventDate = "1995-07-22"; :>> dateBasis = "本文の通日・日付から担当が換算"; :>> kind = "見送り"; :>> inFlightExtension = false; :>> plannedSite = "KSC"; :>> actualSite = "KSC"; :>> causeCategory = "天候"; }
    part <'LND-062'> lnd_062 : LandingEvent { doc /* STS-75 forecasted cloud coverage at Kennedy Space Center (KSC) */ :>> flight = "STS-75"; :>> eventDate = "1996-03-08"; :>> dateBasis = "本文"; :>> kind = "延期"; :>> inFlightExtension = false; :>> plannedSite = "KSC"; :>> actualSite = ""; :>> causeCategory = "天候"; }
    part <'LND-063'> lnd_063 : LandingEvent { doc /* STS-75 cloud coverage */ :>> flight = "STS-75"; :>> eventDate = "1996-03-09"; :>> dateBasis = "本文"; :>> kind = "見送り"; :>> inFlightExtension = false; :>> plannedSite = "KSC"; :>> actualSite = ""; :>> causeCategory = "天候"; }
    part <'LND-064'> lnd_064 : LandingEvent { doc /* STS-76 unacceptable weather conditions at the KSC Shuttle Landing F */ :>> flight = "STS-76"; :>> eventDate = "1996-03-30"; :>> dateBasis = "本文"; :>> kind = "見送り"; :>> inFlightExtension = false; :>> plannedSite = "KSC"; :>> actualSite = ""; :>> causeCategory = "天候"; }
    part <'LND-065'> lnd_065 : LandingEvent { doc /* STS-76 unacceptable weather conditions at the KSC Shuttle Landing F */ :>> flight = "STS-76"; :>> eventDate = "1996-03-30"; :>> dateBasis = "本文"; :>> kind = "延期"; :>> inFlightExtension = false; :>> plannedSite = "KSC"; :>> actualSite = ""; :>> causeCategory = "天候"; }
    part <'LND-066'> lnd_066 : LandingEvent { doc /* STS-76 unacceptable weather conditions at the SLF */ :>> flight = "STS-76"; :>> eventDate = "1996-03-31"; :>> dateBasis = "本文の通日・日付から担当が換算"; :>> kind = "見送り"; :>> inFlightExtension = false; :>> plannedSite = "KSC"; :>> actualSite = ""; :>> causeCategory = "天候"; }
    part <'LND-067'> lnd_067 : LandingEvent { doc /* STS-76 unacceptable weather conditions at the SLF */ :>> flight = "STS-76"; :>> eventDate = "1996-03-31"; :>> dateBasis = "本文"; :>> kind = "着陸地の変更"; :>> inFlightExtension = false; :>> plannedSite = "KSC"; :>> actualSite = "Edwards"; :>> causeCategory = "天候"; }
    part <'LND-068'> lnd_068 : LandingEvent { doc /* STS-80 unacceptable weather conditions at the KSC Shuttle Landing F */ :>> flight = "STS-80"; :>> eventDate = "1996-12-05"; :>> dateBasis = "本文"; :>> kind = "延期"; :>> inFlightExtension = false; :>> plannedSite = "KSC"; :>> actualSite = ""; :>> causeCategory = "天候"; }
    part <'LND-069'> lnd_069 : LandingEvent { doc /* STS-80 unacceptable weather conditions (fog) at the KSC SLF and pre */ :>> flight = "STS-80"; :>> eventDate = "1996-12-06"; :>> dateBasis = "本文"; :>> kind = "延期"; :>> inFlightExtension = false; :>> plannedSite = "KSC"; :>> actualSite = ""; :>> causeCategory = "天候"; }
    part <'LND-070'> lnd_070 : LandingEvent { doc /* STS-81 forecast and observed unacceptable cloud cover */ :>> flight = "STS-81"; :>> eventDate = "1997-01-22"; :>> dateBasis = "本文"; :>> kind = "見送り"; :>> inFlightExtension = false; :>> plannedSite = "KSC"; :>> actualSite = "KSC"; :>> causeCategory = "天候"; }
    part <'LND-071'> lnd_071 : LandingEvent { doc /* STS-82 Unacceptable weather conditions at the Kennedy Space Center  */ :>> flight = "STS-82"; :>> eventDate = "1997-02-21"; :>> dateBasis = "本文"; :>> kind = "見送り"; :>> inFlightExtension = false; :>> plannedSite = "KSC"; :>> actualSite = "KSC"; :>> causeCategory = "天候"; }
    part <'LND-072'> lnd_072 : LandingEvent { doc /* STS-84 Unacceptable weather conditions existed at the Kennedy Space */ :>> flight = "STS-84"; :>> eventDate = "1997-05-24"; :>> dateBasis = "本文"; :>> kind = "見送り"; :>> inFlightExtension = false; :>> plannedSite = "KSC"; :>> actualSite = "KSC"; :>> causeCategory = "天候"; }
    part <'LND-073'> lnd_073 : LandingEvent { doc /* STS-85 anticipated unsatisfactory weather conditions at the landing */ :>> flight = "STS-85"; :>> eventDate = "1997-08-18"; :>> dateBasis = "本文の通日・日付から担当が換算"; :>> kind = "延期"; :>> inFlightExtension = false; :>> plannedSite = "KSC"; :>> actualSite = "KSC"; :>> causeCategory = "天候"; }
    part <'LND-074'> lnd_074 : LandingEvent { doc /* STS-86 unsatisfactory weather conditions */ :>> flight = "STS-86"; :>> eventDate = "1997-10-05"; :>> dateBasis = "本文の通日・日付から担当が換算"; :>> kind = "見送り"; :>> inFlightExtension = false; :>> plannedSite = "KSC"; :>> actualSite = "KSC"; :>> causeCategory = "天候"; }
    part <'LND-075'> lnd_075 : LandingEvent { doc /* STS-86 unsatisfactory weather conditions */ :>> flight = "STS-86"; :>> eventDate = "1997-10-05"; :>> dateBasis = "本文の通日・日付から担当が換算"; :>> kind = "延期"; :>> inFlightExtension = false; :>> plannedSite = "KSC"; :>> actualSite = "KSC"; :>> causeCategory = "天候"; }
    part <'LND-076'> lnd_076 : LandingEvent { doc /* STS-92 crosswinds being higher than the established limits */ :>> flight = "STS-92"; :>> eventDate = "2000-10-22"; :>> dateBasis = "本文の通日・日付から担当が換算"; :>> kind = "延期"; :>> inFlightExtension = false; :>> plannedSite = ""; :>> actualSite = ""; :>> causeCategory = "天候"; }
    part <'LND-077'> lnd_077 : LandingEvent { doc /* STS-92 Winds in excess of the limits for a KSC landing; showers wit */ :>> flight = "STS-92"; :>> eventDate = "2000-10-23"; :>> dateBasis = "本文の通日・日付から担当が換算"; :>> kind = "延期"; :>> inFlightExtension = false; :>> plannedSite = "KSC"; :>> actualSite = ""; :>> causeCategory = "天候"; }
    part <'LND-078'> lnd_078 : LandingEvent { doc /* STS-92 Winds in excess of the limits for a KSC landing on the third */ :>> flight = "STS-92"; :>> eventDate = "2000-10-24"; :>> dateBasis = "本文"; :>> kind = "着陸地の変更"; :>> inFlightExtension = false; :>> plannedSite = "KSC"; :>> actualSite = "Edwards"; :>> causeCategory = "天候"; }
    part <'LND-079'> lnd_079 : LandingEvent { doc /* STS-98 excessive crosswinds */ :>> flight = "STS-98"; :>> eventDate = "2001-02-18"; :>> dateBasis = "本文の通日・日付から担当が換算"; :>> kind = "延期"; :>> inFlightExtension = false; :>> plannedSite = "KSC"; :>> actualSite = ""; :>> causeCategory = "天候"; }
    part <'LND-080'> lnd_080 : LandingEvent { doc /* STS-98 excessive crosswinds */ :>> flight = "STS-98"; :>> eventDate = "2001-02-19"; :>> dateBasis = "本文の通日・日付から担当が換算"; :>> kind = "延期"; :>> inFlightExtension = false; :>> plannedSite = "KSC"; :>> actualSite = ""; :>> causeCategory = "天候"; }
    part <'LND-081'> lnd_081 : LandingEvent { doc /* STS-98  */ :>> flight = "STS-98"; :>> eventDate = "2001-02-20"; :>> dateBasis = "本文"; :>> kind = "着陸地の変更"; :>> inFlightExtension = false; :>> plannedSite = "KSC"; :>> actualSite = "Edwards"; :>> causeCategory = "原因の記載なし"; }
    part <'LND-082'> lnd_082 : LandingEvent { doc /* STS-99 unacceptable weather conditions */ :>> flight = "STS-99"; :>> eventDate = "2000-02-22"; :>> dateBasis = "本文の通日・日付から担当が換算"; :>> kind = "見送り"; :>> inFlightExtension = false; :>> plannedSite = "KSC"; :>> actualSite = "KSC"; :>> causeCategory = "天候"; }
    part <'LND-083'> lnd_083 : LandingEvent { doc /* STS-100 unacceptable weather conditions */ :>> flight = "STS-100"; :>> eventDate = "2001-05-01"; :>> dateBasis = "本文"; :>> kind = "見送り"; :>> inFlightExtension = false; :>> plannedSite = "KSC"; :>> actualSite = "Edwards"; :>> causeCategory = "天候"; }
    part <'LND-084'> lnd_084 : LandingEvent { doc /* STS-100 unacceptable weather conditions (second KSC opportunity also */ :>> flight = "STS-100"; :>> eventDate = "2001-05-01"; :>> dateBasis = "本文"; :>> kind = "着陸地の変更"; :>> inFlightExtension = false; :>> plannedSite = "KSC"; :>> actualSite = "Edwards"; :>> causeCategory = "天候"; }
    part <'LND-085'> lnd_085 : LandingEvent { doc /* STS-102 rain showers within 30 nmi. and crosswinds that were out of  */ :>> flight = "STS-102"; :>> eventDate = "2001-03-21"; :>> dateBasis = "本文の通日・日付から担当が換算"; :>> kind = "見送り"; :>> inFlightExtension = false; :>> plannedSite = "KSC"; :>> actualSite = "KSC"; :>> causeCategory = "天候"; }
    part <'LND-086'> lnd_086 : LandingEvent { doc /* STS-102 New challenges were encountered regarding determination of t */ :>> flight = "STS-102"; :>> eventDate = ""; :>> dateBasis = "日付なし"; :>> kind = "延期"; :>> inFlightExtension = true; :>> plannedSite = ""; :>> actualSite = ""; :>> causeCategory = "ミッション都合"; }
    part <'LND-087'> lnd_087 : LandingEvent { doc /* STS-103 excessive crosswinds and observed turbulence in the pitch ax */ :>> flight = "STS-103"; :>> eventDate = "1999-12-27"; :>> dateBasis = "本文"; :>> kind = "見送り"; :>> inFlightExtension = false; :>> plannedSite = "KSC"; :>> actualSite = ""; :>> causeCategory = "天候"; }
    part <'LND-088'> lnd_088 : LandingEvent { doc /* STS-104 unacceptable weather conditions */ :>> flight = "STS-104"; :>> eventDate = "2001-07-24"; :>> dateBasis = "本文の通日・日付から担当が換算"; :>> kind = "見送り"; :>> inFlightExtension = false; :>> plannedSite = "KSC"; :>> actualSite = "KSC"; :>> causeCategory = "天候"; }
    part <'LND-089'> lnd_089 : LandingEvent { doc /* STS-104 unacceptable weather conditions */ :>> flight = "STS-104"; :>> eventDate = "2001-07-24"; :>> dateBasis = "本文の通日・日付から担当が換算"; :>> kind = "延期"; :>> inFlightExtension = false; :>> plannedSite = "KSC"; :>> actualSite = "KSC"; :>> causeCategory = "天候"; }
    part <'LND-090'> lnd_090 : LandingEvent { doc /* STS-105 rain shower near the end of runway */ :>> flight = "STS-105"; :>> eventDate = "2001-08-22"; :>> dateBasis = "本文"; :>> kind = "見送り"; :>> inFlightExtension = false; :>> plannedSite = "KSC"; :>> actualSite = "KSC"; :>> causeCategory = "天候"; }
    part <'LND-091'> lnd_091 : LandingEvent { doc /* STS-108 The mission was extended one day by the Mission Management T */ :>> flight = "STS-108"; :>> eventDate = ""; :>> dateBasis = "日付なし"; :>> kind = "延期"; :>> inFlightExtension = true; :>> plannedSite = ""; :>> actualSite = ""; :>> causeCategory = "ミッション都合"; }
    part <'LND-092'> lnd_092 : LandingEvent { doc /* STS-111 the forecasted and observed weather conditions were unaccept */ :>> flight = "STS-111"; :>> eventDate = "2002-06-17"; :>> dateBasis = "本文の通日・日付から担当が換算"; :>> kind = "見送り"; :>> inFlightExtension = false; :>> plannedSite = "KSC"; :>> actualSite = ""; :>> causeCategory = "天候"; }
    part <'LND-093'> lnd_093 : LandingEvent { doc /* STS-111 the forecasted and observed weather conditions were unaccept */ :>> flight = "STS-111"; :>> eventDate = "2002-06-17"; :>> dateBasis = "本文の通日・日付から担当が換算"; :>> kind = "延期"; :>> inFlightExtension = false; :>> plannedSite = "KSC"; :>> actualSite = ""; :>> causeCategory = "天候"; }
    part <'LND-094'> lnd_094 : LandingEvent { doc /* STS-111 the forecasted and observed weather conditions were unaccept */ :>> flight = "STS-111"; :>> eventDate = "2002-06-18"; :>> dateBasis = "本文の通日・日付から担当が換算"; :>> kind = "見送り"; :>> inFlightExtension = false; :>> plannedSite = "KSC"; :>> actualSite = ""; :>> causeCategory = "天候"; }
    part <'LND-095'> lnd_095 : LandingEvent { doc /* STS-111 the forecasted and observed weather conditions were unaccept */ :>> flight = "STS-111"; :>> eventDate = "2002-06-18"; :>> dateBasis = "本文の通日・日付から担当が換算"; :>> kind = "延期"; :>> inFlightExtension = false; :>> plannedSite = "KSC"; :>> actualSite = ""; :>> causeCategory = "天候"; }
    part <'LND-096'> lnd_096 : LandingEvent { doc /* STS-111 the forecasted and observed weather conditions were not acce */ :>> flight = "STS-111"; :>> eventDate = "2002-06-19"; :>> dateBasis = "本文"; :>> kind = "見送り"; :>> inFlightExtension = false; :>> plannedSite = "KSC"; :>> actualSite = ""; :>> causeCategory = "天候"; }
    part <'LND-097'> lnd_097 : LandingEvent { doc /* STS-111 the forecasted and observed weather conditions were not acce */ :>> flight = "STS-111"; :>> eventDate = "2002-06-19"; :>> dateBasis = "本文"; :>> kind = "着陸地の変更"; :>> inFlightExtension = false; :>> plannedSite = "KSC"; :>> actualSite = "Edwards"; :>> causeCategory = "天候"; }
    part <'LND-098'> lnd_098 : LandingEvent { doc /* STS-113 unacceptable landing conditions (cloud coverage) */ :>> flight = "STS-113"; :>> eventDate = "2002-12-04"; :>> dateBasis = "本文の通日・日付から担当が換算"; :>> kind = "見送り"; :>> inFlightExtension = false; :>> plannedSite = "KSC"; :>> actualSite = ""; :>> causeCategory = "天候"; }
    part <'LND-099'> lnd_099 : LandingEvent { doc /* STS-113 unacceptable landing conditions (cloud coverage) */ :>> flight = "STS-113"; :>> eventDate = "2002-12-04"; :>> dateBasis = "本文"; :>> kind = "延期"; :>> inFlightExtension = false; :>> plannedSite = "KSC"; :>> actualSite = ""; :>> causeCategory = "天候"; }
    part <'LND-100'> lnd_100 : LandingEvent { doc /* STS-113 forecasted unsatisfactory weather conditions */ :>> flight = "STS-113"; :>> eventDate = "2002-12-05"; :>> dateBasis = "本文の通日・日付から担当が換算"; :>> kind = "延期"; :>> inFlightExtension = false; :>> plannedSite = "KSC"; :>> actualSite = ""; :>> causeCategory = "天候"; }
    part <'LND-101'> lnd_101 : LandingEvent { doc /* STS-113  */ :>> flight = "STS-113"; :>> eventDate = "2002-12-06"; :>> dateBasis = "本文の通日・日付から担当が換算"; :>> kind = "見送り"; :>> inFlightExtension = false; :>> plannedSite = "KSC"; :>> actualSite = ""; :>> causeCategory = "原因の記載なし"; }
    part <'LND-102'> lnd_102 : LandingEvent { doc /* STS-113  */ :>> flight = "STS-113"; :>> eventDate = "2002-12-06"; :>> dateBasis = "本文"; :>> kind = "延期"; :>> inFlightExtension = false; :>> plannedSite = "KSC"; :>> actualSite = ""; :>> causeCategory = "原因の記載なし"; }
    part <'LND-103'> lnd_103 : LandingEvent { doc /* STS-114 forecasted no-go weather conditions */ :>> flight = "STS-114"; :>> eventDate = "2005-08-08"; :>> dateBasis = "本文の通日・日付から担当が換算"; :>> kind = "見送り"; :>> inFlightExtension = false; :>> plannedSite = "KSC"; :>> actualSite = "Edwards"; :>> causeCategory = "天候"; }
    part <'LND-104'> lnd_104 : LandingEvent { doc /* STS-114 improved but unstable weather conditions */ :>> flight = "STS-114"; :>> eventDate = "2005-08-08"; :>> dateBasis = "本文の通日・日付から担当が換算"; :>> kind = "延期"; :>> inFlightExtension = false; :>> plannedSite = "KSC"; :>> actualSite = "Edwards"; :>> causeCategory = "天候"; }
    part <'LND-105'> lnd_105 : LandingEvent { doc /* STS-114 inclement weather */ :>> flight = "STS-114"; :>> eventDate = "2005-08-09"; :>> dateBasis = "本文"; :>> kind = "見送り"; :>> inFlightExtension = false; :>> plannedSite = "KSC"; :>> actualSite = "Edwards"; :>> causeCategory = "天候"; }
    part <'LND-106'> lnd_106 : LandingEvent { doc /* STS-114 inclement weather */ :>> flight = "STS-114"; :>> eventDate = "2005-08-09"; :>> dateBasis = "本文"; :>> kind = "着陸地の変更"; :>> inFlightExtension = false; :>> plannedSite = "KSC"; :>> actualSite = "Edwards"; :>> causeCategory = "天候"; }
    part <'LND-107'> lnd_107 : LandingEvent { doc /* STS-115 forecasted weather violations at KSC for the planned entry d */ :>> flight = "STS-115"; :>> eventDate = ""; :>> dateBasis = "日付なし"; :>> kind = "延期"; :>> inFlightExtension = false; :>> plannedSite = "KSC"; :>> actualSite = "KSC"; :>> causeCategory = "天候"; }
    part <'LND-108'> lnd_108 : LandingEvent { doc /* STS-116 unacceptable weather conditions */ :>> flight = "STS-116"; :>> eventDate = "2006-12-22"; :>> dateBasis = "本文"; :>> kind = "見送り"; :>> inFlightExtension = false; :>> plannedSite = "KSC"; :>> actualSite = "KSC"; :>> causeCategory = "天候"; }
    part <'LND-109'> lnd_109 : LandingEvent { doc /* STS-116 unacceptable weather conditions */ :>> flight = "STS-116"; :>> eventDate = "2006-12-22"; :>> dateBasis = "本文"; :>> kind = "見送り"; :>> inFlightExtension = false; :>> plannedSite = "Edwards"; :>> actualSite = "KSC"; :>> causeCategory = "天候"; }
    part <'LND-110'> lnd_110 : LandingEvent { doc /* STS-116 At the request of the ISS Program, a decision was made by th */ :>> flight = "STS-116"; :>> eventDate = ""; :>> dateBasis = "日付なし"; :>> kind = "延期"; :>> inFlightExtension = true; :>> plannedSite = ""; :>> actualSite = ""; :>> causeCategory = "ミッション都合"; }
    part <'LND-111'> lnd_111 : LandingEvent { doc /* STS-117 unacceptable weather conditions */ :>> flight = "STS-117"; :>> eventDate = "2007-06-21"; :>> dateBasis = "本文の通日・日付から担当が換算"; :>> kind = "見送り"; :>> inFlightExtension = false; :>> plannedSite = "KSC"; :>> actualSite = "Edwards"; :>> causeCategory = "天候"; }
    part <'LND-112'> lnd_112 : LandingEvent { doc /* STS-117 unacceptable weather conditions */ :>> flight = "STS-117"; :>> eventDate = "2007-06-21"; :>> dateBasis = "本文の通日・日付から担当が換算"; :>> kind = "延期"; :>> inFlightExtension = false; :>> plannedSite = "KSC"; :>> actualSite = "Edwards"; :>> causeCategory = "天候"; }
    part <'LND-113'> lnd_113 : LandingEvent { doc /* STS-117 unacceptable weather conditions */ :>> flight = "STS-117"; :>> eventDate = "2007-06-22"; :>> dateBasis = "本文"; :>> kind = "見送り"; :>> inFlightExtension = false; :>> plannedSite = "KSC"; :>> actualSite = "Edwards"; :>> causeCategory = "天候"; }
    part <'LND-114'> lnd_114 : LandingEvent { doc /* STS-117 unacceptable weather conditions */ :>> flight = "STS-117"; :>> eventDate = "2007-06-22"; :>> dateBasis = "本文"; :>> kind = "着陸地の変更"; :>> inFlightExtension = false; :>> plannedSite = "KSC"; :>> actualSite = "Edwards"; :>> causeCategory = "天候"; }
    part <'LND-115'> lnd_115 : LandingEvent { doc /* STS-117 MMT decided to consider the TPS suspect for the port OMS pod */ :>> flight = "STS-117"; :>> eventDate = ""; :>> dateBasis = "日付なし"; :>> kind = "延期"; :>> inFlightExtension = true; :>> plannedSite = ""; :>> actualSite = ""; :>> causeCategory = "機体の系"; }
    part <'LND-116'> lnd_116 : LandingEvent { doc /* STS-117 MMT decided to add a fourth EVA to complete all of the plann */ :>> flight = "STS-117"; :>> eventDate = ""; :>> dateBasis = "日付なし"; :>> kind = "延期"; :>> inFlightExtension = true; :>> plannedSite = ""; :>> actualSite = ""; :>> causeCategory = "ミッション都合"; }
    part <'LND-117'> lnd_117 : LandingEvent { doc /* STS-119 unacceptable weather at Kennedy Space Center (KSC) */ :>> flight = "STS-119"; :>> eventDate = "2009-03-28"; :>> dateBasis = "本文の通日・日付から担当が換算"; :>> kind = "見送り"; :>> inFlightExtension = false; :>> plannedSite = "KSC"; :>> actualSite = "KSC"; :>> causeCategory = "天候"; }
    part <'LND-118'> lnd_118 : LandingEvent { doc /* STS-120 This additional docked day was to allow the fourth EVA to be */ :>> flight = "STS-120"; :>> eventDate = ""; :>> dateBasis = "日付なし"; :>> kind = "延期"; :>> inFlightExtension = true; :>> plannedSite = ""; :>> actualSite = ""; :>> causeCategory = "ミッション都合"; }
    part <'LND-119'> lnd_119 : LandingEvent { doc /* STS-121 EVA 3 was originally unscheduled but was inserted into the f */ :>> flight = "STS-121"; :>> eventDate = ""; :>> dateBasis = "日付なし"; :>> kind = "延期"; :>> inFlightExtension = true; :>> plannedSite = ""; :>> actualSite = ""; :>> causeCategory = "ミッション都合"; }
    part <'LND-120'> lnd_120 : LandingEvent { doc /* STS-122 The MMT also approved the mission duration extension to 13+0 */ :>> flight = "STS-122"; :>> eventDate = ""; :>> dateBasis = "日付なし"; :>> kind = "延期"; :>> inFlightExtension = true; :>> plannedSite = ""; :>> actualSite = ""; :>> causeCategory = "ミッション都合"; }
    part <'LND-121'> lnd_121 : LandingEvent { doc /* STS-123 weather considerations */ :>> flight = "STS-123"; :>> eventDate = "2008-03-26"; :>> dateBasis = "本文"; :>> kind = "見送り"; :>> inFlightExtension = false; :>> plannedSite = "KSC"; :>> actualSite = "KSC"; :>> causeCategory = "天候"; }
    part <'LND-122'> lnd_122 : LandingEvent { doc /* STS-125 inclement weather at the planned KSC landing site */ :>> flight = "STS-125"; :>> eventDate = "2009-05-23"; :>> dateBasis = "本文の通日・日付から担当が換算"; :>> kind = "延期"; :>> inFlightExtension = false; :>> plannedSite = "KSC"; :>> actualSite = ""; :>> causeCategory = "天候"; }
    part <'LND-123'> lnd_123 : LandingEvent { doc /* STS-125 inclement weather */ :>> flight = "STS-125"; :>> eventDate = "2009-05-24"; :>> dateBasis = "本文"; :>> kind = "見送り"; :>> inFlightExtension = false; :>> plannedSite = "KSC"; :>> actualSite = ""; :>> causeCategory = "天候"; }
    part <'LND-124'> lnd_124 : LandingEvent { doc /* STS-125 weather was still to uncertain at KSC */ :>> flight = "STS-125"; :>> eventDate = "2009-05-24"; :>> dateBasis = "本文"; :>> kind = "着陸地の変更"; :>> inFlightExtension = false; :>> plannedSite = "KSC"; :>> actualSite = "Edwards"; :>> causeCategory = "天候"; }
    part <'LND-125'> lnd_125 : LandingEvent { doc /* STS-125 inclement weather at the planned KSC landing site */ :>> flight = "STS-125"; :>> eventDate = ""; :>> dateBasis = "日付なし"; :>> kind = "延期"; :>> inFlightExtension = false; :>> plannedSite = "KSC"; :>> actualSite = ""; :>> causeCategory = "天候"; }
    part <'LND-126'> lnd_126 : LandingEvent { doc /* STS-126 inclement weather */ :>> flight = "STS-126"; :>> eventDate = "2008-11-30"; :>> dateBasis = "本文"; :>> kind = "見送り"; :>> inFlightExtension = false; :>> plannedSite = "KSC"; :>> actualSite = "Edwards"; :>> causeCategory = "天候"; }
    part <'LND-127'> lnd_127 : LandingEvent { doc /* STS-126 inclement weather (poor weather at KSC) */ :>> flight = "STS-126"; :>> eventDate = "2008-11-30"; :>> dateBasis = "本文"; :>> kind = "着陸地の変更"; :>> inFlightExtension = false; :>> plannedSite = "KSC"; :>> actualSite = "Edwards"; :>> causeCategory = "天候"; }
    part <'LND-128'> lnd_128 : LandingEvent { doc /* STS-128 inclement weather at KSC */ :>> flight = "STS-128"; :>> eventDate = "2009-09-10"; :>> dateBasis = "本文の通日・日付から担当が換算"; :>> kind = "見送り"; :>> inFlightExtension = false; :>> plannedSite = "KSC"; :>> actualSite = "Edwards"; :>> causeCategory = "天候"; }
    part <'LND-129'> lnd_129 : LandingEvent { doc /* STS-128 inclement weather at KSC */ :>> flight = "STS-128"; :>> eventDate = "2009-09-10"; :>> dateBasis = "本文の通日・日付から担当が換算"; :>> kind = "延期"; :>> inFlightExtension = false; :>> plannedSite = "KSC"; :>> actualSite = "Edwards"; :>> causeCategory = "天候"; }
    part <'LND-130'> lnd_130 : LandingEvent { doc /* STS-128 unacceptable weather conditions at KSC */ :>> flight = "STS-128"; :>> eventDate = "2009-09-11"; :>> dateBasis = "本文の通日・日付から担当が換算"; :>> kind = "見送り"; :>> inFlightExtension = false; :>> plannedSite = "KSC"; :>> actualSite = "Edwards"; :>> causeCategory = "天候"; }
    part <'LND-131'> lnd_131 : LandingEvent { doc /* STS-128 unacceptable weather conditions at KSC */ :>> flight = "STS-128"; :>> eventDate = "2009-09-11"; :>> dateBasis = "本文の通日・日付から担当が換算"; :>> kind = "着陸地の変更"; :>> inFlightExtension = false; :>> plannedSite = "KSC"; :>> actualSite = "Edwards"; :>> causeCategory = "天候"; }
    part <'LND-132'> lnd_132 : LandingEvent { doc /* STS-131 unacceptable weather (low ceiling) at KSC */ :>> flight = "STS-131"; :>> eventDate = "2010-04-19"; :>> dateBasis = "本文の通日・日付から担当が換算"; :>> kind = "延期"; :>> inFlightExtension = false; :>> plannedSite = "KSC"; :>> actualSite = ""; :>> causeCategory = "天候"; }
    part <'LND-133'> lnd_133 : LandingEvent { doc /* STS-131 low clouds and precipitation */ :>> flight = "STS-131"; :>> eventDate = "2010-04-20"; :>> dateBasis = "本文"; :>> kind = "見送り"; :>> inFlightExtension = false; :>> plannedSite = "KSC"; :>> actualSite = ""; :>> causeCategory = "天候"; }
    part <'LND-134'> lnd_134 : LandingEvent { doc /* STS-131 to accommodate a Docked Late Inspection (DLI) of the thermal */ :>> flight = "STS-131"; :>> eventDate = ""; :>> dateBasis = "日付なし"; :>> kind = "延期"; :>> inFlightExtension = true; :>> plannedSite = ""; :>> actualSite = ""; :>> causeCategory = "ミッション都合"; }
    part <'LND-135'> lnd_135 : LandingEvent { doc /* STS-133 to facilitate PMM outfitting */ :>> flight = "STS-133"; :>> eventDate = ""; :>> dateBasis = "日付なし"; :>> kind = "延期"; :>> inFlightExtension = true; :>> plannedSite = ""; :>> actualSite = ""; :>> causeCategory = "ミッション都合"; }
    part <'LND-136'> lnd_136 : LandingEvent { doc /* STS-133 additional docked day allowed more time for the Space Shuttl */ :>> flight = "STS-133"; :>> eventDate = ""; :>> dateBasis = "日付なし"; :>> kind = "延期"; :>> inFlightExtension = true; :>> plannedSite = ""; :>> actualSite = ""; :>> causeCategory = "ミッション都合"; }
    part <'LND-137'> lnd_137 : LandingEvent { doc /* STS-135 the additional day was used to accommodate several get-ahead */ :>> flight = "STS-135"; :>> eventDate = "2011-07-11"; :>> dateBasis = "本文"; :>> kind = "延期"; :>> inFlightExtension = true; :>> plannedSite = ""; :>> actualSite = ""; :>> causeCategory = "ミッション都合"; }
}
