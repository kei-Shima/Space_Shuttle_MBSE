// SysML v2 テキスト：TPS 損傷・デブリ履歴定義書（着陸後の打痕の数と、打上げ中の剥離・衝突の事象）
// SSD-DMG-ORB-001 TPS 損傷・デブリ履歴定義書（着陸後の打痕の数と、打上げ中の剥離・衝突の事象） の表から生成（lib/build_docs_cz.py・rev_cz/czdata.py）。根拠の頁は SSD-DMG-ORB-001 にある。
package SSD_DMG_ORB_001 {
    doc /* SSD-DMG-ORB-001 TPS 損傷・デブリ履歴定義書（着陸後の打痕の数と、打上げ中の剥離・衝突の事象）。着陸後の TPS 打痕の数を part def TpsImpactCount、打上げ中の剥離・衝突の事象を part def TpsDebrisEvent の使用として持つ。数・区分・機能ブロックは属性で、パッケージへの矢印は張らない。要求への関係（導出・充足・検証）は張らず、トレースの外に置く。 */
    private import ScalarValues::*;
    part def TpsImpactCount {
        doc /* 着陸後の TPS 検査の打痕の数（飛行ごと）。Mission Report 本文の文、または PLAN_CZ 追記1 の条件を満たす表の値。全飛行の数ではない */
        attribute flight : String;
        attribute period : String;
        attribute valueBasis : String;
        attribute tpsTotal : ScalarValues::Integer;
        attribute tpsGe1in : ScalarValues::Integer;
        attribute lowerTotal : ScalarValues::Integer;
        attribute lowerGe1in : ScalarValues::Integer;
        attribute windowImpacts : ScalarValues::Integer;
    }
    part def TpsDebrisEvent {
        doc /* 打上げ中などの具体的な剥離・衝突の事象。原因の区分・機能ブロックは本書の判断（czrules.py） */
        attribute flight : String;
        attribute phase : String;
        attribute causeCategory : String;
        attribute blockCode : String;
        attribute ruleId : String;
    }
    part <'DMG-001'> dmg_001 : TpsImpactCount { doc /* STS-1 */ :>> flight = "STS-1"; :>> period = "A"; :>> valueBasis = "本文"; :>> tpsTotal = 303; }
    part <'DMG-002'> dmg_002 : TpsImpactCount { doc /* STS-2 */ :>> flight = "STS-2"; :>> period = "A"; :>> valueBasis = "本文"; :>> tpsTotal = 334; }
    part <'DMG-003'> dmg_003 : TpsImpactCount { doc /* STS-3 */ :>> flight = "STS-3"; :>> period = "A"; :>> valueBasis = "本文"; :>> tpsTotal = 193; }
    part <'DMG-004'> dmg_004 : TpsImpactCount { doc /* STS-51G */ :>> flight = "STS-51G"; :>> period = "A"; :>> valueBasis = "本文"; :>> tpsTotal = 315; :>> tpsGe1in = 144; :>> lowerTotal = 231; }
    part <'DMG-005'> dmg_005 : TpsImpactCount { doc /* STS-51F */ :>> flight = "STS-51F"; :>> period = "A"; :>> valueBasis = "本文"; :>> tpsTotal = 553; :>> tpsGe1in = 226; }
    part <'DMG-006'> dmg_006 : TpsImpactCount { doc /* STS-26 */ :>> flight = "STS-26"; :>> period = "B"; :>> valueBasis = "本文"; :>> tpsGe1in = 50; }
    part <'DMG-007'> dmg_007 : TpsImpactCount { doc /* STS-27 */ :>> flight = "STS-27"; :>> period = "B"; :>> valueBasis = "本文"; :>> tpsTotal = 707; :>> tpsGe1in = 298; }
    part <'DMG-008'> dmg_008 : TpsImpactCount { doc /* STS-29 */ :>> flight = "STS-29"; :>> period = "B"; :>> valueBasis = "本文"; :>> tpsTotal = 132; :>> tpsGe1in = 23; :>> lowerTotal = 100; :>> lowerGe1in = 18; }
    part <'DMG-009'> dmg_009 : TpsImpactCount { doc /* STS-30 */ :>> flight = "STS-30"; :>> period = "B"; :>> valueBasis = "本文"; :>> tpsTotal = 151; :>> tpsGe1in = 52; :>> lowerTotal = 134; :>> lowerGe1in = 52; }
    part <'DMG-010'> dmg_010 : TpsImpactCount { doc /* STS-28 */ :>> flight = "STS-28"; :>> period = "B"; :>> valueBasis = "本文"; :>> tpsTotal = 76; :>> tpsGe1in = 20; :>> lowerTotal = 51; :>> lowerGe1in = 14; }
    part <'DMG-011'> dmg_011 : TpsImpactCount { doc /* STS-34 */ :>> flight = "STS-34"; :>> period = "B"; :>> valueBasis = "本文"; :>> lowerTotal = 51; :>> lowerGe1in = 17; }
    part <'DMG-012'> dmg_012 : TpsImpactCount { doc /* STS-32 */ :>> flight = "STS-32"; :>> period = "B"; :>> valueBasis = "本文"; :>> tpsTotal = 120; :>> lowerTotal = 111; }
    part <'DMG-013'> dmg_013 : TpsImpactCount { doc /* STS-36 */ :>> flight = "STS-36"; :>> period = "B"; :>> valueBasis = "本文"; :>> tpsTotal = 81; :>> tpsGe1in = 19; :>> lowerTotal = 61; :>> lowerGe1in = 17; }
    part <'DMG-014'> dmg_014 : TpsImpactCount { doc /* STS-31 */ :>> flight = "STS-31"; :>> period = "B"; :>> valueBasis = "本文"; :>> lowerTotal = 33; :>> lowerGe1in = 11; }
    part <'DMG-015'> dmg_015 : TpsImpactCount { doc /* STS-38 */ :>> flight = "STS-38"; :>> period = "B"; :>> valueBasis = "本文"; :>> lowerTotal = 46; :>> lowerGe1in = 6; }
    part <'DMG-016'> dmg_016 : TpsImpactCount { doc /* STS-35 */ :>> flight = "STS-35"; :>> period = "B"; :>> valueBasis = "本文"; :>> tpsTotal = 147; :>> tpsGe1in = 17; :>> lowerTotal = 132; :>> lowerGe1in = 15; }
    part <'DMG-017'> dmg_017 : TpsImpactCount { doc /* STS-37 */ :>> flight = "STS-37"; :>> period = "B"; :>> valueBasis = "本文"; :>> tpsTotal = 113; :>> tpsGe1in = 10; :>> lowerTotal = 91; :>> lowerGe1in = 7; }
    part <'DMG-018'> dmg_018 : TpsImpactCount { doc /* STS-39 */ :>> flight = "STS-39"; :>> period = "B"; :>> valueBasis = "本文"; :>> tpsTotal = 124; :>> tpsGe1in = 11; :>> lowerTotal = 114; :>> lowerGe1in = 10; }
    part <'DMG-019'> dmg_019 : TpsImpactCount { doc /* STS-40 */ :>> flight = "STS-40"; :>> period = "B"; :>> valueBasis = "本文"; :>> tpsTotal = 197; :>> tpsGe1in = 25; :>> lowerTotal = 153; :>> lowerGe1in = 23; }
    part <'DMG-020'> dmg_020 : TpsImpactCount { doc /* STS-43 */ :>> flight = "STS-43"; :>> period = "B"; :>> valueBasis = "本文"; :>> tpsTotal = 131; :>> tpsGe1in = 25; }
    part <'DMG-021'> dmg_021 : TpsImpactCount { doc /* STS-48 */ :>> flight = "STS-48"; :>> period = "B"; :>> valueBasis = "本文"; :>> tpsTotal = 182; :>> tpsGe1in = 25; :>> lowerTotal = 100; :>> lowerGe1in = 14; }
    part <'DMG-022'> dmg_022 : TpsImpactCount { doc /* STS-44 */ :>> flight = "STS-44"; :>> period = "B"; :>> valueBasis = "本文"; :>> tpsTotal = 109; :>> tpsGe1in = 9; :>> lowerTotal = 74; :>> lowerGe1in = 6; }
    part <'DMG-023'> dmg_023 : TpsImpactCount { doc /* STS-42 */ :>> flight = "STS-42"; :>> period = "B"; :>> valueBasis = "本文"; :>> tpsTotal = 209; :>> tpsGe1in = 44; :>> lowerTotal = 159; :>> lowerGe1in = 38; }
    part <'DMG-024'> dmg_024 : TpsImpactCount { doc /* STS-45 */ :>> flight = "STS-45"; :>> period = "B"; :>> valueBasis = "本文"; :>> lowerTotal = 122; :>> lowerGe1in = 18; }
    part <'DMG-025'> dmg_025 : TpsImpactCount { doc /* STS-49 */ :>> flight = "STS-49"; :>> period = "B"; :>> valueBasis = "本文"; :>> tpsTotal = 114; :>> tpsGe1in = 11; :>> lowerTotal = 55; :>> lowerGe1in = 6; :>> windowImpacts = 1; }
    part <'DMG-026'> dmg_026 : TpsImpactCount { doc /* STS-50 */ :>> flight = "STS-50"; :>> period = "B"; :>> valueBasis = "本文"; :>> tpsTotal = 184; :>> tpsGe1in = 45; :>> lowerTotal = 141; :>> lowerGe1in = 28; :>> windowImpacts = 6; }
    part <'DMG-027'> dmg_027 : TpsImpactCount { doc /* STS-46 */ :>> flight = "STS-46"; :>> period = "B"; :>> valueBasis = "本文"; :>> tpsTotal = 236; :>> tpsGe1in = 22; :>> lowerTotal = 186; :>> lowerGe1in = 11; }
    part <'DMG-028'> dmg_028 : TpsImpactCount { doc /* STS-47 */ :>> flight = "STS-47"; :>> period = "B"; :>> valueBasis = "本文"; :>> tpsTotal = 107; :>> tpsGe1in = 11; :>> lowerTotal = 47; :>> lowerGe1in = 3; }
    part <'DMG-029'> dmg_029 : TpsImpactCount { doc /* STS-52 */ :>> flight = "STS-52"; :>> period = "B"; :>> valueBasis = "本文"; :>> tpsTotal = 290; :>> tpsGe1in = 16; :>> lowerTotal = 152; :>> lowerGe1in = 6; }
    part <'DMG-030'> dmg_030 : TpsImpactCount { doc /* STS-53 */ :>> flight = "STS-53"; :>> period = "B"; :>> valueBasis = "本文"; :>> tpsTotal = 240; :>> tpsGe1in = 23; :>> lowerTotal = 145; :>> lowerGe1in = 11; }
    part <'DMG-031'> dmg_031 : TpsImpactCount { doc /* STS-54 */ :>> flight = "STS-54"; :>> period = "B"; :>> valueBasis = "本文"; :>> tpsTotal = 131; :>> tpsGe1in = 14; :>> lowerTotal = 80; :>> lowerGe1in = 14; }
    part <'DMG-032'> dmg_032 : TpsImpactCount { doc /* STS-56 */ :>> flight = "STS-56"; :>> period = "B"; :>> valueBasis = "本文"; :>> tpsTotal = 156; :>> tpsGe1in = 36; }
    part <'DMG-033'> dmg_033 : TpsImpactCount { doc /* STS-55 */ :>> flight = "STS-55"; :>> period = "B"; :>> valueBasis = "本文"; :>> tpsTotal = 143; :>> tpsGe1in = 13; :>> lowerTotal = 128; }
    part <'DMG-034'> dmg_034 : TpsImpactCount { doc /* STS-57 */ :>> flight = "STS-57"; :>> period = "B"; :>> valueBasis = "本文"; :>> tpsTotal = 106; :>> tpsGe1in = 12; :>> lowerTotal = 75; :>> lowerGe1in = 10; }
    part <'DMG-035'> dmg_035 : TpsImpactCount { doc /* STS-51 */ :>> flight = "STS-51"; :>> period = "B"; :>> valueBasis = "本文"; :>> tpsTotal = 154; :>> tpsGe1in = 18; :>> lowerTotal = 100; :>> lowerGe1in = 18; }
    part <'DMG-036'> dmg_036 : TpsImpactCount { doc /* STS-58 */ :>> flight = "STS-58"; :>> period = "B"; :>> valueBasis = "本文"; :>> tpsTotal = 155; :>> tpsGe1in = 26; :>> lowerTotal = 78; }
    part <'DMG-037'> dmg_037 : TpsImpactCount { doc /* STS-61 */ :>> flight = "STS-61"; :>> period = "B"; :>> valueBasis = "本文"; :>> tpsTotal = 120; :>> tpsGe1in = 13; :>> lowerTotal = 59; :>> lowerGe1in = 7; }
    part <'DMG-038'> dmg_038 : TpsImpactCount { doc /* STS-60 */ :>> flight = "STS-60"; :>> period = "B"; :>> valueBasis = "本文"; :>> tpsTotal = 106; :>> tpsGe1in = 15; :>> lowerTotal = 48; }
    part <'DMG-039'> dmg_039 : TpsImpactCount { doc /* STS-62 */ :>> flight = "STS-62"; :>> period = "B"; :>> valueBasis = "本文"; :>> tpsTotal = 97; :>> tpsGe1in = 16; :>> lowerTotal = 39; :>> lowerGe1in = 7; }
    part <'DMG-040'> dmg_040 : TpsImpactCount { doc /* STS-59 */ :>> flight = "STS-59"; :>> period = "B"; :>> valueBasis = "本文"; :>> tpsTotal = 77; :>> tpsGe1in = 19; :>> lowerTotal = 38; :>> lowerGe1in = 11; }
    part <'DMG-041'> dmg_041 : TpsImpactCount { doc /* STS-65 */ :>> flight = "STS-65"; :>> period = "B"; :>> valueBasis = "本文"; :>> lowerTotal = 86; :>> lowerGe1in = 18; }
    part <'DMG-042'> dmg_042 : TpsImpactCount { doc /* STS-68 */ :>> flight = "STS-68"; :>> period = "B"; :>> valueBasis = "本文"; :>> tpsTotal = 110; :>> tpsGe1in = 15; :>> lowerTotal = 59; :>> lowerGe1in = 9; }
    part <'DMG-043'> dmg_043 : TpsImpactCount { doc /* STS-66 */ :>> flight = "STS-66"; :>> period = "B"; :>> valueBasis = "本文"; :>> tpsTotal = 148; :>> tpsGe1in = 28; :>> lowerTotal = 111; :>> lowerGe1in = 22; }
    part <'DMG-044'> dmg_044 : TpsImpactCount { doc /* STS-63 */ :>> flight = "STS-63"; :>> period = "B"; :>> valueBasis = "本文"; :>> tpsTotal = 125; :>> tpsGe1in = 14; :>> lowerTotal = 84; :>> lowerGe1in = 7; }
    part <'DMG-045'> dmg_045 : TpsImpactCount { doc /* STS-67 */ :>> flight = "STS-67"; :>> period = "B"; :>> valueBasis = "本文"; :>> tpsTotal = 79; :>> tpsGe1in = 13; :>> lowerTotal = 50; :>> lowerGe1in = 11; }
    part <'DMG-046'> dmg_046 : TpsImpactCount { doc /* STS-71 */ :>> flight = "STS-71"; :>> period = "B"; :>> valueBasis = "本文"; :>> tpsTotal = 164; :>> tpsGe1in = 25; :>> lowerTotal = 149; :>> lowerGe1in = 24; }
    part <'DMG-047'> dmg_047 : TpsImpactCount { doc /* STS-69 */ :>> flight = "STS-69"; :>> period = "B"; :>> valueBasis = "本文"; :>> tpsTotal = 198; :>> tpsGe1in = 27; :>> lowerTotal = 175; :>> lowerGe1in = 22; }
    part <'DMG-048'> dmg_048 : TpsImpactCount { doc /* STS-73 */ :>> flight = "STS-73"; :>> period = "B"; :>> valueBasis = "本文"; :>> tpsTotal = 147; :>> tpsGe1in = 26; :>> lowerTotal = 102; :>> lowerGe1in = 17; :>> windowImpacts = 1; }
    part <'DMG-049'> dmg_049 : TpsImpactCount { doc /* STS-74 */ :>> flight = "STS-74"; :>> period = "B"; :>> valueBasis = "本文"; :>> tpsTotal = 116; :>> tpsGe1in = 21; }
    part <'DMG-050'> dmg_050 : TpsImpactCount { doc /* STS-72 */ :>> flight = "STS-72"; :>> period = "B"; :>> valueBasis = "本文"; :>> tpsTotal = 55; :>> tpsGe1in = 7; }
    part <'DMG-051'> dmg_051 : TpsImpactCount { doc /* STS-75 */ :>> flight = "STS-75"; :>> period = "B"; :>> valueBasis = "本文"; :>> tpsTotal = 96; :>> tpsGe1in = 17; }
    part <'DMG-052'> dmg_052 : TpsImpactCount { doc /* STS-76 */ :>> flight = "STS-76"; :>> period = "B"; :>> valueBasis = "本文"; :>> tpsTotal = 69; :>> tpsGe1in = 15; :>> lowerGe1in = 5; }
    part <'DMG-053'> dmg_053 : TpsImpactCount { doc /* STS-77 */ :>> flight = "STS-77"; :>> period = "B"; :>> valueBasis = "本文"; :>> tpsTotal = 81; :>> lowerGe1in = 15; }
    part <'DMG-054'> dmg_054 : TpsImpactCount { doc /* STS-78 */ :>> flight = "STS-78"; :>> period = "B"; :>> valueBasis = "本文"; :>> tpsTotal = 85; :>> lowerTotal = 35; :>> lowerGe1in = 5; }
    part <'DMG-055'> dmg_055 : TpsImpactCount { doc /* STS-80 */ :>> flight = "STS-80"; :>> period = "B"; :>> valueBasis = "本文"; :>> tpsTotal = 93; :>> tpsGe1in = 8; }
    part <'DMG-056'> dmg_056 : TpsImpactCount { doc /* STS-81 */ :>> flight = "STS-81"; :>> period = "B"; :>> valueBasis = "本文"; :>> tpsTotal = 100; :>> tpsGe1in = 15; }
    part <'DMG-057'> dmg_057 : TpsImpactCount { doc /* STS-82 */ :>> flight = "STS-82"; :>> period = "B"; :>> valueBasis = "本文"; :>> tpsTotal = 103; :>> tpsGe1in = 18; :>> lowerTotal = 53; :>> lowerGe1in = 15; }
    part <'DMG-058'> dmg_058 : TpsImpactCount { doc /* STS-83 */ :>> flight = "STS-83"; :>> period = "B"; :>> valueBasis = "本文"; :>> tpsTotal = 81; :>> tpsGe1in = 13; :>> lowerTotal = 38; :>> lowerGe1in = 7; }
    part <'DMG-059'> dmg_059 : TpsImpactCount { doc /* STS-84 */ :>> flight = "STS-84"; :>> period = "B"; :>> valueBasis = "本文"; :>> tpsTotal = 103; :>> tpsGe1in = 13; }
    part <'DMG-060'> dmg_060 : TpsImpactCount { doc /* STS-85 */ :>> flight = "STS-85"; :>> period = "B"; :>> valueBasis = "本文"; :>> tpsTotal = 102; :>> tpsGe1in = 13; }
    part <'DMG-061'> dmg_061 : TpsImpactCount { doc /* STS-86 */ :>> flight = "STS-86"; :>> period = "B"; :>> valueBasis = "本文"; :>> tpsTotal = 129; :>> tpsGe1in = 31; }
    part <'DMG-062'> dmg_062 : TpsImpactCount { doc /* STS-87 */ :>> flight = "STS-87"; :>> period = "B"; :>> valueBasis = "本文"; :>> tpsTotal = 308; :>> tpsGe1in = 132; :>> lowerTotal = 244; :>> lowerGe1in = 109; }
    part <'DMG-063'> dmg_063 : TpsImpactCount { doc /* STS-89 */ :>> flight = "STS-89"; :>> period = "B"; :>> valueBasis = "本文"; :>> tpsTotal = 138; :>> tpsGe1in = 40; }
    part <'DMG-064'> dmg_064 : TpsImpactCount { doc /* STS-95 */ :>> flight = "STS-95"; :>> period = "B"; :>> valueBasis = "本文"; :>> tpsTotal = 187; :>> tpsGe1in = 45; }
    part <'DMG-065'> dmg_065 : TpsImpactCount { doc /* STS-88 */ :>> flight = "STS-88"; :>> period = "B"; :>> valueBasis = "本文"; :>> tpsTotal = 116; :>> tpsGe1in = 25; }
    part <'DMG-066'> dmg_066 : TpsImpactCount { doc /* STS-96 */ :>> flight = "STS-96"; :>> period = "B"; :>> valueBasis = "本文"; :>> tpsTotal = 199; :>> tpsGe1in = 72; }
    part <'DMG-067'> dmg_067 : TpsImpactCount { doc /* STS-93 */ :>> flight = "STS-93"; :>> period = "B"; :>> valueBasis = "本文"; :>> tpsTotal = 208; :>> lowerTotal = 161; }
    part <'DMG-068'> dmg_068 : TpsImpactCount { doc /* STS-103 */ :>> flight = "STS-103"; :>> period = "B"; :>> valueBasis = "本文"; :>> tpsTotal = 153; :>> tpsGe1in = 18; :>> lowerTotal = 84; :>> lowerGe1in = 13; }
    part <'DMG-069'> dmg_069 : TpsImpactCount { doc /* STS-99 */ :>> flight = "STS-99"; :>> period = "B"; :>> valueBasis = "本文"; :>> tpsTotal = 87; :>> tpsGe1in = 21; }
    part <'DMG-070'> dmg_070 : TpsImpactCount { doc /* STS-101 */ :>> flight = "STS-101"; :>> period = "B"; :>> valueBasis = "本文"; :>> tpsTotal = 113; :>> tpsGe1in = 27; :>> lowerTotal = 70; :>> lowerGe1in = 19; }
    part <'DMG-071'> dmg_071 : TpsImpactCount { doc /* STS-106 */ :>> flight = "STS-106"; :>> period = "B"; :>> valueBasis = "本文"; :>> tpsTotal = 105; :>> tpsGe1in = 17; :>> lowerTotal = 73; :>> lowerGe1in = 17; }
    part <'DMG-072'> dmg_072 : TpsImpactCount { doc /* STS-92 */ :>> flight = "STS-92"; :>> period = "B"; :>> valueBasis = "本文"; :>> tpsTotal = 127; :>> tpsGe1in = 24; :>> lowerTotal = 86; :>> lowerGe1in = 14; }
    part <'DMG-073'> dmg_073 : TpsImpactCount { doc /* STS-97 */ :>> flight = "STS-97"; :>> period = "B"; :>> valueBasis = "本文"; :>> tpsTotal = 84; :>> tpsGe1in = 10; :>> lowerTotal = 78; :>> lowerGe1in = 10; }
    part <'DMG-074'> dmg_074 : TpsImpactCount { doc /* STS-98 */ :>> flight = "STS-98"; :>> period = "B"; :>> valueBasis = "本文"; :>> tpsTotal = 102; :>> tpsGe1in = 13; :>> lowerTotal = 73; :>> lowerGe1in = 8; }
    part <'DMG-075'> dmg_075 : TpsImpactCount { doc /* STS-102 */ :>> flight = "STS-102"; :>> period = "B"; :>> valueBasis = "本文"; :>> tpsTotal = 100; :>> tpsGe1in = 14; :>> lowerTotal = 44; :>> lowerGe1in = 10; }
    part <'DMG-076'> dmg_076 : TpsImpactCount { doc /* STS-100 */ :>> flight = "STS-100"; :>> period = "B"; :>> valueBasis = "本文"; :>> tpsTotal = 92; :>> tpsGe1in = 13; :>> lowerTotal = 42; :>> lowerGe1in = 4; }
    part <'DMG-077'> dmg_077 : TpsImpactCount { doc /* STS-104 */ :>> flight = "STS-104"; :>> period = "B"; :>> valueBasis = "本文"; :>> tpsTotal = 126; :>> tpsGe1in = 26; :>> lowerTotal = 108; :>> lowerGe1in = 24; }
    part <'DMG-078'> dmg_078 : TpsImpactCount { doc /* STS-105 */ :>> flight = "STS-105"; :>> period = "B"; :>> valueBasis = "本文"; :>> tpsTotal = 144; :>> tpsGe1in = 25; :>> lowerTotal = 108; :>> lowerGe1in = 15; }
    part <'DMG-079'> dmg_079 : TpsImpactCount { doc /* STS-108 */ :>> flight = "STS-108"; :>> period = "B"; :>> valueBasis = "本文"; :>> tpsTotal = 95; :>> tpsGe1in = 22; :>> lowerTotal = 81; :>> lowerGe1in = 12; }
    part <'DMG-080'> dmg_080 : TpsImpactCount { doc /* STS-109 */ :>> flight = "STS-109"; :>> period = "B"; :>> valueBasis = "本文"; :>> tpsTotal = 98; :>> tpsGe1in = 18; :>> lowerTotal = 63; :>> lowerGe1in = 14; }
    part <'DMG-081'> dmg_081 : TpsImpactCount { doc /* STS-110 */ :>> flight = "STS-110"; :>> period = "B"; :>> valueBasis = "本文"; :>> tpsTotal = 110; :>> tpsGe1in = 22; :>> lowerTotal = 70; :>> lowerGe1in = 18; }
    part <'DMG-082'> dmg_082 : TpsImpactCount { doc /* STS-111 */ :>> flight = "STS-111"; :>> period = "B"; :>> valueBasis = "本文"; :>> tpsTotal = 79; :>> tpsGe1in = 26; :>> lowerTotal = 47; :>> lowerGe1in = 21; }
    part <'DMG-083'> dmg_083 : TpsImpactCount { doc /* STS-112 */ :>> flight = "STS-112"; :>> period = "B"; :>> valueBasis = "本文"; :>> tpsTotal = 79; :>> tpsGe1in = 26; :>> lowerTotal = 47; :>> lowerGe1in = 21; }
    part <'DMG-084'> dmg_084 : TpsImpactCount { doc /* STS-113 */ :>> flight = "STS-113"; :>> period = "B"; :>> valueBasis = "本文"; :>> tpsTotal = 113; :>> tpsGe1in = 29; :>> lowerTotal = 68; :>> lowerGe1in = 14; }
    part <'DMG-085'> dmg_085 : TpsImpactCount { doc /* STS-33 */ :>> flight = "STS-33"; :>> period = "B"; :>> valueBasis = "本文"; :>> tpsTotal = 118; :>> tpsGe1in = 21; :>> lowerTotal = 107; :>> lowerGe1in = 21; }
    part <'DMG-086'> dmg_086 : TpsImpactCount { doc /* STS-41 */ :>> flight = "STS-41"; :>> period = "B"; :>> valueBasis = "本文"; :>> tpsTotal = 76; :>> tpsGe1in = 16; :>> lowerTotal = 64; :>> lowerGe1in = 13; }
    part <'DMG-087'> dmg_087 : TpsImpactCount { doc /* STS-64 */ :>> flight = "STS-64"; :>> period = "B"; :>> valueBasis = "本文"; :>> tpsTotal = 173; :>> tpsGe1in = 22; :>> lowerTotal = 116; :>> lowerGe1in = 18; }
    part <'DMG-088'> dmg_088 : TpsImpactCount { doc /* STS-70 */ :>> flight = "STS-70"; :>> period = "B"; :>> valueBasis = "本文"; :>> tpsTotal = 127; :>> lowerTotal = 81; :>> lowerGe1in = 5; }
    part <'DMG-089'> dmg_089 : TpsImpactCount { doc /* STS-90 */ :>> flight = "STS-90"; :>> period = "B"; :>> valueBasis = "本文"; :>> tpsTotal = 131; :>> tpsGe1in = 20; :>> lowerTotal = 76; }
    part <'DMG-090'> dmg_090 : TpsImpactCount { doc /* STS-91 */ :>> flight = "STS-91"; :>> period = "B"; :>> valueBasis = "本文"; :>> tpsTotal = 198; :>> tpsGe1in = 50; }
    part <'DMG-091'> dmg_091 : TpsImpactCount { doc /* STS-94 */ :>> flight = "STS-94"; :>> period = "B"; :>> valueBasis = "本文"; :>> tpsTotal = 90; :>> tpsGe1in = 12; :>> lowerTotal = 34; :>> lowerGe1in = 11; }
    part <'DMG-092'> dmg_092 : TpsImpactCount { doc /* STS-114 */ :>> flight = "STS-114"; :>> period = "C"; :>> valueBasis = "本文"; :>> tpsTotal = 176; :>> tpsGe1in = 29; :>> lowerTotal = 152; :>> lowerGe1in = 21; }
    part <'DMG-093'> dmg_093 : TpsImpactCount { doc /* STS-121 */ :>> flight = "STS-121"; :>> period = "C"; :>> valueBasis = "本文"; :>> tpsTotal = 117; :>> tpsGe1in = 12; :>> windowImpacts = 160; }
    part <'DMG-094'> dmg_094 : TpsImpactCount { doc /* STS-115 */ :>> flight = "STS-115"; :>> period = "C"; :>> valueBasis = "本文"; :>> windowImpacts = 224; }
    part <'DMG-095'> dmg_095 : TpsImpactCount { doc /* STS-116 */ :>> flight = "STS-116"; :>> period = "C"; :>> valueBasis = "本文"; :>> lowerTotal = 120; :>> lowerGe1in = 22; }
    part <'DMG-096'> dmg_096 : TpsImpactCount { doc /* STS-117 */ :>> flight = "STS-117"; :>> period = "C"; :>> valueBasis = "本文"; :>> lowerTotal = 247; :>> lowerGe1in = 15; }
    part <'DMG-097'> dmg_097 : TpsImpactCount { doc /* STS-118 */ :>> flight = "STS-118"; :>> period = "C"; :>> valueBasis = "本文"; :>> tpsTotal = 237; :>> tpsGe1in = 40; :>> lowerTotal = 188; :>> lowerGe1in = 28; }
    part <'DMG-098'> dmg_098 : TpsImpactCount { doc /* STS-122 */ :>> flight = "STS-122"; :>> period = "C"; :>> valueBasis = "表"; :>> tpsTotal = 208; :>> tpsGe1in = 21; :>> lowerTotal = 158; :>> lowerGe1in = 16; }
    part <'DMG-099'> dmg_099 : TpsImpactCount { doc /* STS-123 */ :>> flight = "STS-123"; :>> period = "C"; :>> valueBasis = "表"; :>> tpsTotal = 98; :>> tpsGe1in = 13; :>> lowerTotal = 45; :>> lowerGe1in = 8; }
    part <'DMG-100'> dmg_100 : TpsImpactCount { doc /* STS-124 */ :>> flight = "STS-124"; :>> period = "C"; :>> valueBasis = "表"; :>> tpsTotal = 147; :>> tpsGe1in = 16; :>> lowerTotal = 104; :>> lowerGe1in = 10; }
    part <'DMG-101'> dmg_101 : TpsImpactCount { doc /* STS-126 */ :>> flight = "STS-126"; :>> period = "C"; :>> valueBasis = "表"; :>> tpsTotal = 97; :>> tpsGe1in = 14; :>> lowerTotal = 74; :>> lowerGe1in = 8; :>> windowImpacts = 1; }
    part <'DMG-102'> dmg_102 : TpsImpactCount { doc /* STS-119 */ :>> flight = "STS-119"; :>> period = "C"; :>> valueBasis = "表"; :>> tpsTotal = 119; :>> tpsGe1in = 11; :>> lowerTotal = 76; :>> lowerGe1in = 8; }
    part <'DMG-103'> dmg_103 : TpsImpactCount { doc /* STS-125 */ :>> flight = "STS-125"; :>> period = "C"; :>> valueBasis = "表"; :>> tpsTotal = 156; :>> tpsGe1in = 18; :>> lowerTotal = 109; :>> lowerGe1in = 14; }
    part <'DMG-104'> dmg_104 : TpsImpactCount { doc /* STS-127 */ :>> flight = "STS-127"; :>> period = "C"; :>> valueBasis = "表"; :>> tpsTotal = 107; :>> tpsGe1in = 21; :>> lowerTotal = 82; :>> lowerGe1in = 18; }
    part <'DMG-105'> dmg_105 : TpsImpactCount { doc /* STS-128 */ :>> flight = "STS-128"; :>> period = "C"; :>> valueBasis = "表"; :>> tpsTotal = 180; :>> tpsGe1in = 27; :>> lowerTotal = 143; :>> lowerGe1in = 23; }
    part <'DMG-106'> dmg_106 : TpsImpactCount { doc /* STS-129 */ :>> flight = "STS-129"; :>> period = "C"; :>> valueBasis = "表"; :>> tpsTotal = 89; :>> tpsGe1in = 14; :>> lowerTotal = 58; :>> lowerGe1in = 8; :>> windowImpacts = 14; }
    part <'DMG-107'> dmg_107 : TpsImpactCount { doc /* STS-130 */ :>> flight = "STS-130"; :>> period = "C"; :>> valueBasis = "表"; :>> tpsTotal = 64; :>> tpsGe1in = 12; :>> lowerTotal = 46; :>> lowerGe1in = 9; }
    part <'DMG-108'> dmg_108 : TpsImpactCount { doc /* STS-131 */ :>> flight = "STS-131"; :>> period = "C"; :>> valueBasis = "表"; :>> tpsTotal = 155; :>> tpsGe1in = 10; :>> lowerTotal = 136; :>> lowerGe1in = 8; }
    part <'DMG-109'> dmg_109 : TpsImpactCount { doc /* STS-132 */ :>> flight = "STS-132"; :>> period = "C"; :>> valueBasis = "表"; :>> tpsTotal = 124; :>> tpsGe1in = 9; :>> lowerTotal = 95; :>> lowerGe1in = 4; }
    part <'DMG-110'> dmg_110 : TpsImpactCount { doc /* STS-133 */ :>> flight = "STS-133"; :>> period = "C"; :>> valueBasis = "表"; :>> tpsTotal = 56; :>> tpsGe1in = 6; :>> lowerTotal = 46; :>> lowerGe1in = 5; }
    part <'DMG-111'> dmg_111 : TpsImpactCount { doc /* STS-134 */ :>> flight = "STS-134"; :>> period = "C"; :>> valueBasis = "表"; :>> tpsTotal = 121; :>> tpsGe1in = 22; :>> lowerTotal = 104; :>> lowerGe1in = 21; }
    part <'DMG-112'> dmg_112 : TpsImpactCount { doc /* STS-135 */ :>> flight = "STS-135"; :>> period = "C"; :>> valueBasis = "表"; :>> tpsTotal = 103; :>> tpsGe1in = 17; :>> lowerTotal = 83; :>> lowerGe1in = 14; }
    part <'DME-001'> dme_001 : TpsDebrisEvent { doc /* STS-1 ice, frost and/or Spray-on-foam insulation (SOFI)  */ :>> flight = "STS-1"; :>> phase = "ascent"; :>> causeCategory = "ET・臍帯部起因"; :>> blockCode = "ET"; :>> ruleId = "E"; }
    part <'DME-002'> dme_002 : TpsDebrisEvent { doc /* STS-2 pad debris (documented by launch pad cameras) */ :>> flight = "STS-2"; :>> phase = "ascent"; :>> causeCategory = "地上・発射台"; :>> blockCode = ""; :>> ruleId = "G"; }
    part <'DME-003'> dme_003 : TpsDebrisEvent { doc /* STS-2 baggy cord impact (or ascent debris impact), assum */ :>> flight = "STS-2"; :>> phase = "ascent"; :>> causeCategory = "オービタ自身"; :>> blockCode = "TPS"; :>> ruleId = "O"; }
    part <'DME-004'> dme_004 : TpsDebrisEvent { doc /* STS-2 instrumentation wires that disconnected from the m */ :>> flight = "STS-2"; :>> phase = "landing"; :>> causeCategory = "オービタ自身"; :>> blockCode = "TPS"; :>> ruleId = "O"; }
    part <'DME-005'> dme_005 : TpsDebrisEvent { doc /* STS-3 undensified tiles and pieces of tiles lost (21 ful */ :>> flight = "STS-3"; :>> phase = "ascent"; :>> causeCategory = "オービタ自身"; :>> blockCode = "TPS"; :>> ruleId = "O"; }
    part <'DME-006'> dme_006 : TpsDebrisEvent { doc /* STS-3 undensified tiles lost (16) */ :>> flight = "STS-3"; :>> phase = "ascent"; :>> causeCategory = "オービタ自身"; :>> blockCode = "TPS"; :>> ruleId = "O"; }
    part <'DME-007'> dme_007 : TpsDebrisEvent { doc /* STS-4 hail (storm at Launch Pad A) */ :>> flight = "STS-4"; :>> phase = "prelaunch"; :>> causeCategory = "地上・発射台"; :>> blockCode = ""; :>> ruleId = "G"; }
    part <'DME-008'> dme_008 : TpsDebrisEvent { doc /* STS-7 pit (cause not stated; crew first noticed it on da */ :>> flight = "STS-7"; :>> phase = "on-orbit"; :>> causeCategory = "その他・原因の記載なし"; :>> blockCode = ""; :>> ruleId = "U"; }
    part <'DME-009'> dme_009 : TpsDebrisEvent { doc /* STS-7 debris (unspecified) */ :>> flight = "STS-7"; :>> phase = "ascent"; :>> causeCategory = "その他・原因の記載なし"; :>> blockCode = ""; :>> ruleId = "U"; }
    part <'DME-010'> dme_010 : TpsDebrisEvent { doc /* STS-8 one Orbiter gap filler, one felt plug and two scra */ :>> flight = "STS-8"; :>> phase = "ascent"; :>> causeCategory = "オービタ自身"; :>> blockCode = "TPS"; :>> ruleId = "O"; }
    part <'DME-011'> dme_011 : TpsDebrisEvent { doc /* STS-41G multilayer FRSI closeout strip (about 6x40 in) mis */ :>> flight = "STS-41G"; :>> phase = "on-orbit"; :>> causeCategory = "オービタ自身"; :>> blockCode = "TPS"; :>> ruleId = "O"; }
    part <'DME-012'> dme_012 : TpsDebrisEvent { doc /* STS-41G tile missing */ :>> flight = "STS-41G"; :>> phase = "postlanding"; :>> causeCategory = "オービタ自身"; :>> blockCode = "TPS"; :>> ruleId = "O"; }
    part <'DME-013'> dme_013 : TpsDebrisEvent { doc /* STS-51A a 'hit' of some type (source not stated) */ :>> flight = "STS-51A"; :>> phase = "on-orbit"; :>> causeCategory = "その他・原因の記載なし"; :>> blockCode = ""; :>> ruleId = "U"; }
    part <'DME-014'> dme_014 : TpsDebrisEvent { doc /* STS-51B protrusion from the thermal protection system */ :>> flight = "STS-51B"; :>> phase = "on-orbit"; :>> causeCategory = "その他・原因の記載なし"; :>> blockCode = ""; :>> ruleId = "U"; }
    part <'DME-015'> dme_015 : TpsDebrisEvent { doc /* STS-51G pieces of ET insulation (foam) ejected by gas bubb */ :>> flight = "STS-51G"; :>> phase = "ascent"; :>> causeCategory = "ET・臍帯部起因"; :>> blockCode = "ET"; :>> ruleId = "E"; }
    part <'DME-016'> dme_016 : TpsDebrisEvent { doc /* STS-51F SOFI (spray-on foam insulation) piece from the ext */ :>> flight = "STS-51F"; :>> phase = "ascent"; :>> causeCategory = "ET・臍帯部起因"; :>> blockCode = "ET"; :>> ruleId = "E"; }
    part <'DME-017'> dme_017 : TpsDebrisEvent { doc /* STS-51F large divots in the SOFI (from ET separation films */ :>> flight = "STS-51F"; :>> phase = "ascent"; :>> causeCategory = "ET・臍帯部起因"; :>> blockCode = "ET"; :>> ruleId = "E"; }
    part <'DME-018'> dme_018 : TpsDebrisEvent { doc /* STS-51F SOFI piece */ :>> flight = "STS-51F"; :>> phase = ""; :>> causeCategory = "ET・臍帯部起因"; :>> blockCode = "ET"; :>> ruleId = "E"; }
    part <'DME-019'> dme_019 : TpsDebrisEvent { doc /* STS-26 large impact damage site (source not stated); part */ :>> flight = "STS-26"; :>> phase = ""; :>> causeCategory = "その他・原因の記載なし"; :>> blockCode = ""; :>> ruleId = "U"; }
    part <'DME-020'> dme_020 : TpsDebrisEvent { doc /* STS-27 debris hits (source not stated); area of major dam */ :>> flight = "STS-27"; :>> phase = ""; :>> causeCategory = "その他・原因の記載なし"; :>> blockCode = ""; :>> ruleId = "X"; }
    part <'DME-021'> dme_021 : TpsDebrisEvent { doc /* STS-27 AFRSI-covered fiberglass carrier panel lost (attri */ :>> flight = "STS-27"; :>> phase = ""; :>> causeCategory = "オービタ自身"; :>> blockCode = "TPS"; :>> ruleId = "O"; }
    part <'DME-022'> dme_022 : TpsDebrisEvent { doc /* STS-29 holddown post 8 hardware pieces missing (NSI boost */ :>> flight = "STS-29"; :>> phase = "ascent"; :>> causeCategory = "地上・発射台"; :>> blockCode = ""; :>> ruleId = "G"; }
    part <'DME-023'> dme_023 : TpsDebrisEvent { doc /* STS-29 butcher paper debris (pieces) */ :>> flight = "STS-29"; :>> phase = "ascent"; :>> causeCategory = "オービタ自身"; :>> blockCode = "TPS"; :>> ruleId = "O"; }
    part <'DME-024'> dme_024 : TpsDebrisEvent { doc /* STS-30 shredded rubber tire tread */ :>> flight = "STS-30"; :>> phase = "postlanding"; :>> causeCategory = "オービタ自身"; :>> blockCode = "TPS"; :>> ruleId = "O"; }
    part <'DME-025'> dme_025 : TpsDebrisEvent { doc /* STS-30 butcher paper used to protect RCS thrusters (sever */ :>> flight = "STS-30"; :>> phase = "ascent"; :>> causeCategory = "オービタ自身"; :>> blockCode = "RCS"; :>> ruleId = "O"; }
    part <'DME-026'> dme_026 : TpsDebrisEvent { doc /* STS-30 SRB debris (minimal amount) */ :>> flight = "STS-30"; :>> phase = "ascent"; :>> causeCategory = "SRB・RSRM 起因"; :>> blockCode = "SRB"; :>> ruleId = "X"; }
    part <'DME-027'> dme_027 : TpsDebrisEvent { doc /* STS-28 TPS along forward portion of liquid oxygen umbilic */ :>> flight = "STS-28"; :>> phase = ""; :>> causeCategory = "その他・原因の記載なし"; :>> blockCode = ""; :>> ruleId = "U"; }
    part <'DME-028'> dme_028 : TpsDebrisEvent { doc /* STS-34 no. 10 washer */ :>> flight = "STS-34"; :>> phase = ""; :>> causeCategory = "オービタ自身"; :>> blockCode = "TPS"; :>> ruleId = "O"; }
    part <'DME-029'> dme_029 : TpsDebrisEvent { doc /* STS-34 debris impact (OMS pod hit) */ :>> flight = "STS-34"; :>> phase = ""; :>> causeCategory = "その他・原因の記載なし"; :>> blockCode = ""; :>> ruleId = "U"; }
    part <'DME-030'> dme_030 : TpsDebrisEvent { doc /* STS-32 umbilical ice impacts during ET separation */ :>> flight = "STS-32"; :>> phase = "ascent"; :>> causeCategory = "ET・臍帯部起因"; :>> blockCode = "ET"; :>> ruleId = "E"; }
    part <'DME-031'> dme_031 : TpsDebrisEvent { doc /* STS-32 screed repair (identified in the launch films and  */ :>> flight = "STS-32"; :>> phase = "ascent"; :>> causeCategory = "オービタ自身"; :>> blockCode = "TPS"; :>> ruleId = "O"; }
    part <'DME-032'> dme_032 : TpsDebrisEvent { doc /* STS-35 hits (cluster; source not stated) */ :>> flight = "STS-35"; :>> phase = ""; :>> causeCategory = "その他・原因の記載なし"; :>> blockCode = ""; :>> ruleId = "U"; }
    part <'DME-033'> dme_033 : TpsDebrisEvent { doc /* STS-37 ice/debris impacts during ET separation and/or dam */ :>> flight = "STS-37"; :>> phase = "ascent"; :>> causeCategory = "ET・臍帯部起因"; :>> blockCode = "ET"; :>> ruleId = "E"; }
    part <'DME-034'> dme_034 : TpsDebrisEvent { doc /* STS-40 small guide pin sleeve (bushing) from the ET half  */ :>> flight = "STS-40"; :>> phase = "ascent"; :>> causeCategory = "ET・臍帯部起因"; :>> blockCode = "ET"; :>> ruleId = "E"; }
    part <'DME-035'> dme_035 : TpsDebrisEvent { doc /* STS-43 section of an engine dome blanket detached (about  */ :>> flight = "STS-43"; :>> phase = "ascent"; :>> causeCategory = "オービタ自身"; :>> blockCode = "TPS"; :>> ruleId = "O"; }
    part <'DME-036'> dme_036 : TpsDebrisEvent { doc /* STS-43 ice from the liquid oxygen feedline bellows or sup */ :>> flight = "STS-43"; :>> phase = "ascent"; :>> causeCategory = "ET・臍帯部起因"; :>> blockCode = "ET"; :>> ruleId = "E"; }
    part <'DME-037'> dme_037 : TpsDebrisEvent { doc /* STS-43 ice from the liquid oxygen ET/Orbiter umbilical du */ :>> flight = "STS-43"; :>> phase = "ascent"; :>> causeCategory = "ET・臍帯部起因"; :>> blockCode = "ET"; :>> ruleId = "E"; }
    part <'DME-038'> dme_038 : TpsDebrisEvent { doc /* STS-48 ice from the ET liquid oxygen feedline bellows and */ :>> flight = "STS-48"; :>> phase = ""; :>> causeCategory = "ET・臍帯部起因"; :>> blockCode = "ET"; :>> ruleId = "E"; }
    part <'DME-039'> dme_039 : TpsDebrisEvent { doc /* STS-48 hits (source still being evaluated) */ :>> flight = "STS-48"; :>> phase = ""; :>> causeCategory = "その他・原因の記載なし"; :>> blockCode = ""; :>> ruleId = "U"; }
    part <'DME-040'> dme_040 : TpsDebrisEvent { doc /* STS-44 ice and TPS debris from random sources */ :>> flight = "STS-44"; :>> phase = "ascent"; :>> causeCategory = "その他・原因の記載なし"; :>> blockCode = ""; :>> ruleId = "X"; }
    part <'DME-041'> dme_041 : TpsDebrisEvent { doc /* STS-45 low density material (shallow debris hits) */ :>> flight = "STS-45"; :>> phase = ""; :>> causeCategory = "その他・原因の記載なし"; :>> blockCode = ""; :>> ruleId = "U"; }
    part <'DME-042'> dme_042 : TpsDebrisEvent { doc /* STS-45 SSME 3 main engine closeout blanket sacrificial pa */ :>> flight = "STS-45"; :>> phase = "ascent"; :>> causeCategory = "オービタ自身"; :>> blockCode = "TPS"; :>> ruleId = "O"; }
    part <'DME-043'> dme_043 : TpsDebrisEvent { doc /* STS-45 two impact damage sites (gouges); cause and time o */ :>> flight = "STS-45"; :>> phase = ""; :>> causeCategory = "その他・原因の記載なし"; :>> blockCode = ""; :>> ruleId = "U"; }
    part <'DME-044'> dme_044 : TpsDebrisEvent { doc /* STS-49 impact by a low-density material such as ET TPS fo */ :>> flight = "STS-49"; :>> phase = ""; :>> causeCategory = "ET・臍帯部起因"; :>> blockCode = "ET"; :>> ruleId = "E"; }
    part <'DME-045'> dme_045 : TpsDebrisEvent { doc /* STS-49 impact (reported by the crew, photographed) */ :>> flight = "STS-49"; :>> phase = "on-orbit"; :>> causeCategory = "その他・原因の記載なし"; :>> blockCode = ""; :>> ruleId = "U"; }
    part <'DME-046'> dme_046 : TpsDebrisEvent { doc /* STS-49 RTV material used to bond paper covers to the forw */ :>> flight = "STS-49"; :>> phase = ""; :>> causeCategory = "オービタ自身"; :>> blockCode = "RCS"; :>> ruleId = "X"; }
    part <'DME-047'> dme_047 : TpsDebrisEvent { doc /* STS-50 ice and TPS debris shed from random sources */ :>> flight = "STS-50"; :>> phase = "ascent"; :>> causeCategory = "ET・臍帯部起因"; :>> blockCode = "ET"; :>> ruleId = "E"; }
    part <'DME-048'> dme_048 : TpsDebrisEvent { doc /* STS-50 orbital impact */ :>> flight = "STS-50"; :>> phase = "on-orbit"; :>> causeCategory = "軌道上（MMOD）"; :>> blockCode = "STR"; :>> ruleId = "M"; }
    part <'DME-049'> dme_049 : TpsDebrisEvent { doc /* STS-50 impact site (projectile material to be determined  */ :>> flight = "STS-50"; :>> phase = "on-orbit"; :>> causeCategory = "その他・原因の記載なし"; :>> blockCode = ""; :>> ruleId = "U"; }
    part <'DME-050'> dme_050 : TpsDebrisEvent { doc /* STS-46 ice and debris shed from the LH2 umbilical */ :>> flight = "STS-46"; :>> phase = "ascent"; :>> causeCategory = "ET・臍帯部起因"; :>> blockCode = "ET"; :>> ruleId = "E"; }
    part <'DME-051'> dme_051 : TpsDebrisEvent { doc /* STS-46 impact (cause not stated) */ :>> flight = "STS-46"; :>> phase = ""; :>> causeCategory = "その他・原因の記載なし"; :>> blockCode = ""; :>> ruleId = "U"; }
    part <'DME-052'> dme_052 : TpsDebrisEvent { doc /* STS-46 RTV used to bond the paper covers to the forward R */ :>> flight = "STS-46"; :>> phase = ""; :>> causeCategory = "オービタ自身"; :>> blockCode = "RCS"; :>> ruleId = "X"; }
    part <'DME-053'> dme_053 : TpsDebrisEvent { doc /* STS-47 ice and TPS debris from random sources (no single  */ :>> flight = "STS-47"; :>> phase = "ascent"; :>> causeCategory = "その他・原因の記載なし"; :>> blockCode = ""; :>> ruleId = "X"; }
    part <'DME-054'> dme_054 : TpsDebrisEvent { doc /* STS-52 ice and TPS debris from random sources (no single  */ :>> flight = "STS-52"; :>> phase = "ascent"; :>> causeCategory = "その他・原因の記載なし"; :>> blockCode = ""; :>> ruleId = "X"; }
    part <'DME-055'> dme_055 : TpsDebrisEvent { doc /* STS-52 dense object, possibly the lost base heat shield t */ :>> flight = "STS-52"; :>> phase = ""; :>> causeCategory = "オービタ自身"; :>> blockCode = "TPS"; :>> ruleId = "O"; }
    part <'DME-056'> dme_056 : TpsDebrisEvent { doc /* STS-52 RTV used to bond paper covers to the forward RCS t */ :>> flight = "STS-52"; :>> phase = ""; :>> causeCategory = "オービタ自身"; :>> blockCode = "RCS"; :>> ruleId = "X"; }
    part <'DME-057'> dme_057 : TpsDebrisEvent { doc /* STS-53 ice from the LO2 feedline */ :>> flight = "STS-53"; :>> phase = ""; :>> causeCategory = "ET・臍帯部起因"; :>> blockCode = "ET"; :>> ruleId = "E"; }
    part <'DME-058'> dme_058 : TpsDebrisEvent { doc /* STS-53 ice/debris impacts at ET separation */ :>> flight = "STS-53"; :>> phase = ""; :>> causeCategory = "ET・臍帯部起因"; :>> blockCode = "ET"; :>> ruleId = "E"; }
    part <'DME-059'> dme_059 : TpsDebrisEvent { doc /* STS-53 Orbiter tile material (foreign material found in t */ :>> flight = "STS-53"; :>> phase = ""; :>> causeCategory = "オービタ自身"; :>> blockCode = "TPS"; :>> ruleId = "O"; }
    part <'DME-060'> dme_060 : TpsDebrisEvent { doc /* STS-53 RTV used to bond paper covers to the forward RCS e */ :>> flight = "STS-53"; :>> phase = ""; :>> causeCategory = "オービタ自身"; :>> blockCode = "RCS"; :>> ruleId = "X"; }
    part <'DME-061'> dme_061 : TpsDebrisEvent { doc /* STS-54 ice and TPS debris from random sources */ :>> flight = "STS-54"; :>> phase = "ascent"; :>> causeCategory = "その他・原因の記載なし"; :>> blockCode = ""; :>> ruleId = "X"; }
    part <'DME-062'> dme_062 : TpsDebrisEvent { doc /* STS-56 impact by low-density material, such as ET insulat */ :>> flight = "STS-56"; :>> phase = ""; :>> causeCategory = "ET・臍帯部起因"; :>> blockCode = "ET"; :>> ruleId = "E"; }
    part <'DME-063'> dme_063 : TpsDebrisEvent { doc /* STS-51 debris hits */ :>> flight = "STS-51"; :>> phase = ""; :>> causeCategory = "その他・原因の記載なし"; :>> blockCode = ""; :>> ruleId = "U"; }
    part <'DME-064'> dme_064 : TpsDebrisEvent { doc /* STS-51 higher density materials, such as ice */ :>> flight = "STS-51"; :>> phase = "ascent"; :>> causeCategory = "ET・臍帯部起因"; :>> blockCode = "ET"; :>> ruleId = "E"; }
    part <'DME-065'> dme_065 : TpsDebrisEvent { doc /* STS-58 single white piece of debris, probably a piece of  */ :>> flight = "STS-58"; :>> phase = "ascent"; :>> causeCategory = "オービタ自身"; :>> blockCode = "TPS"; :>> ruleId = "O"; }
    part <'DME-066'> dme_066 : TpsDebrisEvent { doc /* STS-61 ice and TPS debris from random sources (no single  */ :>> flight = "STS-61"; :>> phase = "ascent"; :>> causeCategory = "その他・原因の記載なし"; :>> blockCode = ""; :>> ruleId = "X"; }
    part <'DME-067'> dme_067 : TpsDebrisEvent { doc /* STS-61 impacts from higher density materials such as ice  */ :>> flight = "STS-61"; :>> phase = ""; :>> causeCategory = "ET・臍帯部起因"; :>> blockCode = "ET"; :>> ruleId = "E"; }
    part <'DME-068'> dme_068 : TpsDebrisEvent { doc /* STS-60 ice and TPS debris from random sources (no single  */ :>> flight = "STS-60"; :>> phase = "ascent"; :>> causeCategory = "その他・原因の記載なし"; :>> blockCode = ""; :>> ruleId = "X"; }
    part <'DME-069'> dme_069 : TpsDebrisEvent { doc /* STS-62 four distinct impacts (enlarged by erosion during  */ :>> flight = "STS-62"; :>> phase = "entry"; :>> causeCategory = "その他・原因の記載なし"; :>> blockCode = ""; :>> ruleId = "U"; }
    part <'DME-070'> dme_070 : TpsDebrisEvent { doc /* STS-62 debris hits (source to be determined by lab analys */ :>> flight = "STS-62"; :>> phase = ""; :>> causeCategory = "その他・原因の記載なし"; :>> blockCode = ""; :>> ruleId = "U"; }
    part <'DME-071'> dme_071 : TpsDebrisEvent { doc /* STS-59 apparent micrometeorite impact */ :>> flight = "STS-59"; :>> phase = "on-orbit"; :>> causeCategory = "軌道上（MMOD）"; :>> blockCode = "STR"; :>> ruleId = "M"; }
    part <'DME-072'> dme_072 : TpsDebrisEvent { doc /* STS-59 impact crater (0.029 in by 0.023 in by 0.0019 in d */ :>> flight = "STS-59"; :>> phase = "on-orbit"; :>> causeCategory = "その他・原因の記載なし"; :>> blockCode = ""; :>> ruleId = "U"; }
    part <'DME-073'> dme_073 : TpsDebrisEvent { doc /* STS-68 debris (streamers seen at about 36 seconds, Mach 0 */ :>> flight = "STS-68"; :>> phase = "ascent"; :>> causeCategory = "その他・原因の記載なし"; :>> blockCode = ""; :>> ruleId = "U"; }
    part <'DME-074'> dme_074 : TpsDebrisEvent { doc /* STS-68 embedded debris (removed for analysis at KSC to de */ :>> flight = "STS-68"; :>> phase = ""; :>> causeCategory = "その他・原因の記載なし"; :>> blockCode = ""; :>> ruleId = "U"; }
    part <'DME-075'> dme_075 : TpsDebrisEvent { doc /* STS-68 forward RCS thruster covers (butcher paper) */ :>> flight = "STS-68"; :>> phase = "ascent"; :>> causeCategory = "オービタ自身"; :>> blockCode = "RCS"; :>> ruleId = "O"; }
    part <'DME-076'> dme_076 : TpsDebrisEvent { doc /* STS-68 tile lost from around window 8 (crew reported tile */ :>> flight = "STS-68"; :>> phase = ""; :>> causeCategory = "オービタ自身"; :>> blockCode = "TPS"; :>> ruleId = "O"; }
    part <'DME-077'> dme_077 : TpsDebrisEvent { doc /* STS-66 icicle formed during a waste water dump (break-up  */ :>> flight = "STS-66"; :>> phase = ""; :>> causeCategory = "その他・原因の記載なし"; :>> blockCode = ""; :>> ruleId = "U"; }
    part <'DME-078'> dme_078 : TpsDebrisEvent { doc /* STS-66 forward RCS paper covers and/or paper-cover RTV ad */ :>> flight = "STS-66"; :>> phase = ""; :>> causeCategory = "オービタ自身"; :>> blockCode = "RCS"; :>> ruleId = "O"; }
    part <'DME-079'> dme_079 : TpsDebrisEvent { doc /* STS-63 RTV material from the main landing gear (may have  */ :>> flight = "STS-63"; :>> phase = ""; :>> causeCategory = "オービタ自身"; :>> blockCode = "TPS"; :>> ruleId = "X"; }
    part <'DME-080'> dme_080 : TpsDebrisEvent { doc /* STS-63 ice (believed) */ :>> flight = "STS-63"; :>> phase = ""; :>> causeCategory = "ET・臍帯部起因"; :>> blockCode = "ET"; :>> ruleId = "E"; }
    part <'DME-081'> dme_081 : TpsDebrisEvent { doc /* STS-67 one small impact (experimental toughened unipiece  */ :>> flight = "STS-67"; :>> phase = ""; :>> causeCategory = "オービタ自身"; :>> blockCode = "TPS"; :>> ruleId = "O"; }
    part <'DME-082'> dme_082 : TpsDebrisEvent { doc /* STS-67 forward RCS paper covers and/or paper-covered room */ :>> flight = "STS-67"; :>> phase = ""; :>> causeCategory = "オービタ自身"; :>> blockCode = "RCS"; :>> ruleId = "O"; }
    part <'DME-083'> dme_083 : TpsDebrisEvent { doc /* STS-67 missing corner piece of a tile (2 1/2 inches by 2  */ :>> flight = "STS-67"; :>> phase = ""; :>> causeCategory = "オービタ自身"; :>> blockCode = "TPS"; :>> ruleId = "O"; }
    part <'DME-084'> dme_084 : TpsDebrisEvent { doc /* STS-71 umbilical ice (believed) */ :>> flight = "STS-71"; :>> phase = ""; :>> causeCategory = "ET・臍帯部起因"; :>> blockCode = "ET"; :>> ruleId = "E"; }
    part <'DME-085'> dme_085 : TpsDebrisEvent { doc /* STS-69 ice and shredded pieces of umbilical purge barrier */ :>> flight = "STS-69"; :>> phase = "ascent"; :>> causeCategory = "ET・臍帯部起因"; :>> blockCode = "ET"; :>> ruleId = "E"; }
    part <'DME-086'> dme_086 : TpsDebrisEvent { doc /* STS-69 ice impacts from the ET liquid oxygen feedline bel */ :>> flight = "STS-69"; :>> phase = "ascent"; :>> causeCategory = "ET・臍帯部起因"; :>> blockCode = "ET"; :>> ruleId = "E"; }
    part <'DME-087'> dme_087 : TpsDebrisEvent { doc /* STS-69 forward RCS paper cover pieces or room temperature */ :>> flight = "STS-69"; :>> phase = "ascent"; :>> causeCategory = "オービタ自身"; :>> blockCode = "RCS"; :>> ruleId = "O"; }
    part <'DME-088'> dme_088 : TpsDebrisEvent { doc /* STS-73 impact crater (source not stated) */ :>> flight = "STS-73"; :>> phase = "on-orbit"; :>> causeCategory = "その他・原因の記載なし"; :>> blockCode = ""; :>> ruleId = "U"; }
    part <'DME-089'> dme_089 : TpsDebrisEvent { doc /* STS-73 ice from the ET liquid oxygen feed-line bellows an */ :>> flight = "STS-73"; :>> phase = ""; :>> causeCategory = "ET・臍帯部起因"; :>> blockCode = "ET"; :>> ruleId = "E"; }
    part <'DME-090'> dme_090 : TpsDebrisEvent { doc /* STS-73 umbilical ice or shredded pieces of umbilical purg */ :>> flight = "STS-73"; :>> phase = ""; :>> causeCategory = "ET・臍帯部起因"; :>> blockCode = "ET"; :>> ruleId = "E"; }
    part <'DME-091'> dme_091 : TpsDebrisEvent { doc /* STS-73 forward RCS paper cover pieces and RTV */ :>> flight = "STS-73"; :>> phase = ""; :>> causeCategory = "オービタ自身"; :>> blockCode = "RCS"; :>> ruleId = "O"; }
    part <'DME-092'> dme_092 : TpsDebrisEvent { doc /* STS-73 micrometeorite or on-orbit debris impact (possible */ :>> flight = "STS-73"; :>> phase = "on-orbit"; :>> causeCategory = "軌道上（MMOD）"; :>> blockCode = "TPS"; :>> ruleId = "M"; }
    part <'DME-093'> dme_093 : TpsDebrisEvent { doc /* STS-74 ice from the ET liquid oxygen feed-line bellows an */ :>> flight = "STS-74"; :>> phase = ""; :>> causeCategory = "ET・臍帯部起因"; :>> blockCode = "ET"; :>> ruleId = "E"; }
    part <'DME-094'> dme_094 : TpsDebrisEvent { doc /* STS-74 umbilical ice or shredded pieces of umbilical purg */ :>> flight = "STS-74"; :>> phase = ""; :>> causeCategory = "ET・臍帯部起因"; :>> blockCode = "ET"; :>> ruleId = "E"; }
    part <'DME-095'> dme_095 : TpsDebrisEvent { doc /* STS-74 forward RCS paper cover pieces and room temperatur */ :>> flight = "STS-74"; :>> phase = ""; :>> causeCategory = "オービタ自身"; :>> blockCode = "RCS"; :>> ruleId = "O"; }
    part <'DME-096'> dme_096 : TpsDebrisEvent { doc /* STS-72 ice impacts from the ET LO2 feedline bellows and s */ :>> flight = "STS-72"; :>> phase = "ascent"; :>> causeCategory = "ET・臍帯部起因"; :>> blockCode = "ET"; :>> ruleId = "E"; }
    part <'DME-097'> dme_097 : TpsDebrisEvent { doc /* STS-72 forward RCS thruster paper covers and RTV adhesive */ :>> flight = "STS-72"; :>> phase = ""; :>> causeCategory = "オービタ自身"; :>> blockCode = "RCS"; :>> ruleId = "O"; }
    part <'DME-098'> dme_098 : TpsDebrisEvent { doc /* STS-75 umbilical ice or shredded pieces of umbilical purg */ :>> flight = "STS-75"; :>> phase = "ascent"; :>> causeCategory = "ET・臍帯部起因"; :>> blockCode = "ET"; :>> ruleId = "E"; }
    part <'DME-099'> dme_099 : TpsDebrisEvent { doc /* STS-75 forward RCS thruster paper cover/adhesive (and old */ :>> flight = "STS-75"; :>> phase = "ascent"; :>> causeCategory = "オービタ自身"; :>> blockCode = "RCS"; :>> ruleId = "O"; }
    part <'DME-100'> dme_100 : TpsDebrisEvent { doc /* STS-76 umbilical purge barrier torn away and released muc */ :>> flight = "STS-76"; :>> phase = "ascent"; :>> causeCategory = "ET・臍帯部起因"; :>> blockCode = "ET"; :>> ruleId = "E"; }
    part <'DME-101'> dme_101 : TpsDebrisEvent { doc /* STS-76 impacts by RCS paper cover/room temperature vulcan */ :>> flight = "STS-76"; :>> phase = "ascent"; :>> causeCategory = "オービタ自身"; :>> blockCode = "RCS"; :>> ruleId = "O"; }
    part <'DME-102'> dme_102 : TpsDebrisEvent { doc /* STS-77 ice from the ET LO2 feed-line bellows and support  */ :>> flight = "STS-77"; :>> phase = "ascent"; :>> causeCategory = "ET・臍帯部起因"; :>> blockCode = "ET"; :>> ruleId = "E"; }
    part <'DME-103'> dme_103 : TpsDebrisEvent { doc /* STS-77 possible divots on the intertank foam (on-orbit ET */ :>> flight = "STS-77"; :>> phase = "ascent"; :>> causeCategory = "ET・臍帯部起因"; :>> blockCode = "ET"; :>> ruleId = "X"; }
    part <'DME-104'> dme_104 : TpsDebrisEvent { doc /* STS-78 impact of ice from the umbilicals */ :>> flight = "STS-78"; :>> phase = "ascent"; :>> causeCategory = "ET・臍帯部起因"; :>> blockCode = "ET"; :>> ruleId = "E"; }
    part <'DME-105'> dme_105 : TpsDebrisEvent { doc /* STS-78 debris impact due to exhaust plume recirculation ( */ :>> flight = "STS-78"; :>> phase = "ascent"; :>> causeCategory = "その他・原因の記載なし"; :>> blockCode = ""; :>> ruleId = "U"; }
    part <'DME-106'> dme_106 : TpsDebrisEvent { doc /* STS-78 old repair material flaking off */ :>> flight = "STS-78"; :>> phase = ""; :>> causeCategory = "オービタ自身"; :>> blockCode = "TPS"; :>> ruleId = "O"; }
    part <'DME-107'> dme_107 : TpsDebrisEvent { doc /* STS-80 ice impact from the umbilical */ :>> flight = "STS-80"; :>> phase = "ascent"; :>> causeCategory = "ET・臍帯部起因"; :>> blockCode = "ET"; :>> ruleId = "E"; }
    part <'DME-108'> dme_108 : TpsDebrisEvent { doc /* STS-80 forward RCS thruster paper covers / RTV adhesive */ :>> flight = "STS-80"; :>> phase = "ascent"; :>> causeCategory = "オービタ自身"; :>> blockCode = "RCS"; :>> ruleId = "O"; }
    part <'DME-109'> dme_109 : TpsDebrisEvent { doc /* STS-80 micrometeoroids (possible) */ :>> flight = "STS-80"; :>> phase = "on-orbit"; :>> causeCategory = "軌道上（MMOD）"; :>> blockCode = "STR"; :>> ruleId = "M"; }
    part <'DME-110'> dme_110 : TpsDebrisEvent { doc /* STS-81 probable impact of ice */ :>> flight = "STS-81"; :>> phase = ""; :>> causeCategory = "ET・臍帯部起因"; :>> blockCode = "ET"; :>> ruleId = "E"; }
    part <'DME-111'> dme_111 : TpsDebrisEvent { doc /* STS-82 umbilical ice or shredded pieces of umbilical purg */ :>> flight = "STS-82"; :>> phase = "ascent"; :>> causeCategory = "ET・臍帯部起因"; :>> blockCode = "ET"; :>> ruleId = "E"; }
    part <'DME-112'> dme_112 : TpsDebrisEvent { doc /* STS-82 forward RCS thruster paper covers/RTV adhesive (be */ :>> flight = "STS-82"; :>> phase = ""; :>> causeCategory = "オービタ自身"; :>> blockCode = "RCS"; :>> ruleId = "O"; }
    part <'DME-113'> dme_113 : TpsDebrisEvent { doc /* STS-82 launch debris impact (rather than contact from the */ :>> flight = "STS-82"; :>> phase = "ascent"; :>> causeCategory = "その他・原因の記載なし"; :>> blockCode = ""; :>> ruleId = "U"; }
    part <'DME-114'> dme_114 : TpsDebrisEvent { doc /* STS-83 umbilical ice or shredded pieces of umbilical purg */ :>> flight = "STS-83"; :>> phase = "ascent"; :>> causeCategory = "ET・臍帯部起因"; :>> blockCode = "ET"; :>> ruleId = "E"; }
    part <'DME-115'> dme_115 : TpsDebrisEvent { doc /* STS-83 excessive RTV material used to attach paper covers */ :>> flight = "STS-83"; :>> phase = "ascent"; :>> causeCategory = "オービタ自身"; :>> blockCode = "RCS"; :>> ruleId = "O"; }
    part <'DME-116'> dme_116 : TpsDebrisEvent { doc /* STS-84 umbilical ice or shredded pieces of umbilical purg */ :>> flight = "STS-84"; :>> phase = "ascent"; :>> causeCategory = "ET・臍帯部起因"; :>> blockCode = "ET"; :>> ruleId = "E"; }
    part <'DME-117'> dme_117 : TpsDebrisEvent { doc /* STS-84 impacts from excessive RTV adhesive used in attach */ :>> flight = "STS-84"; :>> phase = ""; :>> causeCategory = "オービタ自身"; :>> blockCode = "RCS"; :>> ruleId = "O"; }
    part <'DME-118'> dme_118 : TpsDebrisEvent { doc /* STS-85 impacts from excessive RTV adhesive used in attach */ :>> flight = "STS-85"; :>> phase = ""; :>> causeCategory = "オービタ自身"; :>> blockCode = "RCS"; :>> ruleId = "O"; }
    part <'DME-119'> dme_119 : TpsDebrisEvent { doc /* STS-86 cause not determined (umbilical films gave no usef */ :>> flight = "STS-86"; :>> phase = "ascent"; :>> causeCategory = "その他・原因の記載なし"; :>> blockCode = ""; :>> ruleId = "U"; }
    part <'DME-120'> dme_120 : TpsDebrisEvent { doc /* STS-86 micrometeorite or on-orbit debris impact */ :>> flight = "STS-86"; :>> phase = ""; :>> causeCategory = "軌道上（MMOD）"; :>> blockCode = "TPS"; :>> ruleId = "M"; }
    part <'DME-121'> dme_121 : TpsDebrisEvent { doc /* STS-86 piece of a forward RCS thruster-paper cover */ :>> flight = "STS-86"; :>> phase = ""; :>> causeCategory = "オービタ自身"; :>> blockCode = "RCS"; :>> ruleId = "O"; }
    part <'DME-122'> dme_122 : TpsDebrisEvent { doc /* STS-87 flex-line hose section of the GSE GN2 purge line a */ :>> flight = "STS-87"; :>> phase = "ascent"; :>> causeCategory = "地上・発射台"; :>> blockCode = ""; :>> ruleId = "X"; }
    part <'DME-123'> dme_123 : TpsDebrisEvent { doc /* STS-87 TPS loss from the intertank area of the ET (suspec */ :>> flight = "STS-87"; :>> phase = "ascent"; :>> causeCategory = "ET・臍帯部起因"; :>> blockCode = "ET"; :>> ruleId = "E"; }
    part <'DME-124'> dme_124 : TpsDebrisEvent { doc /* STS-89 umbilical ice or shredded pieces of umbilical purg */ :>> flight = "STS-89"; :>> phase = "ascent"; :>> causeCategory = "ET・臍帯部起因"; :>> blockCode = "ET"; :>> ruleId = "E"; }
    part <'DME-125'> dme_125 : TpsDebrisEvent { doc /* STS-89 light-colored pieces of debris (insulation and fro */ :>> flight = "STS-89"; :>> phase = "ascent"; :>> causeCategory = "その他・原因の記載なし"; :>> blockCode = ""; :>> ruleId = "U"; }
    part <'DME-126'> dme_126 : TpsDebrisEvent { doc /* STS-95 umbilical ice or shredded pieces of umbilical purg */ :>> flight = "STS-95"; :>> phase = "ascent"; :>> causeCategory = "ET・臍帯部起因"; :>> blockCode = "ET"; :>> ruleId = "E"; }
    part <'DME-127'> dme_127 : TpsDebrisEvent { doc /* STS-95 small pieces of rubber released from the nose land */ :>> flight = "STS-95"; :>> phase = "entry"; :>> causeCategory = "オービタ自身"; :>> blockCode = "TPS"; :>> ruleId = "O"; }
    part <'DME-128'> dme_128 : TpsDebrisEvent { doc /* STS-88 umbilical ice or shredded pieces of umbilical purg */ :>> flight = "STS-88"; :>> phase = ""; :>> causeCategory = "ET・臍帯部起因"; :>> blockCode = "ET"; :>> ruleId = "E"; }
    part <'DME-129'> dme_129 : TpsDebrisEvent { doc /* STS-96 ice impacts from the overboard dump valves (on the */ :>> flight = "STS-96"; :>> phase = "ascent"; :>> causeCategory = "オービタ自身"; :>> blockCode = "TPS"; :>> ruleId = "X"; }
    part <'DME-130'> dme_130 : TpsDebrisEvent { doc /* STS-103 impact (source not identified; pink and yellow dis */ :>> flight = "STS-103"; :>> phase = ""; :>> causeCategory = "その他・原因の記載なし"; :>> blockCode = ""; :>> ruleId = "U"; }
    part <'DME-131'> dme_131 : TpsDebrisEvent { doc /* STS-103 shredded pieces of umbilical purge barrier materia */ :>> flight = "STS-103"; :>> phase = "ascent"; :>> causeCategory = "ET・臍帯部起因"; :>> blockCode = "ET"; :>> ruleId = "E"; }
    part <'DME-132'> dme_132 : TpsDebrisEvent { doc /* STS-103 forward RCS thruster paper covers and RTV adhesive */ :>> flight = "STS-103"; :>> phase = ""; :>> causeCategory = "オービタ自身"; :>> blockCode = "RCS"; :>> ruleId = "O"; }
    part <'DME-133'> dme_133 : TpsDebrisEvent { doc /* STS-103 launch debris impact */ :>> flight = "STS-103"; :>> phase = "ascent"; :>> causeCategory = "その他・原因の記載なし"; :>> blockCode = ""; :>> ruleId = "U"; }
    part <'DME-134'> dme_134 : TpsDebrisEvent { doc /* STS-99 impacts from forward RCS thruster paper covers and */ :>> flight = "STS-99"; :>> phase = ""; :>> causeCategory = "オービタ自身"; :>> blockCode = "RCS"; :>> ruleId = "O"; }
    part <'DME-135'> dme_135 : TpsDebrisEvent { doc /* STS-99 metal clip (flow restrictor, part of the seal on t */ :>> flight = "STS-99"; :>> phase = "postlanding"; :>> causeCategory = "オービタ自身"; :>> blockCode = "TPS"; :>> ruleId = "O"; }
    part <'DME-136'> dme_136 : TpsDebrisEvent { doc /* STS-101 ice from the ET LO2 feedline bellows (may have bee */ :>> flight = "STS-101"; :>> phase = "ascent"; :>> causeCategory = "ET・臍帯部起因"; :>> blockCode = "ET"; :>> ruleId = "E"; }
    part <'DME-137'> dme_137 : TpsDebrisEvent { doc /* STS-101 loss of foam from the ET thrust panels */ :>> flight = "STS-101"; :>> phase = ""; :>> causeCategory = "ET・臍帯部起因"; :>> blockCode = "ET"; :>> ruleId = "E"; }
    part <'DME-138'> dme_138 : TpsDebrisEvent { doc /* STS-101 umbilical ice or shredded pieces of umbilical purg */ :>> flight = "STS-101"; :>> phase = ""; :>> causeCategory = "ET・臍帯部起因"; :>> blockCode = "ET"; :>> ruleId = "E"; }
    part <'DME-139'> dme_139 : TpsDebrisEvent { doc /* STS-106 loss of foam from the ET thrust panels */ :>> flight = "STS-106"; :>> phase = ""; :>> causeCategory = "ET・臍帯部起因"; :>> blockCode = "ET"; :>> ruleId = "E"; }
    part <'DME-140'> dme_140 : TpsDebrisEvent { doc /* STS-106 ice on the LO2 feedline bellows (some of the hits  */ :>> flight = "STS-106"; :>> phase = ""; :>> causeCategory = "ET・臍帯部起因"; :>> blockCode = "ET"; :>> ruleId = "E"; }
    part <'DME-141'> dme_141 : TpsDebrisEvent { doc /* STS-106 umbilical ice or pieces of the umbilical purge bar */ :>> flight = "STS-106"; :>> phase = ""; :>> causeCategory = "ET・臍帯部起因"; :>> blockCode = "ET"; :>> ruleId = "E"; }
    part <'DME-142'> dme_142 : TpsDebrisEvent { doc /* STS-92 ice from the ET LO2 feedline */ :>> flight = "STS-92"; :>> phase = "ascent"; :>> causeCategory = "ET・臍帯部起因"; :>> blockCode = "ET"; :>> ruleId = "E"; }
    part <'DME-143'> dme_143 : TpsDebrisEvent { doc /* STS-92 pieces of the umbilical purge barrier material fla */ :>> flight = "STS-92"; :>> phase = "ascent"; :>> causeCategory = "ET・臍帯部起因"; :>> blockCode = "ET"; :>> ruleId = "E"; }
    part <'DME-144'> dme_144 : TpsDebrisEvent { doc /* STS-97 pieces of the umbilical purge barrier flailing in  */ :>> flight = "STS-97"; :>> phase = "ascent"; :>> causeCategory = "ET・臍帯部起因"; :>> blockCode = "ET"; :>> ruleId = "E"; }
    part <'DME-145'> dme_145 : TpsDebrisEvent { doc /* STS-98 forward RCS paper covers with RTV adhesive on the  */ :>> flight = "STS-98"; :>> phase = ""; :>> causeCategory = "オービタ自身"; :>> blockCode = "RCS"; :>> ruleId = "O"; }
    part <'DME-146'> dme_146 : TpsDebrisEvent { doc /* STS-98 light-colored debris (at least five or six pieces) */ :>> flight = "STS-98"; :>> phase = "ascent"; :>> causeCategory = "その他・原因の記載なし"; :>> blockCode = ""; :>> ruleId = "U"; }
    part <'DME-147'> dme_147 : TpsDebrisEvent { doc /* STS-98 two pieces of debris, 3.4 s before SRB separation */ :>> flight = "STS-98"; :>> phase = "ascent"; :>> causeCategory = "その他・原因の記載なし"; :>> blockCode = ""; :>> ruleId = "U"; }
    part <'DME-148'> dme_148 : TpsDebrisEvent { doc /* STS-102 pieces of the umbilical purge barrier */ :>> flight = "STS-102"; :>> phase = "ascent"; :>> causeCategory = "ET・臍帯部起因"; :>> blockCode = "ET"; :>> ruleId = "E"; }
    part <'DME-149'> dme_149 : TpsDebrisEvent { doc /* STS-100 ice/frost from the LO2 feedline or foam debris */ :>> flight = "STS-100"; :>> phase = "ascent"; :>> causeCategory = "ET・臍帯部起因"; :>> blockCode = "ET"; :>> ruleId = "E"; }
    part <'DME-150'> dme_150 : TpsDebrisEvent { doc /* STS-100 impact of low-density foam material */ :>> flight = "STS-100"; :>> phase = "ascent"; :>> causeCategory = "ET・臍帯部起因"; :>> blockCode = "ET"; :>> ruleId = "E"; }
    part <'DME-151'> dme_151 : TpsDebrisEvent { doc /* STS-100 impacts by RTV adhesive used on the forward RCS pa */ :>> flight = "STS-100"; :>> phase = "ascent"; :>> causeCategory = "オービタ自身"; :>> blockCode = "RCS"; :>> ruleId = "O"; }
    part <'DME-152'> dme_152 : TpsDebrisEvent { doc /* STS-104 ice/frost from the LO2 feedline or foam debris */ :>> flight = "STS-104"; :>> phase = "ascent"; :>> causeCategory = "ET・臍帯部起因"; :>> blockCode = "ET"; :>> ruleId = "E"; }
    part <'DME-153'> dme_153 : TpsDebrisEvent { doc /* STS-105 ET foam loss (pattern and size ratio of the sites) */ :>> flight = "STS-105"; :>> phase = "ascent"; :>> causeCategory = "ET・臍帯部起因"; :>> blockCode = "ET"; :>> ruleId = "E"; }
    part <'DME-154'> dme_154 : TpsDebrisEvent { doc /* STS-105 pieces of the umbilical purge barrier flailing in  */ :>> flight = "STS-105"; :>> phase = "ascent"; :>> causeCategory = "ET・臍帯部起因"; :>> blockCode = "ET"; :>> ruleId = "E"; }
    part <'DME-155'> dme_155 : TpsDebrisEvent { doc /* STS-108 pieces of the umbilical purge barrier flailing in  */ :>> flight = "STS-108"; :>> phase = "ascent"; :>> causeCategory = "ET・臍帯部起因"; :>> blockCode = "ET"; :>> ruleId = "E"; }
    part <'DME-156'> dme_156 : TpsDebrisEvent { doc /* STS-109 pieces of the umbilical purge barrier */ :>> flight = "STS-109"; :>> phase = "ascent"; :>> causeCategory = "ET・臍帯部起因"; :>> blockCode = "ET"; :>> ruleId = "E"; }
    part <'DME-157'> dme_157 : TpsDebrisEvent { doc /* STS-110 pieces of the umbilical purge barrier flailing in  */ :>> flight = "STS-110"; :>> phase = "ascent"; :>> causeCategory = "ET・臍帯部起因"; :>> blockCode = "ET"; :>> ruleId = "E"; }
    part <'DME-158'> dme_158 : TpsDebrisEvent { doc /* STS-111 pieces of the umbilical purge barrier flailing in  */ :>> flight = "STS-111"; :>> phase = "ascent"; :>> causeCategory = "ET・臍帯部起因"; :>> blockCode = "ET"; :>> ruleId = "E"; }
    part <'DME-159'> dme_159 : TpsDebrisEvent { doc /* STS-111 same source (not identified) */ :>> flight = "STS-111"; :>> phase = ""; :>> causeCategory = "その他・原因の記載なし"; :>> blockCode = ""; :>> ruleId = "U"; }
    part <'DME-160'> dme_160 : TpsDebrisEvent { doc /* STS-111 forward RCS paper covers with RTV adhesive on the  */ :>> flight = "STS-111"; :>> phase = ""; :>> causeCategory = "オービタ自身"; :>> blockCode = "RCS"; :>> ruleId = "O"; }
    part <'DME-161'> dme_161 : TpsDebrisEvent { doc /* STS-111 debris (source not stated) */ :>> flight = "STS-111"; :>> phase = ""; :>> causeCategory = "その他・原因の記載なし"; :>> blockCode = ""; :>> ruleId = "U"; }
    part <'DME-162'> dme_162 : TpsDebrisEvent { doc /* STS-112 pieces of the umbilical purge barrier */ :>> flight = "STS-112"; :>> phase = "ascent"; :>> causeCategory = "ET・臍帯部起因"; :>> blockCode = "ET"; :>> ruleId = "E"; }
    part <'DME-163'> dme_163 : TpsDebrisEvent { doc /* STS-112 forward RCS paper covers with RTV adhesive on the  */ :>> flight = "STS-112"; :>> phase = "ascent"; :>> causeCategory = "オービタ自身"; :>> blockCode = "RCS"; :>> ruleId = "O"; }
    part <'DME-164'> dme_164 : TpsDebrisEvent { doc /* STS-113 ET foam (shallow damage sites) */ :>> flight = "STS-113"; :>> phase = "ascent"; :>> causeCategory = "ET・臍帯部起因"; :>> blockCode = "ET"; :>> ruleId = "E"; }
    part <'DME-165'> dme_165 : TpsDebrisEvent { doc /* STS-113 forward RCS paper covers with room temperature vul */ :>> flight = "STS-113"; :>> phase = "ascent"; :>> causeCategory = "オービタ自身"; :>> blockCode = "RCS"; :>> ruleId = "O"; }
    part <'DME-166'> dme_166 : TpsDebrisEvent { doc /* STS-107 large light-colored piece of debris (ET foam) from */ :>> flight = "STS-107"; :>> phase = "ascent"; :>> causeCategory = "ET・臍帯部起因"; :>> blockCode = "ET"; :>> ruleId = "E"; }
    part <'DME-167'> dme_167 : TpsDebrisEvent { doc /* STS-33 acoustical environment during ascent (probable cau */ :>> flight = "STS-33"; :>> phase = "ascent"; :>> causeCategory = "その他・原因の記載なし"; :>> blockCode = ""; :>> ruleId = "U"; }
    part <'DME-168'> dme_168 : TpsDebrisEvent { doc /* STS-64 right-hand main landing gear door thermal barrier  */ :>> flight = "STS-64"; :>> phase = "landing"; :>> causeCategory = "オービタ自身"; :>> blockCode = "TPS"; :>> ruleId = "O"; }
    part <'DME-169'> dme_169 : TpsDebrisEvent { doc /* STS-64 debris hits (source not stated) */ :>> flight = "STS-64"; :>> phase = ""; :>> causeCategory = "その他・原因の記載なし"; :>> blockCode = ""; :>> ruleId = "U"; }
    part <'DME-170'> dme_170 : TpsDebrisEvent { doc /* STS-70 debris impact */ :>> flight = "STS-70"; :>> phase = "on-orbit"; :>> causeCategory = "その他・原因の記載なし"; :>> blockCode = ""; :>> ruleId = "U"; }
    part <'DME-171'> dme_171 : TpsDebrisEvent { doc /* STS-90 umbilical ice or shredded pieces of umbilical purg */ :>> flight = "STS-90"; :>> phase = ""; :>> causeCategory = "ET・臍帯部起因"; :>> blockCode = "ET"; :>> ruleId = "E"; }
    part <'DME-172'> dme_172 : TpsDebrisEvent { doc /* STS-90 umbilical purge barrier material or tape flapping  */ :>> flight = "STS-90"; :>> phase = ""; :>> causeCategory = "ET・臍帯部起因"; :>> blockCode = "ET"; :>> ruleId = "E"; }
    part <'DME-173'> dme_173 : TpsDebrisEvent { doc /* STS-91 loose foam thermal protection system (TPS) materia */ :>> flight = "STS-91"; :>> phase = "prelaunch"; :>> causeCategory = "ET・臍帯部起因"; :>> blockCode = "ET"; :>> ruleId = "E"; }
    part <'DME-174'> dme_174 : TpsDebrisEvent { doc /* STS-91 secondary debris impact */ :>> flight = "STS-91"; :>> phase = ""; :>> causeCategory = "その他・原因の記載なし"; :>> blockCode = ""; :>> ruleId = "U"; }
    part <'DME-175'> dme_175 : TpsDebrisEvent { doc /* STS-91 ice from the waste water dump nozzle */ :>> flight = "STS-91"; :>> phase = "ascent"; :>> causeCategory = "オービタ自身"; :>> blockCode = "TPS"; :>> ruleId = "X"; }
    part <'DME-176'> dme_176 : TpsDebrisEvent { doc /* STS-91 portion of a blanket coming loose and flailing in  */ :>> flight = "STS-91"; :>> phase = "ascent"; :>> causeCategory = "オービタ自身"; :>> blockCode = "TPS"; :>> ruleId = "O"; }
    part <'DME-177'> dme_177 : TpsDebrisEvent { doc /* STS-91 debris in the plume recirculation */ :>> flight = "STS-91"; :>> phase = ""; :>> causeCategory = "その他・原因の記載なし"; :>> blockCode = ""; :>> ruleId = "U"; }
    part <'DME-178'> dme_178 : TpsDebrisEvent { doc /* STS-94 debris impact (about 0.5 cm diameter, 1 mm deep) */ :>> flight = "STS-94"; :>> phase = "on-orbit"; :>> causeCategory = "その他・原因の記載なし"; :>> blockCode = ""; :>> ruleId = "U"; }
    part <'DME-179'> dme_179 : TpsDebrisEvent { doc /* STS-94 micrometeorite impacts (two sites) */ :>> flight = "STS-94"; :>> phase = "on-orbit"; :>> causeCategory = "軌道上（MMOD）"; :>> blockCode = "TPS"; :>> ruleId = "M"; }
    part <'DME-180'> dme_180 : TpsDebrisEvent { doc /* STS-94 low-density object, such as ET foam */ :>> flight = "STS-94"; :>> phase = "ascent"; :>> causeCategory = "ET・臍帯部起因"; :>> blockCode = "ET"; :>> ruleId = "E"; }
    part <'DME-181'> dme_181 : TpsDebrisEvent { doc /* STS-94 excessive RTV adhesive used in attaching paper cov */ :>> flight = "STS-94"; :>> phase = "ascent"; :>> causeCategory = "オービタ自身"; :>> blockCode = "RCS"; :>> ruleId = "O"; }
    part <'DME-182'> dme_182 : TpsDebrisEvent { doc /* STS-114 FRCS launch covers (Tyvek), thrusters F3D and F4D, */ :>> flight = "STS-114"; :>> phase = "ascent"; :>> causeCategory = "オービタ自身"; :>> blockCode = "RCS"; :>> ruleId = "O"; }
    part <'DME-183'> dme_183 : TpsDebrisEvent { doc /* STS-114 two potential impact sites in the ET attachment ri */ :>> flight = "STS-114"; :>> phase = "ascent"; :>> causeCategory = "ET・臍帯部起因"; :>> blockCode = "ET"; :>> ruleId = "E"; }
    part <'DME-184'> dme_184 : TpsDebrisEvent { doc /* STS-114 small piece of foam found on the runway (source no */ :>> flight = "STS-114"; :>> phase = "postlanding"; :>> causeCategory = "地上・発射台"; :>> blockCode = ""; :>> ruleId = "G"; }
    part <'DME-185'> dme_185 : TpsDebrisEvent { doc /* STS-114 LH2 PAL ramp foam loss (36.3 in by 110 in by 6.7 i */ :>> flight = "STS-114"; :>> phase = "ascent"; :>> causeCategory = "ET・臍帯部起因"; :>> blockCode = "ET"; :>> ruleId = "E"; }
    part <'DME-186'> dme_186 : TpsDebrisEvent { doc /* STS-114 minus Y bipod spindle closeout foam loss (8.4 in b */ :>> flight = "STS-114"; :>> phase = "ascent"; :>> causeCategory = "ET・臍帯部起因"; :>> blockCode = "ET"; :>> ruleId = "E"; }
    part <'DME-187'> dme_187 : TpsDebrisEvent { doc /* STS-114 LH2 acreage foam loss (4.8 in by 3.3 in by 1.0 in; */ :>> flight = "STS-114"; :>> phase = "ascent"; :>> causeCategory = "ET・臍帯部起因"; :>> blockCode = "ET"; :>> ruleId = "E"; }
    part <'DME-188'> dme_188 : TpsDebrisEvent { doc /* STS-114 LH2 ice/frost ramp foam loss at three locations (5 */ :>> flight = "STS-114"; :>> phase = "ascent"; :>> causeCategory = "ET・臍帯部起因"; :>> blockCode = "ET"; :>> ruleId = "E"; }
    part <'DME-189'> dme_189 : TpsDebrisEvent { doc /* STS-114 LH2 intertank flange foam loss (7.5x7.5x2.0 in and */ :>> flight = "STS-114"; :>> phase = "ascent"; :>> causeCategory = "ET・臍帯部起因"; :>> blockCode = "ET"; :>> ruleId = "E"; }
    part <'DME-190'> dme_190 : TpsDebrisEvent { doc /* STS-114 debris loss of thermal protection system material  */ :>> flight = "STS-114"; :>> phase = "ascent"; :>> causeCategory = "ET・臍帯部起因"; :>> blockCode = "ET"; :>> ruleId = "X"; }
    part <'DME-191'> dme_191 : TpsDebrisEvent { doc /* STS-121 ET thermal protection system (TPS) foam piece, 5 i */ :>> flight = "STS-121"; :>> phase = "prelaunch"; :>> causeCategory = "ET・臍帯部起因"; :>> blockCode = "ET"; :>> ruleId = "E"; }
    part <'DME-192'> dme_192 : TpsDebrisEvent { doc /* STS-121 hypervelocity impacts (four of 160 impacts) */ :>> flight = "STS-121"; :>> phase = ""; :>> causeCategory = "軌道上（MMOD）"; :>> blockCode = "STR"; :>> ruleId = "M"; }
    part <'DME-193'> dme_193 : TpsDebrisEvent { doc /* STS-121 Instafoam (ejected); aft-skirt foam exiting the ve */ :>> flight = "STS-121"; :>> phase = "ascent"; :>> causeCategory = "SRB・RSRM 起因"; :>> blockCode = "SRB"; :>> ruleId = "X"; }
    part <'DME-194'> dme_194 : TpsDebrisEvent { doc /* STS-115 probable ascent debris impacts (WLE impact detecti */ :>> flight = "STS-115"; :>> phase = "ascent"; :>> causeCategory = "その他・原因の記載なし"; :>> blockCode = ""; :>> ruleId = "U"; }
    part <'DME-195'> dme_195 : TpsDebrisEvent { doc /* STS-116 Flexible Reusable Surface Insulation (FRSI) plug */ :>> flight = "STS-116"; :>> phase = "postlaunch"; :>> causeCategory = "オービタ自身"; :>> blockCode = "TPS"; :>> ruleId = "O"; }
    part <'DME-196'> dme_196 : TpsDebrisEvent { doc /* STS-116 debris piece of unknown origin (BTA from the left- */ :>> flight = "STS-116"; :>> phase = "ascent"; :>> causeCategory = "SRB・RSRM 起因"; :>> blockCode = "SRB"; :>> ruleId = "S"; }
    part <'DME-197'> dme_197 : TpsDebrisEvent { doc /* STS-116 missing stiffener ring foam with heat effects (RSR */ :>> flight = "STS-116"; :>> phase = ""; :>> causeCategory = "SRB・RSRM 起因"; :>> blockCode = "SRB"; :>> ruleId = "S"; }
    part <'DME-198'> dme_198 : TpsDebrisEvent { doc /* STS-116 MMOD (valid 0.7-g trigger, probable impact detecte */ :>> flight = "STS-116"; :>> phase = "on-orbit"; :>> causeCategory = "軌道上（MMOD）"; :>> blockCode = "TPS"; :>> ruleId = "M"; }
    part <'DME-199'> dme_199 : TpsDebrisEvent { doc /* STS-117 hail */ :>> flight = "STS-117"; :>> phase = "prelaunch"; :>> causeCategory = "地上・発射台"; :>> blockCode = ""; :>> ruleId = "G"; }
    part <'DME-200'> dme_200 : TpsDebrisEvent { doc /* STS-117 thermal blanket turned up (extended upward about 4 */ :>> flight = "STS-117"; :>> phase = "on-orbit"; :>> causeCategory = "オービタ自身"; :>> blockCode = "TPS"; :>> ruleId = "O"; }
    part <'DME-201'> dme_201 : TpsDebrisEvent { doc /* STS-117 LH2 acreage foam loss (approx. 13.98 in3; may have */ :>> flight = "STS-117"; :>> phase = "ascent"; :>> causeCategory = "ET・臍帯部起因"; :>> blockCode = "ET"; :>> ruleId = "E"; }
    part <'DME-202'> dme_202 : TpsDebrisEvent { doc /* STS-117 LH2 acreage foam loss */ :>> flight = "STS-117"; :>> phase = "ascent"; :>> causeCategory = "ET・臍帯部起因"; :>> blockCode = "ET"; :>> ruleId = "E"; }
    part <'DME-203'> dme_203 : TpsDebrisEvent { doc /* STS-117 hypervelocity impacts */ :>> flight = "STS-117"; :>> phase = ""; :>> causeCategory = "軌道上（MMOD）"; :>> blockCode = "TPS"; :>> ruleId = "M"; }
    part <'DME-204'> dme_204 : TpsDebrisEvent { doc /* STS-117 piano key tile piece liberated from aft stub carri */ :>> flight = "STS-117"; :>> phase = "ascent"; :>> causeCategory = "オービタ自身"; :>> blockCode = "TPS"; :>> ruleId = "O"; }
    part <'DME-205'> dme_205 : TpsDebrisEvent { doc /* STS-117 ice/frost from the LO2 T-0 umbilical */ :>> flight = "STS-117"; :>> phase = "ascent"; :>> causeCategory = "ET・臍帯部起因"; :>> blockCode = "ET"; :>> ruleId = "E"; }
    part <'DME-206'> dme_206 : TpsDebrisEvent { doc /* STS-117 debris impact after SRB separation (debris measure */ :>> flight = "STS-117"; :>> phase = "ascent"; :>> causeCategory = "その他・原因の記載なし"; :>> blockCode = ""; :>> ruleId = "U"; }
    part <'DME-207'> dme_207 : TpsDebrisEvent { doc /* STS-117 shower of dark debris objects coming from the area */ :>> flight = "STS-117"; :>> phase = "ascent"; :>> causeCategory = "その他・原因の記載なし"; :>> blockCode = ""; :>> ruleId = "X"; }
    part <'DME-208'> dme_208 : TpsDebrisEvent { doc /* STS-118 MMOD 1/8-in impact */ :>> flight = "STS-118"; :>> phase = "on-orbit"; :>> causeCategory = "軌道上（MMOD）"; :>> blockCode = "STR"; :>> ruleId = "M"; }
    part <'DME-209'> dme_209 : TpsDebrisEvent { doc /* STS-118 probable ascent debris impacts (WLE impact detecti */ :>> flight = "STS-118"; :>> phase = "ascent"; :>> causeCategory = "その他・原因の記載なし"; :>> blockCode = ""; :>> ruleId = "U"; }
    part <'DME-210'> dme_210 : TpsDebrisEvent { doc /* STS-118 foam debris from the XT1623 LO2 feedline bracket ( */ :>> flight = "STS-118"; :>> phase = "ascent"; :>> causeCategory = "ET・臍帯部起因"; :>> blockCode = "ET"; :>> ruleId = "E"; }
    part <'DME-211'> dme_211 : TpsDebrisEvent { doc /* STS-118 a single piece of debris */ :>> flight = "STS-118"; :>> phase = "ascent"; :>> causeCategory = "その他・原因の記載なし"; :>> blockCode = ""; :>> ruleId = "U"; }
    part <'DME-212'> dme_212 : TpsDebrisEvent { doc /* STS-118 piece of ET umbilical purge material (umbilical pu */ :>> flight = "STS-118"; :>> phase = "ascent"; :>> causeCategory = "ET・臍帯部起因"; :>> blockCode = "ET"; :>> ruleId = "E"; }
    part <'DME-213'> dme_213 : TpsDebrisEvent { doc /* STS-120 clear ice with frost (4 in long by 1.5 in wide by  */ :>> flight = "STS-120"; :>> phase = "prelaunch"; :>> causeCategory = "ET・臍帯部起因"; :>> blockCode = "ET"; :>> ruleId = "E"; }
    part <'DME-214'> dme_214 : TpsDebrisEvent { doc /* STS-120 LH2 acreage foam loss at three locations */ :>> flight = "STS-120"; :>> phase = "ascent"; :>> causeCategory = "ET・臍帯部起因"; :>> blockCode = "ET"; :>> ruleId = "E"; }
    part <'DME-215'> dme_215 : TpsDebrisEvent { doc /* STS-120 foam loss at LO2 Feedline Bracket Base Closeout ad */ :>> flight = "STS-120"; :>> phase = "ascent"; :>> causeCategory = "ET・臍帯部起因"; :>> blockCode = "ET"; :>> ruleId = "E"; }
    part <'DME-216'> dme_216 : TpsDebrisEvent { doc /* STS-120 hypervelocity impacts */ :>> flight = "STS-120"; :>> phase = ""; :>> causeCategory = "軌道上（MMOD）"; :>> blockCode = "TPS"; :>> ruleId = "M"; }
    part <'DME-217'> dme_217 : TpsDebrisEvent { doc /* STS-120 potential MMOD damage (reported late in the missio */ :>> flight = "STS-120"; :>> phase = "on-orbit"; :>> causeCategory = "軌道上（MMOD）"; :>> blockCode = "TPS"; :>> ruleId = "M"; }
    part <'DME-218'> dme_218 : TpsDebrisEvent { doc /* STS-122 ET TPS loss at the LH2-to-Intertank flange closeou */ :>> flight = "STS-122"; :>> phase = ""; :>> causeCategory = "ET・臍帯部起因"; :>> blockCode = "ET"; :>> ruleId = "E"; }
    part <'DME-219'> dme_219 : TpsDebrisEvent { doc /* STS-122 ET TPS loss in LH2 acreage foam forward of the Sta */ :>> flight = "STS-122"; :>> phase = "ascent"; :>> causeCategory = "ET・臍帯部起因"; :>> blockCode = "ET"; :>> ruleId = "E"; }
    part <'DME-220'> dme_220 : TpsDebrisEvent { doc /* STS-122 ET TPS loss in LH2 acreage foam at Station 1145 du */ :>> flight = "STS-122"; :>> phase = "ascent"; :>> causeCategory = "ET・臍帯部起因"; :>> blockCode = "ET"; :>> ruleId = "E"; }
    part <'DME-221'> dme_221 : TpsDebrisEvent { doc /* STS-122 ET TPS loss in the LO2 Umbilical Cable Tray */ :>> flight = "STS-122"; :>> phase = "ascent"; :>> causeCategory = "ET・臍帯部起因"; :>> blockCode = "ET"; :>> ruleId = "E"; }
    part <'DME-222'> dme_222 : TpsDebrisEvent { doc /* STS-122 an entire tile falling from the aft end of the por */ :>> flight = "STS-122"; :>> phase = ""; :>> causeCategory = "オービタ自身"; :>> blockCode = "TPS"; :>> ruleId = "O"; }
    part <'DME-223'> dme_223 : TpsDebrisEvent { doc /* STS-122 small piece of debris (at 27 sec MET) */ :>> flight = "STS-122"; :>> phase = "ascent"; :>> causeCategory = "その他・原因の記載なし"; :>> blockCode = ""; :>> ruleId = "U"; }
    part <'DME-224'> dme_224 : TpsDebrisEvent { doc /* STS-122 multiple pieces of small debris (at 125 sec MET, d */ :>> flight = "STS-122"; :>> phase = "ascent"; :>> causeCategory = "その他・原因の記載なし"; :>> blockCode = ""; :>> ruleId = "U"; }
    part <'DME-225'> dme_225 : TpsDebrisEvent { doc /* STS-123 stub tile partly missing (about 25 percent of volu */ :>> flight = "STS-123"; :>> phase = "postlanding"; :>> causeCategory = "オービタ自身"; :>> blockCode = "TPS"; :>> ruleId = "O"; }
    part <'DME-226'> dme_226 : TpsDebrisEvent { doc /* STS-123 MM/OD impact (1/8 to 3/16 in diameter) */ :>> flight = "STS-123"; :>> phase = "on-orbit"; :>> causeCategory = "軌道上（MMOD）"; :>> blockCode = "STR"; :>> ruleId = "M"; }
    part <'DME-227'> dme_227 : TpsDebrisEvent { doc /* STS-124 bricks from the flame trench (liberated refractory */ :>> flight = "STS-124"; :>> phase = "ascent"; :>> causeCategory = "地上・発射台"; :>> blockCode = ""; :>> ruleId = "G"; }
    part <'DME-228'> dme_228 : TpsDebrisEvent { doc /* STS-124 Tyvek rain cover remnants (about 2 g) released lat */ :>> flight = "STS-124"; :>> phase = "ascent"; :>> causeCategory = "オービタ自身"; :>> blockCode = "RCS"; :>> ruleId = "O"; }
    part <'DME-229'> dme_229 : TpsDebrisEvent { doc /* STS-124 tile loss (part of a tile missing) */ :>> flight = "STS-124"; :>> phase = "ascent"; :>> causeCategory = "オービタ自身"; :>> blockCode = "TPS"; :>> ruleId = "O"; }
    part <'DME-230'> dme_230 : TpsDebrisEvent { doc /* STS-124 two foam losses within the XT 1129 LO2 feedline su */ :>> flight = "STS-124"; :>> phase = "ascent"; :>> causeCategory = "ET・臍帯部起因"; :>> blockCode = "ET"; :>> ruleId = "E"; }
    part <'DME-231'> dme_231 : TpsDebrisEvent { doc /* STS-126 MM/OD impact */ :>> flight = "STS-126"; :>> phase = "on-orbit"; :>> causeCategory = "軌道上（MMOD）"; :>> blockCode = "STR"; :>> ruleId = "M"; }
    part <'DME-232'> dme_232 : TpsDebrisEvent { doc /* STS-126 ET TPS loss at -100 sec caused by the Gaseous Oxyg */ :>> flight = "STS-126"; :>> phase = "prelaunch"; :>> causeCategory = "ET・臍帯部起因"; :>> blockCode = "ET"; :>> ruleId = "E"; }
    part <'DME-233'> dme_233 : TpsDebrisEvent { doc /* STS-126 multiple pieces of debris (additional data: most l */ :>> flight = "STS-126"; :>> phase = "ascent"; :>> causeCategory = "ET・臍帯部起因"; :>> blockCode = "ET"; :>> ruleId = "E"; }
    part <'DME-234'> dme_234 : TpsDebrisEvent { doc /* STS-126 light-colored piece of debris at about 29 sec MET  */ :>> flight = "STS-126"; :>> phase = "ascent"; :>> causeCategory = "オービタ自身"; :>> blockCode = "RCS"; :>> ruleId = "O"; }
    part <'DME-235'> dme_235 : TpsDebrisEvent { doc /* STS-119 hypervelocity impacts */ :>> flight = "STS-119"; :>> phase = "on-orbit"; :>> causeCategory = "軌道上（MMOD）"; :>> blockCode = "STR"; :>> ruleId = "M"; }
    part <'DME-236'> dme_236 : TpsDebrisEvent { doc /* STS-119 tile chips (observed during the ignition transient */ :>> flight = "STS-119"; :>> phase = "ascent"; :>> causeCategory = "オービタ自身"; :>> blockCode = "TPS"; :>> ruleId = "O"; }
    part <'DME-237'> dme_237 : TpsDebrisEvent { doc /* STS-119 forward RCS thruster F4D Tyvek rain cover (partial */ :>> flight = "STS-119"; :>> phase = "ascent"; :>> causeCategory = "オービタ自身"; :>> blockCode = "RCS"; :>> ruleId = "O"; }
    part <'DME-238'> dme_238 : TpsDebrisEvent { doc /* STS-125 line of small damages (about 21 in long); two WLEI */ :>> flight = "STS-125"; :>> phase = "ascent"; :>> causeCategory = "その他・原因の記載なし"; :>> blockCode = ""; :>> ruleId = "U"; }
    part <'DME-239'> dme_239 : TpsDebrisEvent { doc /* STS-125 hypervelocity impact */ :>> flight = "STS-125"; :>> phase = "on-orbit"; :>> causeCategory = "軌道上（MMOD）"; :>> blockCode = "STR"; :>> ruleId = "M"; }
    part <'DME-240'> dme_240 : TpsDebrisEvent { doc /* STS-125 ice/frost debris from the LO2 T-0 umbilical lines */ :>> flight = "STS-125"; :>> phase = "ascent"; :>> causeCategory = "ET・臍帯部起因"; :>> blockCode = "ET"; :>> ruleId = "E"; }
    part <'DME-241'> dme_241 : TpsDebrisEvent { doc /* STS-127 foam loss from the LO2 Ice-Frost Ramp (aft inboard */ :>> flight = "STS-127"; :>> phase = ""; :>> causeCategory = "ET・臍帯部起因"; :>> blockCode = "ET"; :>> ruleId = "E"; }
    part <'DME-242'> dme_242 : TpsDebrisEvent { doc /* STS-127 loss of foam at several locations on the Intertank */ :>> flight = "STS-127"; :>> phase = "ascent"; :>> causeCategory = "ET・臍帯部起因"; :>> blockCode = "ET"; :>> ruleId = "E"; }
    part <'DME-243'> dme_243 : TpsDebrisEvent { doc /* STS-127 three losses of TPS material at the +Y and -Y bipo */ :>> flight = "STS-127"; :>> phase = "ascent"; :>> causeCategory = "ET・臍帯部起因"; :>> blockCode = "ET"; :>> ruleId = "E"; }
    part <'DME-244'> dme_244 : TpsDebrisEvent { doc /* STS-127 damage sites seen in R-bar pitch maneuver (RPM) im */ :>> flight = "STS-127"; :>> phase = "on-orbit"; :>> causeCategory = "その他・原因の記載なし"; :>> blockCode = ""; :>> ruleId = "X"; }
    part <'DME-245'> dme_245 : TpsDebrisEvent { doc /* STS-127 single piece of debris aft of the port bipod foot  */ :>> flight = "STS-127"; :>> phase = "ascent"; :>> causeCategory = "その他・原因の記載なし"; :>> blockCode = ""; :>> ruleId = "X"; }
    part <'DME-246'> dme_246 : TpsDebrisEvent { doc /* STS-128 ET foam loss (LH2/intertank flange closeout, betwe */ :>> flight = "STS-128"; :>> phase = "ascent"; :>> causeCategory = "ET・臍帯部起因"; :>> blockCode = "ET"; :>> ruleId = "E"; }
    part <'DME-247'> dme_247 : TpsDebrisEvent { doc /* STS-128 several pieces of Viton-coated nylon from the SRB  */ :>> flight = "STS-128"; :>> phase = "ascent"; :>> causeCategory = "SRB・RSRM 起因"; :>> blockCode = "SRB"; :>> ruleId = "X"; }
    part <'DME-248'> dme_248 : TpsDebrisEvent { doc /* STS-129 High Velocity Impacts (HVIs) and Low Velocity Impa */ :>> flight = "STS-129"; :>> phase = "on-orbit"; :>> causeCategory = "軌道上（MMOD）"; :>> blockCode = "STR"; :>> ruleId = "M"; }
    part <'DME-249'> dme_249 : TpsDebrisEvent { doc /* STS-129 ET TPS foam losses (multiple areas and divots, ele */ :>> flight = "STS-129"; :>> phase = "ascent"; :>> causeCategory = "ET・臍帯部起因"; :>> blockCode = "ET"; :>> ruleId = "E"; }
    part <'DME-250'> dme_250 : TpsDebrisEvent { doc /* STS-129 single piece of debris near the starboard bipod sp */ :>> flight = "STS-129"; :>> phase = "ascent"; :>> causeCategory = "その他・原因の記載なし"; :>> blockCode = ""; :>> ruleId = "X"; }
    part <'DME-251'> dme_251 : TpsDebrisEvent { doc /* STS-129 possible Orbiter tile damage observed during RSRB  */ :>> flight = "STS-129"; :>> phase = "ascent"; :>> causeCategory = "オービタ自身"; :>> blockCode = "TPS"; :>> ruleId = "O"; }
    part <'DME-252'> dme_252 : TpsDebrisEvent { doc /* STS-129 debris liberating from the aft section of the ET,  */ :>> flight = "STS-129"; :>> phase = "ascent"; :>> causeCategory = "ET・臍帯部起因"; :>> blockCode = "ET"; :>> ruleId = "E"; }
    part <'DME-253'> dme_253 : TpsDebrisEvent { doc /* STS-129 debris first observed near the LH2 Tail Service Ma */ :>> flight = "STS-129"; :>> phase = "ascent"; :>> causeCategory = "その他・原因の記載なし"; :>> blockCode = ""; :>> ruleId = "X"; }
    part <'DME-254'> dme_254 : TpsDebrisEvent { doc /* STS-130 possible debris impact (light spot on the surface; */ :>> flight = "STS-130"; :>> phase = "ascent"; :>> causeCategory = "その他・原因の記載なし"; :>> blockCode = ""; :>> ruleId = "U"; }
    part <'DME-255'> dme_255 : TpsDebrisEvent { doc /* STS-130 ET intertank foam losses (NCFI 24-124 acreage): 2  */ :>> flight = "STS-130"; :>> phase = "ascent"; :>> causeCategory = "ET・臍帯部起因"; :>> blockCode = "ET"; :>> ruleId = "E"; }
    part <'DME-256'> dme_256 : TpsDebrisEvent { doc /* STS-131 MM/OD impact site */ :>> flight = "STS-131"; :>> phase = "on-orbit"; :>> causeCategory = "軌道上（MMOD）"; :>> blockCode = "STR"; :>> ruleId = "M"; }
    part <'DME-257'> dme_257 : TpsDebrisEvent { doc /* STS-131 tile from the port-upper rudder speed brake traili */ :>> flight = "STS-131"; :>> phase = "ascent"; :>> causeCategory = "オービタ自身"; :>> blockCode = "TPS"; :>> ruleId = "O"; }
    part <'DME-258'> dme_258 : TpsDebrisEvent { doc /* STS-131 small piece of debris, an RTV material repair that */ :>> flight = "STS-131"; :>> phase = "ascent"; :>> causeCategory = "オービタ自身"; :>> blockCode = "TPS"; :>> ruleId = "O"; }
    part <'DME-259'> dme_259 : TpsDebrisEvent { doc /* STS-132 ET intertank foam loss (weak bond adhesion) */ :>> flight = "STS-132"; :>> phase = "ascent"; :>> causeCategory = "ET・臍帯部起因"; :>> blockCode = "ET"; :>> ruleId = "E"; }
    part <'DME-260'> dme_260 : TpsDebrisEvent { doc /* STS-132 ET TPS (intertank), one piece liberated; poor TPS  */ :>> flight = "STS-132"; :>> phase = "ascent"; :>> causeCategory = "ET・臍帯部起因"; :>> blockCode = "ET"; :>> ruleId = "E"; }
    part <'DME-261'> dme_261 : TpsDebrisEvent { doc /* STS-132 ice (LH2 T-0 umbilical retraction) */ :>> flight = "STS-132"; :>> phase = "ascent"; :>> causeCategory = "ET・臍帯部起因"; :>> blockCode = "ET"; :>> ruleId = "E"; }
    part <'DME-262'> dme_262 : TpsDebrisEvent { doc /* STS-133 a single piece of debris (during RSRB separation,  */ :>> flight = "STS-133"; :>> phase = "ascent"; :>> causeCategory = "その他・原因の記載なし"; :>> blockCode = ""; :>> ruleId = "U"; }
    part <'DME-263'> dme_263 : TpsDebrisEvent { doc /* STS-133 large piece of ET TPS foam (several smaller partic */ :>> flight = "STS-133"; :>> phase = "ascent"; :>> causeCategory = "ET・臍帯部起因"; :>> blockCode = "ET"; :>> ruleId = "E"; }
    part <'DME-264'> dme_264 : TpsDebrisEvent { doc /* STS-133 a single piece of linear-shaped, flexible debris n */ :>> flight = "STS-133"; :>> phase = "ascent"; :>> causeCategory = "その他・原因の記載なし"; :>> blockCode = ""; :>> ruleId = "X"; }
    part <'DME-265'> dme_265 : TpsDebrisEvent { doc /* STS-134 off-nominal foam loss */ :>> flight = "STS-134"; :>> phase = ""; :>> causeCategory = "ET・臍帯部起因"; :>> blockCode = "ET"; :>> ruleId = "E"; }
    part <'DME-266'> dme_266 : TpsDebrisEvent { doc /* STS-134 foam hit (at 3:51 into launch) */ :>> flight = "STS-134"; :>> phase = "ascent"; :>> causeCategory = "ET・臍帯部起因"; :>> blockCode = "ET"; :>> ruleId = "E"; }
    part <'DME-267'> dme_267 : TpsDebrisEvent { doc /* STS-134 hypervelocity-type impacts (defects) */ :>> flight = "STS-134"; :>> phase = ""; :>> causeCategory = "軌道上（MMOD）"; :>> blockCode = "STR"; :>> ruleId = "M"; }
    part <'DME-268'> dme_268 : TpsDebrisEvent { doc /* STS-134 cylindrically shaped metallic-looking object (at a */ :>> flight = "STS-134"; :>> phase = "ascent"; :>> causeCategory = "その他・原因の記載なし"; :>> blockCode = ""; :>> ruleId = "U"; }
    part <'DME-269'> dme_269 : TpsDebrisEvent { doc /* STS-135 debris near the left vertical strut that appears t */ :>> flight = "STS-135"; :>> phase = "ascent"; :>> causeCategory = "その他・原因の記載なし"; :>> blockCode = ""; :>> ruleId = "U"; }
    part <'DME-270'> dme_270 : TpsDebrisEvent { doc /* STS-135 single piece of debris near the LO2 feedline (abou */ :>> flight = "STS-135"; :>> phase = "ascent"; :>> causeCategory = "その他・原因の記載なし"; :>> blockCode = ""; :>> ruleId = "X"; }
    part <'DME-271'> dme_271 : TpsDebrisEvent { doc /* STS-135 lift-off debris and possible vapors from the flame */ :>> flight = "STS-135"; :>> phase = "ascent"; :>> causeCategory = "地上・発射台"; :>> blockCode = ""; :>> ruleId = "G"; }
    part <'DME-272'> dme_272 : TpsDebrisEvent { doc /* STS-135 single piece of debris near the LH2 intertank flan */ :>> flight = "STS-135"; :>> phase = "ascent"; :>> causeCategory = "その他・原因の記載なし"; :>> blockCode = ""; :>> ruleId = "X"; }
}
