// SysML v2 テキスト：LCC 原典定義書（NSTS 16007 Rev H の項目の索引と天候の規則）
// SSD-LCO-ORB-001 LCC 原典定義書（NSTS 16007 Rev H の項目の索引と天候の規則） の表から生成（lib/build_docs_do.py・rev_do/lcodata_do.py）。根拠の頁は SSD-LCO-ORB-001 にある。
package SSD_LCO_ORB_001 {
    doc /* SSD-LCO-ORB-001 LCC 原典定義書（NSTS 16007 Rev H の項目の索引と天候の規則）。LCC 本体（NSTS 16007 Rev H）の SSID を節（LccSection）の中の項目（LccItem）として持ち、境界は isCounted = false の項目で持つ。WEA-01 の数値つき規則を WeatherRule として持つ。Mission Report の LCC 違反の記録との結び 25件を LccJoin として持つ（結び直しはしない。測定値は持たない）。要求への関係は張らず、トレースの外に置く。 */
    private import ScalarValues::*;
    part def LccSection {
        doc /* LCC 本体の節（目次の節の番号・SSID の接頭辞）。目次に接頭辞が無い付録の SSID は節の番号を持たない */
        attribute sectionNo : String;
        attribute sectionTitle : String;
        attribute ssidPrefix : String;
    }
    part def LccItem {
        doc /* LCC 本体の SSID（項目）。題は LCC VIOLATION CALL の行（無ければ空）。適用範囲は頁の MISSION の行のとおり。測定値は持たない */
        attribute ssid : String;
        attribute title : String;
        attribute effectivity : String;
        attribute changeNo : String;
        attribute measurementCount : Integer;
        attribute numericLimitCount : Integer;
        attribute sourcePage : Integer;
        attribute isCounted : Boolean;
    }
    part def WeatherRule {
        doc /* LCC 本体 WEA-01（Change 056）の数値つき規則。条項は本文の番号どおり。数・単位は本文のまま */
        attribute clause : String;
        attribute limitValues : String;
        attribute ruleText : String;
        attribute sourcePage : Integer;
    }
    part lccSections {
        part sec_srm : LccSection {
            :>> sectionNo = "10";
            :>> sectionTitle = "SOLID ROCKET MOTOR";
            :>> ssidPrefix = "SRM";
            part <'LCO-001'> lco_001 : LccItem { doc /* SRM-01 */ :>> ssid = "SRM-01"; :>> title = "SRB Ignition Safe and Arm Safed Anomaly"; :>> effectivity = "STS-115-999"; :>> changeNo = "060"; :>> measurementCount = 4; :>> numericLimitCount = 0; :>> sourcePage = 139; :>> isCounted = true; }
            part <'LCO-002'> lco_002 : LccItem { doc /* SRM-02 */ :>> ssid = "SRM-02"; :>> title = "SRB Ignition Safe and Arm Armed Anomaly"; :>> effectivity = "STS-115-999"; :>> changeNo = "060"; :>> measurementCount = 4; :>> numericLimitCount = 0; :>> sourcePage = 141; :>> isCounted = true; }
            part <'LCO-003'> lco_003 : LccItem { doc /* SRM-04 */ :>> ssid = "SRM-04"; :>> title = "SRM Chamber Pressure Anomaly"; :>> effectivity = "STS-115-999"; :>> changeNo = "060"; :>> measurementCount = 6; :>> numericLimitCount = 6; :>> sourcePage = 145; :>> isCounted = true; }
            part <'LCO-004'> lco_004 : LccItem { doc /* SRM-06 */ :>> ssid = "SRM-06"; :>> title = "SRM Field Joint Temperature Anomaly"; :>> effectivity = "STS-116-120,122-999"; :>> changeNo = "070"; :>> measurementCount = 48; :>> numericLimitCount = 48; :>> sourcePage = 151; :>> isCounted = true; }
            part <'LCO-005'> lco_005 : LccItem { doc /* SRM-07 */ :>> ssid = "SRM-07"; :>> title = "SRM Nozzle-To-Case Joint Temperature Anomaly"; :>> effectivity = "STS-116-120,122-999"; :>> changeNo = "070"; :>> measurementCount = 20; :>> numericLimitCount = 20; :>> sourcePage = 157; :>> isCounted = true; }
            part <'LCO-006'> lco_006 : LccItem { doc /* SRM-10 */ :>> ssid = "SRM-10"; :>> title = "SRM Igniter Joint Temperature Anomaly"; :>> effectivity = "STS-116-120,122-999"; :>> changeNo = "070"; :>> measurementCount = 8; :>> numericLimitCount = 8; :>> sourcePage = 167; :>> isCounted = true; }
            part <'LCO-007'> lco_007 : LccItem { doc /* SRM-11 */ :>> ssid = "SRM-11"; :>> title = "SRM Case Acreage Temperature Anomaly"; :>> effectivity = "STS-116-120,122-999"; :>> changeNo = "070"; :>> measurementCount = 20; :>> numericLimitCount = 20; :>> sourcePage = 171; :>> isCounted = true; }
            part <'LCO-505'> lco_505 : LccItem { doc /* SRM-00 */ :>> ssid = "SRM-00"; :>> title = ""; :>> effectivity = "N/A"; :>> changeNo = "062"; :>> measurementCount = 0; :>> numericLimitCount = 0; :>> sourcePage = 135; :>> isCounted = false; }
            part <'LCO-506'> lco_506 : LccItem { doc /* SRM-03 */ :>> ssid = "SRM-03"; :>> title = ""; :>> effectivity = "STS-98,100,102,104,105,107-999"; :>> changeNo = "000"; :>> measurementCount = 0; :>> numericLimitCount = 0; :>> sourcePage = 143; :>> isCounted = false; }
            part <'LCO-507'> lco_507 : LccItem { doc /* SRM-05 */ :>> ssid = "SRM-05"; :>> title = ""; :>> effectivity = "STS-98,100,102,104,105,107-999"; :>> changeNo = "000"; :>> measurementCount = 0; :>> numericLimitCount = 0; :>> sourcePage = 149; :>> isCounted = false; }
            part <'LCO-508'> lco_508 : LccItem { doc /* SRM-08 */ :>> ssid = "SRM-08"; :>> title = ""; :>> effectivity = "STS-98,100,102,104,105,107-999"; :>> changeNo = "000"; :>> measurementCount = 0; :>> numericLimitCount = 0; :>> sourcePage = 163; :>> isCounted = false; }
            part <'LCO-509'> lco_509 : LccItem { doc /* SRM-09 */ :>> ssid = "SRM-09"; :>> title = ""; :>> effectivity = "STS-98,100,102,104,105,107-999"; :>> changeNo = "000"; :>> measurementCount = 0; :>> numericLimitCount = 0; :>> sourcePage = 165; :>> isCounted = false; }
        }
        part sec_btvc : LccSection {
            :>> sectionNo = "11";
            :>> sectionTitle = "BOOSTER THRUST VECTOR CONTROL SUBSYSTEM";
            :>> ssidPrefix = "BTVC";
            part <'LCO-008'> lco_008 : LccItem { doc /* BTVC-01 */ :>> ssid = "BTVC-01"; :>> title = "SRB HPU Fuel Supply Pressure Anomaly"; :>> effectivity = "STS-119,123-999"; :>> changeNo = "086"; :>> measurementCount = 4; :>> numericLimitCount = 4; :>> sourcePage = 179; :>> isCounted = true; }
            part <'LCO-009'> lco_009 : LccItem { doc /* BTVC-02 */ :>> ssid = "BTVC-02"; :>> title = "SRB HPU Fuel Supply Module GN2 Pressure Anomaly"; :>> effectivity = "STS-119,123-999"; :>> changeNo = "086"; :>> measurementCount = 4; :>> numericLimitCount = 4; :>> sourcePage = 183; :>> isCounted = true; }
            part <'LCO-010'> lco_010 : LccItem { doc /* BTVC-03 */ :>> ssid = "BTVC-03"; :>> title = "SRB Hydraulic Fluid Reservoir Level Anomaly"; :>> effectivity = "STS-98,100,102,104,105,107-999"; :>> changeNo = "000"; :>> measurementCount = 4; :>> numericLimitCount = 4; :>> sourcePage = 187; :>> isCounted = true; }
            part <'LCO-011'> lco_011 : LccItem { doc /* BTVC-04 */ :>> ssid = "BTVC-04"; :>> title = "SRB Hydraulic Fluid Reservoir Level Anomaly"; :>> effectivity = "STS-98,100,102,104,105,107-999"; :>> changeNo = "000"; :>> measurementCount = 4; :>> numericLimitCount = 4; :>> sourcePage = 189; :>> isCounted = true; }
            part <'LCO-012'> lco_012 : LccItem { doc /* BTVC-05 */ :>> ssid = "BTVC-05"; :>> title = "SRB APU Hydrazine Isolation Valve Position Anomaly"; :>> effectivity = "STS-114-999"; :>> changeNo = "047"; :>> measurementCount = 8; :>> numericLimitCount = 0; :>> sourcePage = 191; :>> isCounted = true; }
            part <'LCO-013'> lco_013 : LccItem { doc /* BTVC-06 */ :>> ssid = "BTVC-06"; :>> title = "SRB HPU Secondary Speed Control Anomaly"; :>> effectivity = "STS-98,100,102,104,105,107-999"; :>> changeNo = "000"; :>> measurementCount = 4; :>> numericLimitCount = 0; :>> sourcePage = 195; :>> isCounted = true; }
            part <'LCO-014'> lco_014 : LccItem { doc /* BTVC-07 */ :>> ssid = "BTVC-07"; :>> title = "SRB HPU Turbine Speed Anomaly"; :>> effectivity = "STS-98,100,102,104,105,107-999"; :>> changeNo = "000"; :>> measurementCount = 4; :>> numericLimitCount = 4; :>> sourcePage = 197; :>> isCounted = true; }
            part <'LCO-015'> lco_015 : LccItem { doc /* BTVC-08 */ :>> ssid = "BTVC-08"; :>> title = "SRB HPU Turbine Speed Anomaly"; :>> effectivity = "STS-98,100,102,104,105,107-999"; :>> changeNo = "000"; :>> measurementCount = 4; :>> numericLimitCount = 4; :>> sourcePage = 199; :>> isCounted = true; }
            part <'LCO-016'> lco_016 : LccItem { doc /* BTVC-09 */ :>> ssid = "BTVC-09"; :>> title = "SRB Hydraulic Fluid Supply Pressure Anomaly"; :>> effectivity = "STS-98,100,102,104,105,107-999"; :>> changeNo = "000"; :>> measurementCount = 4; :>> numericLimitCount = 4; :>> sourcePage = 201; :>> isCounted = true; }
            part <'LCO-017'> lco_017 : LccItem { doc /* BTVC-10 */ :>> ssid = "BTVC-10"; :>> title = "SRB TVC Gimbal Profile Anomaly"; :>> effectivity = "STS-98,100,102,104,105,107-999"; :>> changeNo = "000"; :>> measurementCount = 4; :>> numericLimitCount = 0; :>> sourcePage = 203; :>> isCounted = true; }
            part <'LCO-018'> lco_018 : LccItem { doc /* BTVC-11 */ :>> ssid = "BTVC-11"; :>> title = "SRB TVC Hydraulic Actuator Secondary Delta Pressure"; :>> effectivity = "STS-98,100,102,104,105,107-999"; :>> changeNo = "000"; :>> measurementCount = 16; :>> numericLimitCount = 16; :>> sourcePage = 207; :>> isCounted = true; }
            part <'LCO-019'> lco_019 : LccItem { doc /* BTVC-12 */ :>> ssid = "BTVC-12"; :>> title = "SRB Rock and Tilt Actuator Fail Indication"; :>> effectivity = "STS-98,100,102,104,105,107-999"; :>> changeNo = "000"; :>> measurementCount = 16; :>> numericLimitCount = 0; :>> sourcePage = 209; :>> isCounted = true; }
            part <'LCO-020'> lco_020 : LccItem { doc /* BTVC-13 */ :>> ssid = "BTVC-13"; :>> title = "SRB TVC Secondary Delta Pressure Post Gimbal Profile"; :>> effectivity = "STS-98,100,102,104,105,107-999"; :>> changeNo = "000"; :>> measurementCount = 16; :>> numericLimitCount = 16; :>> sourcePage = 211; :>> isCounted = true; }
            part <'LCO-021'> lco_021 : LccItem { doc /* BTVC-14 */ :>> ssid = "BTVC-14"; :>> title = "SRB TVC Hydraulic Actuator Null Position Anomaly"; :>> effectivity = "STS-98,100,102,104,105,107-999"; :>> changeNo = "000"; :>> measurementCount = 4; :>> numericLimitCount = 4; :>> sourcePage = 213; :>> isCounted = true; }
            part <'LCO-022'> lco_022 : LccItem { doc /* BTVC-15 */ :>> ssid = "BTVC-15"; :>> title = "SRB APU Gas Generator Temperature Anomaly"; :>> effectivity = "STS-98,100,102,104,105,107-999"; :>> changeNo = "000"; :>> measurementCount = 8; :>> numericLimitCount = 8; :>> sourcePage = 215; :>> isCounted = true; }
            part <'LCO-023'> lco_023 : LccItem { doc /* BTVC-16 */ :>> ssid = "BTVC-16"; :>> title = "SRB HPU Primary Pressure OK Anomaly"; :>> effectivity = "STS-107-999"; :>> changeNo = "011"; :>> measurementCount = 4; :>> numericLimitCount = 0; :>> sourcePage = 217; :>> isCounted = true; }
            part <'LCO-510'> lco_510 : LccItem { doc /* BTVC-00 */ :>> ssid = "BTVC-00"; :>> title = ""; :>> effectivity = "N/A"; :>> changeNo = "047"; :>> measurementCount = 0; :>> numericLimitCount = 0; :>> sourcePage = 175; :>> isCounted = false; }
        }
        part sec_brss : LccSection {
            :>> sectionNo = "12";
            :>> sectionTitle = "BOOSTER RANGE SAFETY SYSTEM";
            :>> ssidPrefix = "BRSS";
            part <'LCO-024'> lco_024 : LccItem { doc /* BRSS-01 */ :>> ssid = "BRSS-01"; :>> title = "SRB Range Safety System Armed Indication Anomaly"; :>> effectivity = "STS-119,120,122-999"; :>> changeNo = "080"; :>> measurementCount = 4; :>> numericLimitCount = 0; :>> sourcePage = 223; :>> isCounted = true; }
            part <'LCO-025'> lco_025 : LccItem { doc /* BRSS-05 */ :>> ssid = "BRSS-05"; :>> title = "SRB Range Safety System Inhibit Anomaly"; :>> effectivity = "STS-119,120,122-999"; :>> changeNo = "080"; :>> measurementCount = 4; :>> numericLimitCount = 0; :>> sourcePage = 231; :>> isCounted = true; }
            part <'LCO-026'> lco_026 : LccItem { doc /* BRSS-07 */ :>> ssid = "BRSS-07"; :>> title = "SRB Range Safety System Battery Voltage Anomaly"; :>> effectivity = "STS-119,120,122-999"; :>> changeNo = "080"; :>> measurementCount = 8; :>> numericLimitCount = 6; :>> sourcePage = 235; :>> isCounted = true; }
            part <'LCO-027'> lco_027 : LccItem { doc /* BRSS-08 */ :>> ssid = "BRSS-08"; :>> title = "SRB Recovery Battery Voltage Anomaly"; :>> effectivity = "STS-119,120,122-999"; :>> changeNo = "080"; :>> measurementCount = 8; :>> numericLimitCount = 6; :>> sourcePage = 239; :>> isCounted = true; }
            part <'LCO-028'> lco_028 : LccItem { doc /* BRSS-09 */ :>> ssid = "BRSS-09"; :>> title = "SRB Range Safety System Arm Latch Voltage Anomaly"; :>> effectivity = "STS-119,120,122-999"; :>> changeNo = "080"; :>> measurementCount = 4; :>> numericLimitCount = 4; :>> sourcePage = 243; :>> isCounted = true; }
            part <'LCO-029'> lco_029 : LccItem { doc /* BRSS-11 */ :>> ssid = "BRSS-11"; :>> title = "SRB Range Safety System Battery Current Anomaly"; :>> effectivity = "STS-119,120,122-999"; :>> changeNo = "080"; :>> measurementCount = 4; :>> numericLimitCount = 4; :>> sourcePage = 247; :>> isCounted = true; }
            part <'LCO-030'> lco_030 : LccItem { doc /* BRSS-12 */ :>> ssid = "BRSS-12"; :>> title = "SRB Recovery Battery Current Anomaly"; :>> effectivity = "STS-119,120,122-999"; :>> changeNo = "080"; :>> measurementCount = 4; :>> numericLimitCount = 4; :>> sourcePage = 249; :>> isCounted = true; }
            part <'LCO-031'> lco_031 : LccItem { doc /* BRSS-13 */ :>> ssid = "BRSS-13"; :>> title = "SRB Range Safety System Armed Command Anomaly"; :>> effectivity = "STS-119,120,122-999"; :>> changeNo = "080"; :>> measurementCount = 4; :>> numericLimitCount = 0; :>> sourcePage = 251; :>> isCounted = true; }
            part <'LCO-032'> lco_032 : LccItem { doc /* BRSS-14 */ :>> ssid = "BRSS-14"; :>> title = "SRB Range Safety System Fire Command Anomaly"; :>> effectivity = "STS-119,120,122-999"; :>> changeNo = "080"; :>> measurementCount = 4; :>> numericLimitCount = 0; :>> sourcePage = 253; :>> isCounted = true; }
            part <'LCO-033'> lco_033 : LccItem { doc /* BRSS-15 */ :>> ssid = "BRSS-15"; :>> title = "SRB Range Safety System Receiver Signal Strength Anomaly"; :>> effectivity = "STS-119,120,122-999"; :>> changeNo = "080"; :>> measurementCount = 4; :>> numericLimitCount = 0; :>> sourcePage = 255; :>> isCounted = true; }
            part <'LCO-034'> lco_034 : LccItem { doc /* BRSS-16 */ :>> ssid = "BRSS-16"; :>> title = "SRB Range Safety System Safe & Arm Device Anomaly"; :>> effectivity = "STS-119,120,122-999"; :>> changeNo = "080"; :>> measurementCount = 4; :>> numericLimitCount = 0; :>> sourcePage = 259; :>> isCounted = true; }
            part <'LCO-511'> lco_511 : LccItem { doc /* BRSS-00 */ :>> ssid = "BRSS-00"; :>> title = ""; :>> effectivity = "N/A"; :>> changeNo = "078"; :>> measurementCount = 0; :>> numericLimitCount = 0; :>> sourcePage = 219; :>> isCounted = false; }
            part <'LCO-512'> lco_512 : LccItem { doc /* BRSS-02 */ :>> ssid = "BRSS-02"; :>> title = ""; :>> effectivity = "STS-98,100,102,104,105,107-999"; :>> changeNo = "000"; :>> measurementCount = 0; :>> numericLimitCount = 0; :>> sourcePage = 225; :>> isCounted = false; }
            part <'LCO-513'> lco_513 : LccItem { doc /* BRSS-03 */ :>> ssid = "BRSS-03"; :>> title = ""; :>> effectivity = "STS-98,100,102,104,105,107-999"; :>> changeNo = "000"; :>> measurementCount = 0; :>> numericLimitCount = 0; :>> sourcePage = 227; :>> isCounted = false; }
            part <'LCO-514'> lco_514 : LccItem { doc /* BRSS-04 */ :>> ssid = "BRSS-04"; :>> title = ""; :>> effectivity = "STS-98,100,102,104,105,107-999"; :>> changeNo = "000"; :>> measurementCount = 0; :>> numericLimitCount = 0; :>> sourcePage = 229; :>> isCounted = false; }
            part <'LCO-515'> lco_515 : LccItem { doc /* BRSS-06 */ :>> ssid = "BRSS-06"; :>> title = ""; :>> effectivity = "STS-98,100,102,104,105,107-999"; :>> changeNo = "000"; :>> measurementCount = 0; :>> numericLimitCount = 0; :>> sourcePage = 233; :>> isCounted = false; }
            part <'LCO-516'> lco_516 : LccItem { doc /* BRSS-10 */ :>> ssid = "BRSS-10"; :>> title = ""; :>> effectivity = "STS-98,100,102,104,105,107-999"; :>> changeNo = "000"; :>> measurementCount = 0; :>> numericLimitCount = 0; :>> sourcePage = 245; :>> isCounted = false; }
            part <'LCO-517'> lco_517 : LccItem { doc /* BRSS-17 */ :>> ssid = "BRSS-17"; :>> title = ""; :>> effectivity = "STS-118-120,122-999"; :>> changeNo = "078"; :>> measurementCount = 0; :>> numericLimitCount = 0; :>> sourcePage = 261; :>> isCounted = false; }
        }
        part sec_bei : LccSection {
            :>> sectionNo = "13";
            :>> sectionTitle = "BOOSTER ELECTRICAL AND INSTRUMENTATION";
            :>> ssidPrefix = "BEI";
            part <'LCO-035'> lco_035 : LccItem { doc /* BEI-01 */ :>> ssid = "BEI-01"; :>> title = "SRB Operational Bus Voltage"; :>> effectivity = "STS-98,100,102,104,105,107-999"; :>> changeNo = "000"; :>> measurementCount = 8; :>> numericLimitCount = 8; :>> sourcePage = 267; :>> isCounted = true; }
            part <'LCO-036'> lco_036 : LccItem { doc /* BEI-03 */ :>> ssid = "BEI-03"; :>> title = "MDM Post Lockout BSR Status Anomaly"; :>> effectivity = "STS-98,100,102,104,105,107-999"; :>> changeNo = "000"; :>> measurementCount = 0; :>> numericLimitCount = 0; :>> sourcePage = 271; :>> isCounted = true; }
            part <'LCO-037'> lco_037 : LccItem { doc /* BEI-04 */ :>> ssid = "BEI-04"; :>> title = "MDM PROM Bypass Anomaly"; :>> effectivity = "STS-107-999"; :>> changeNo = "011"; :>> measurementCount = 4; :>> numericLimitCount = 0; :>> sourcePage = 273; :>> isCounted = true; }
            part <'LCO-038'> lco_038 : LccItem { doc /* BEI-05 */ :>> ssid = "BEI-05"; :>> title = "MDM Post Lockout BSR Status Anomaly"; :>> effectivity = "STS-98,100,102,104,105,107-999"; :>> changeNo = "000"; :>> measurementCount = 0; :>> numericLimitCount = 0; :>> sourcePage = 277; :>> isCounted = true; }
            part <'LCO-039'> lco_039 : LccItem { doc /* BEI-06 */ :>> ssid = "BEI-06"; :>> title = "Aft MDM Power Separation Anomaly"; :>> effectivity = "STS-107-999"; :>> changeNo = "011"; :>> measurementCount = 8; :>> numericLimitCount = 8; :>> sourcePage = 279; :>> isCounted = true; }
            part <'LCO-040'> lco_040 : LccItem { doc /* BEI-07 */ :>> ssid = "BEI-07"; :>> title = "Fwd MDM Power Separation Anomaly"; :>> effectivity = "STS-107-999"; :>> changeNo = "011"; :>> measurementCount = 8; :>> numericLimitCount = 8; :>> sourcePage = 283; :>> isCounted = true; }
            part <'LCO-041'> lco_041 : LccItem { doc /* BEI-08 */ :>> ssid = "BEI-08"; :>> title = "SRB Igniter PIC Cap Voltage Anomaly"; :>> effectivity = "STS-98,100,102,104,105,107-999"; :>> changeNo = "000"; :>> measurementCount = 4; :>> numericLimitCount = 4; :>> sourcePage = 287; :>> isCounted = true; }
            part <'LCO-042'> lco_042 : LccItem { doc /* BEI-09 */ :>> ssid = "BEI-09"; :>> title = "SRB Igniter PICs Properly Charged Anomaly"; :>> effectivity = "STS-98,100,102,104,105,107-999"; :>> changeNo = "000"; :>> measurementCount = 4; :>> numericLimitCount = 4; :>> sourcePage = 289; :>> isCounted = true; }
            part <'LCO-043'> lco_043 : LccItem { doc /* BEI-10 */ :>> ssid = "BEI-10"; :>> title = "SRM Ignition Fire 2 Test Power ON Command Anomaly"; :>> effectivity = "STS-98,100,102,104,105,107-999"; :>> changeNo = "000"; :>> measurementCount = 4; :>> numericLimitCount = 0; :>> sourcePage = 291; :>> isCounted = true; }
            part <'LCO-518'> lco_518 : LccItem { doc /* BEI-00 */ :>> ssid = "BEI-00"; :>> title = ""; :>> effectivity = "N/A"; :>> changeNo = "000"; :>> measurementCount = 0; :>> numericLimitCount = 0; :>> sourcePage = 263; :>> isCounted = false; }
            part <'LCO-519'> lco_519 : LccItem { doc /* BEI-02 */ :>> ssid = "BEI-02"; :>> title = ""; :>> effectivity = "STS-98,100,102,104,105,107-999"; :>> changeNo = "000"; :>> measurementCount = 0; :>> numericLimitCount = 0; :>> sourcePage = 269; :>> isCounted = false; }
        }
        part sec_bsep : LccSection {
            :>> sectionNo = "14";
            :>> sectionTitle = "BOOSTER SEPARATION SUBSYSTEM";
            :>> ssidPrefix = "BSEP";
            part <'LCO-044'> lco_044 : LccItem { doc /* BSEP-01 */ :>> ssid = "BSEP-01"; :>> title = "SRB Separation PIC's Cap Voltage Anomaly"; :>> effectivity = "STS-107-999"; :>> changeNo = "011"; :>> measurementCount = 24; :>> numericLimitCount = 24; :>> sourcePage = 297; :>> isCounted = true; }
            part <'LCO-045'> lco_045 : LccItem { doc /* BSEP-05 */ :>> ssid = "BSEP-05"; :>> title = "Separation Fire 2 Test Power ON Command Anomaly"; :>> effectivity = "STS-98,100,102,104,105,107-999"; :>> changeNo = "000"; :>> measurementCount = 4; :>> numericLimitCount = 0; :>> sourcePage = 307; :>> isCounted = true; }
            part <'LCO-046'> lco_046 : LccItem { doc /* BSEP-06 */ :>> ssid = "BSEP-06"; :>> title = "SRB Separation Auto Command Anomaly"; :>> effectivity = "STS-98,100,102,104,105,107-999"; :>> changeNo = "000"; :>> measurementCount = 1; :>> numericLimitCount = 0; :>> sourcePage = 309; :>> isCounted = true; }
            part <'LCO-520'> lco_520 : LccItem { doc /* BSEP-00 */ :>> ssid = "BSEP-00"; :>> title = ""; :>> effectivity = "N/A"; :>> changeNo = "000"; :>> measurementCount = 0; :>> numericLimitCount = 0; :>> sourcePage = 293; :>> isCounted = false; }
            part <'LCO-521'> lco_521 : LccItem { doc /* BSEP-02 */ :>> ssid = "BSEP-02"; :>> title = ""; :>> effectivity = "STS-98,100,102,104,105,107-999"; :>> changeNo = "000"; :>> measurementCount = 0; :>> numericLimitCount = 0; :>> sourcePage = 301; :>> isCounted = false; }
            part <'LCO-522'> lco_522 : LccItem { doc /* BSEP-03 */ :>> ssid = "BSEP-03"; :>> title = ""; :>> effectivity = "STS-98,100,102,104,105,107-999"; :>> changeNo = "000"; :>> measurementCount = 0; :>> numericLimitCount = 0; :>> sourcePage = 303; :>> isCounted = false; }
            part <'LCO-523'> lco_523 : LccItem { doc /* BSEP-04 */ :>> ssid = "BSEP-04"; :>> title = ""; :>> effectivity = "STS-98,100,102,104,105,107-999"; :>> changeNo = "000"; :>> measurementCount = 0; :>> numericLimitCount = 0; :>> sourcePage = 305; :>> isCounted = false; }
        }
        part sec_brec : LccSection {
            :>> sectionNo = "15";
            :>> sectionTitle = "BOOSTER RECOVERY SUBSYSTEM";
            :>> ssidPrefix = "BREC";
            part <'LCO-047'> lco_047 : LccItem { doc /* BREC-02 */ :>> ssid = "BREC-02"; :>> title = "SRB Recovery System PIC Cap Voltage Anomaly"; :>> effectivity = "STS-107-999"; :>> changeNo = "011"; :>> measurementCount = 6; :>> numericLimitCount = 6; :>> sourcePage = 317; :>> isCounted = true; }
            part <'LCO-048'> lco_048 : LccItem { doc /* BREC-05 */ :>> ssid = "BREC-05"; :>> title = "Recovery System Reset Command Event Anomaly"; :>> effectivity = "STS-98,100,102,104,105,107-999"; :>> changeNo = "000"; :>> measurementCount = 2; :>> numericLimitCount = 0; :>> sourcePage = 325; :>> isCounted = true; }
            part <'LCO-524'> lco_524 : LccItem { doc /* BREC-00 */ :>> ssid = "BREC-00"; :>> title = ""; :>> effectivity = "N/A"; :>> changeNo = "000"; :>> measurementCount = 0; :>> numericLimitCount = 0; :>> sourcePage = 311; :>> isCounted = false; }
            part <'LCO-525'> lco_525 : LccItem { doc /* BREC-01 */ :>> ssid = "BREC-01"; :>> title = ""; :>> effectivity = "STS-98,100,102,104,105,107-999"; :>> changeNo = "000"; :>> measurementCount = 0; :>> numericLimitCount = 0; :>> sourcePage = 315; :>> isCounted = false; }
            part <'LCO-526'> lco_526 : LccItem { doc /* BREC-03 */ :>> ssid = "BREC-03"; :>> title = ""; :>> effectivity = "STS-98,100,102,104,105,107-999"; :>> changeNo = "000"; :>> measurementCount = 0; :>> numericLimitCount = 0; :>> sourcePage = 321; :>> isCounted = false; }
            part <'LCO-527'> lco_527 : LccItem { doc /* BREC-04 */ :>> ssid = "BREC-04"; :>> title = ""; :>> effectivity = "STS-98,100,102,104,105,107-999"; :>> changeNo = "000"; :>> measurementCount = 0; :>> numericLimitCount = 0; :>> sourcePage = 323; :>> isCounted = false; }
        }
        part sec_et : LccSection {
            :>> sectionNo = "17";
            :>> sectionTitle = "EXTERNAL TANK SUBSYSTEMS";
            :>> ssidPrefix = "ET";
            part <'LCO-049'> lco_049 : LccItem { doc /* ET-01 */ :>> ssid = "ET-01"; :>> title = "ET Nose Cone Temperature Anomaly"; :>> effectivity = "STS-104,105,107-999"; :>> changeNo = "008"; :>> measurementCount = 8; :>> numericLimitCount = 6; :>> sourcePage = 331; :>> isCounted = true; }
            part <'LCO-050'> lco_050 : LccItem { doc /* ET-02 */ :>> ssid = "ET-02"; :>> title = "ET Nose Cone Purge Termination Anomaly"; :>> effectivity = "STS-98,100,102,104,105,107-999"; :>> changeNo = "000"; :>> measurementCount = 4; :>> numericLimitCount = 4; :>> sourcePage = 333; :>> isCounted = true; }
            part <'LCO-051'> lco_051 : LccItem { doc /* ET-03 */ :>> ssid = "ET-03"; :>> title = "ET LO2 Helium Injection Termination Anomaly"; :>> effectivity = "STS-119,123-999"; :>> changeNo = "086"; :>> measurementCount = 8; :>> numericLimitCount = 3; :>> sourcePage = 335; :>> isCounted = true; }
            part <'LCO-052'> lco_052 : LccItem { doc /* ET-04 */ :>> ssid = "ET-04"; :>> title = "External Tank LH2 Prepressurization Cycle Anomaly"; :>> effectivity = "STS-119,123-999"; :>> changeNo = "087"; :>> measurementCount = 2; :>> numericLimitCount = 0; :>> sourcePage = 339; :>> isCounted = true; }
            part <'LCO-053'> lco_053 : LccItem { doc /* ET-05 */ :>> ssid = "ET-05"; :>> title = "ET LH2 Ullage Pressure/Transducer Anomaly"; :>> effectivity = "STS-114-999"; :>> changeNo = "041"; :>> measurementCount = 6; :>> numericLimitCount = 6; :>> sourcePage = 341; :>> isCounted = true; }
            part <'LCO-054'> lco_054 : LccItem { doc /* ET-06 */ :>> ssid = "ET-06"; :>> title = "ET LO2 Ullage Pressure/Transducer Anomaly"; :>> effectivity = "STS-98,100,102,104,105,107-999"; :>> changeNo = "000"; :>> measurementCount = 6; :>> numericLimitCount = 6; :>> sourcePage = 345; :>> isCounted = true; }
            part <'LCO-055'> lco_055 : LccItem { doc /* ET-07 */ :>> ssid = "ET-07"; :>> title = "External Tank Intertank Temperature Anomaly"; :>> effectivity = "STS-104,105,107-999"; :>> changeNo = "008"; :>> measurementCount = 6; :>> numericLimitCount = 2; :>> sourcePage = 347; :>> isCounted = true; }
            part <'LCO-056'> lco_056 : LccItem { doc /* ET-08 */ :>> ssid = "ET-08"; :>> title = "ET Intertank Purge Termination Anomaly"; :>> effectivity = "STS-98,100,102,104,105,107-999"; :>> changeNo = "000"; :>> measurementCount = 4; :>> numericLimitCount = 4; :>> sourcePage = 349; :>> isCounted = true; }
            part <'LCO-057'> lco_057 : LccItem { doc /* ET-09 */ :>> ssid = "ET-09"; :>> title = "ET LH2 Flight Level Anomaly"; :>> effectivity = "STS-98,100,102,104,105,107-999"; :>> changeNo = "000"; :>> measurementCount = 8; :>> numericLimitCount = 8; :>> sourcePage = 351; :>> isCounted = true; }
            part <'LCO-058'> lco_058 : LccItem { doc /* ET-10 */ :>> ssid = "ET-10"; :>> title = "ET LO2 Flight Level Anomaly"; :>> effectivity = "STS 119,120,122-999"; :>> changeNo = "081"; :>> measurementCount = 9; :>> numericLimitCount = 9; :>> sourcePage = 353; :>> isCounted = true; }
            part <'LCO-059'> lco_059 : LccItem { doc /* ET-12 */ :>> ssid = "ET-12"; :>> title = "ET Bipod Heater System Deadfacing Anomaly"; :>> effectivity = "STS-114-999"; :>> changeNo = "042"; :>> measurementCount = 80; :>> numericLimitCount = 56; :>> sourcePage = 359; :>> isCounted = true; }
            part <'LCO-060'> lco_060 : LccItem { doc /* ET-13 */ :>> ssid = "ET-13"; :>> title = "ET Bipod Slot Temp Anomaly"; :>> effectivity = "STS-114-999"; :>> changeNo = "048"; :>> measurementCount = 16; :>> numericLimitCount = 8; :>> sourcePage = 363; :>> isCounted = true; }
            part <'LCO-061'> lco_061 : LccItem { doc /* ET-14 */ :>> ssid = "ET-14"; :>> title = "ET Bipod Web Temp Anomaly"; :>> effectivity = "STS-114-999"; :>> changeNo = "048"; :>> measurementCount = 8; :>> numericLimitCount = 8; :>> sourcePage = 367; :>> isCounted = true; }
            part <'LCO-062'> lco_062 : LccItem { doc /* ET-15 */ :>> ssid = "ET-15"; :>> title = "ET Camera System Deadfacing Anomaly"; :>> effectivity = "STS-114-999"; :>> changeNo = "041"; :>> measurementCount = 8; :>> numericLimitCount = 2; :>> sourcePage = 371; :>> isCounted = true; }
            part <'LCO-063'> lco_063 : LccItem { doc /* ET-16 */ :>> ssid = "ET-16"; :>> title = "ET LO2 Feedline Bellows Heater Current Anomaly"; :>> effectivity = "STS-114-999"; :>> changeNo = "056"; :>> measurementCount = 8; :>> numericLimitCount = 8; :>> sourcePage = 373; :>> isCounted = true; }
            part <'LCO-064'> lco_064 : LccItem { doc /* ET-17 */ :>> ssid = "ET-17"; :>> title = "ET LO2 Feedline Bellows Heater System Deadfacing Anomaly"; :>> effectivity = "STS-114-999"; :>> changeNo = "055"; :>> measurementCount = 6; :>> numericLimitCount = 4; :>> sourcePage = 377; :>> isCounted = true; }
            part <'LCO-528'> lco_528 : LccItem { doc /* ET-00 */ :>> ssid = "ET-00"; :>> title = ""; :>> effectivity = "N/A"; :>> changeNo = "055"; :>> measurementCount = 0; :>> numericLimitCount = 0; :>> sourcePage = 327; :>> isCounted = false; }
            part <'LCO-529'> lco_529 : LccItem { doc /* ET-11 */ :>> ssid = "ET-11"; :>> title = ""; :>> effectivity = "STS-98,100,102,104,105,107-999"; :>> changeNo = "000"; :>> measurementCount = 0; :>> numericLimitCount = 0; :>> sourcePage = 357; :>> isCounted = false; }
            part <'LCO-530'> lco_530 : LccItem { doc /* ET-FG01 */ :>> ssid = "ET-FG01"; :>> title = ""; :>> effectivity = "STS-104,105,107-999"; :>> changeNo = "008"; :>> measurementCount = 0; :>> numericLimitCount = 0; :>> sourcePage = 379; :>> isCounted = false; }
            part <'LCO-531'> lco_531 : LccItem { doc /* ET-FG02 */ :>> ssid = "ET-FG02"; :>> title = ""; :>> effectivity = "STS-104,105,107-999"; :>> changeNo = "008"; :>> measurementCount = 0; :>> numericLimitCount = 0; :>> sourcePage = 381; :>> isCounted = false; }
            part <'LCO-532'> lco_532 : LccItem { doc /* ET-FG03 */ :>> ssid = "ET-FG03"; :>> title = ""; :>> effectivity = "STS-98,100,102,104,105,107-999"; :>> changeNo = "000"; :>> measurementCount = 0; :>> numericLimitCount = 0; :>> sourcePage = 383; :>> isCounted = false; }
        }
        part sec_ssme : LccSection {
            :>> sectionNo = "20";
            :>> sectionTitle = "SPACE SHUTTLE MAIN ENGINE";
            :>> ssidPrefix = "SSME";
            part <'LCO-065'> lco_065 : LccItem { doc /* SSME-01 */ :>> ssid = "SSME-01"; :>> title = "SSME OPOV LOX Supply Line Temperature Anomaly"; :>> effectivity = "STS-107,112-999"; :>> changeNo = "027"; :>> measurementCount = 6; :>> numericLimitCount = 6; :>> sourcePage = 395; :>> isCounted = true; }
            part <'LCO-066'> lco_066 : LccItem { doc /* SSME-02 */ :>> ssid = "SSME-02"; :>> title = "SSME Main Fuel Valve Downstream Temperature Anomaly"; :>> effectivity = "STS-114-999"; :>> changeNo = "050"; :>> measurementCount = 6; :>> numericLimitCount = 6; :>> sourcePage = 397; :>> isCounted = true; }
            part <'LCO-067'> lco_067 : LccItem { doc /* SSME-03 */ :>> ssid = "SSME-03"; :>> title = "SSME HPOTP Intermediate Seal Purge Pressure Anomaly"; :>> effectivity = "STS-98,100,102,104,105,107-999"; :>> changeNo = "000"; :>> measurementCount = 6; :>> numericLimitCount = 6; :>> sourcePage = 399; :>> isCounted = true; }
            part <'LCO-068'> lco_068 : LccItem { doc /* SSME-04 */ :>> ssid = "SSME-04"; :>> title = "SSME Anti-Flood Valve Downstream Temperature Anomaly"; :>> effectivity = "STS-98,100,102,104,105,107-999"; :>> changeNo = "000"; :>> measurementCount = 6; :>> numericLimitCount = 6; :>> sourcePage = 401; :>> isCounted = true; }
            part <'LCO-069'> lco_069 : LccItem { doc /* SSME-05 */ :>> ssid = "SSME-05"; :>> title = "SSME MCC LOX Dome Temperature Anomaly"; :>> effectivity = "STS-119,125-999"; :>> changeNo = "093"; :>> measurementCount = 6; :>> numericLimitCount = 6; :>> sourcePage = 403; :>> isCounted = true; }
            part <'LCO-070'> lco_070 : LccItem { doc /* SSME-07 */ :>> ssid = "SSME-07"; :>> title = "SSME Phase/Mode Anomaly"; :>> effectivity = "STS-107-999"; :>> changeNo = "011"; :>> measurementCount = 6; :>> numericLimitCount = 0; :>> sourcePage = 409; :>> isCounted = true; }
            part <'LCO-071'> lco_071 : LccItem { doc /* SSME-08 */ :>> ssid = "SSME-08"; :>> title = "SSME Actuator Position Channel Anomaly"; :>> effectivity = "STS-98,100,102,104,105,107-999"; :>> changeNo = "000"; :>> measurementCount = 36; :>> numericLimitCount = 0; :>> sourcePage = 411; :>> isCounted = true; }
            part <'LCO-072'> lco_072 : LccItem { doc /* SSME-09 */ :>> ssid = "SSME-09"; :>> title = "SSME Fuel System Purge Pressure Anomaly"; :>> effectivity = "STS-119,125-999"; :>> changeNo = "094"; :>> measurementCount = 6; :>> numericLimitCount = 0; :>> sourcePage = 415; :>> isCounted = true; }
            part <'LCO-073'> lco_073 : LccItem { doc /* SSME-10 */ :>> ssid = "SSME-10"; :>> title = "SSME HPOTP Intermediate Seal Purge Pressure Anomaly"; :>> effectivity = "STS-114-999"; :>> changeNo = "050"; :>> measurementCount = 6; :>> numericLimitCount = 0; :>> sourcePage = 419; :>> isCounted = true; }
            part <'LCO-074'> lco_074 : LccItem { doc /* SSME-11 */ :>> ssid = "SSME-11"; :>> title = "SSME POGO Precharge Pressure Anomaly"; :>> effectivity = "STS-114-999"; :>> changeNo = "050"; :>> measurementCount = 6; :>> numericLimitCount = 0; :>> sourcePage = 423; :>> isCounted = true; }
            part <'LCO-075'> lco_075 : LccItem { doc /* SSME-12 */ :>> ssid = "SSME-12"; :>> title = "SSME POGO Recirculation Isolation Valve Anomaly"; :>> effectivity = "STS-98,100,102,104,105,107-999"; :>> changeNo = "000"; :>> measurementCount = 3; :>> numericLimitCount = 0; :>> sourcePage = 427; :>> isCounted = true; }
            part <'LCO-076'> lco_076 : LccItem { doc /* SSME-13 */ :>> ssid = "SSME-13"; :>> title = "SSME Propellant Bleed Valve Anomaly"; :>> effectivity = "STS-98,100,102,104,105,107-999"; :>> changeNo = "000"; :>> measurementCount = 6; :>> numericLimitCount = 0; :>> sourcePage = 429; :>> isCounted = true; }
            part <'LCO-077'> lco_077 : LccItem { doc /* SSME-14 */ :>> ssid = "SSME-14"; :>> title = "SSME Anti-Flood Valve Anomaly"; :>> effectivity = "STS-98,100,102,104,105,107-999"; :>> changeNo = "000"; :>> measurementCount = 6; :>> numericLimitCount = 6; :>> sourcePage = 431; :>> isCounted = true; }
            part <'LCO-078'> lco_078 : LccItem { doc /* SSME-15 */ :>> ssid = "SSME-15"; :>> title = "SSME Propellant Valve Hydraulic Temperature Anomaly"; :>> effectivity = "STS-98,100,102,104,105,107-999"; :>> changeNo = "000"; :>> measurementCount = 12; :>> numericLimitCount = 12; :>> sourcePage = 433; :>> isCounted = true; }
            part <'LCO-079'> lco_079 : LccItem { doc /* SSME-16 */ :>> ssid = "SSME-16"; :>> title = "SSME Emergency Shutdown Pressure Anomaly"; :>> effectivity = "STS-98,100,102,104,105,107-999"; :>> changeNo = "000"; :>> measurementCount = 6; :>> numericLimitCount = 0; :>> sourcePage = 435; :>> isCounted = true; }
            part <'LCO-080'> lco_080 : LccItem { doc /* SSME-17 */ :>> ssid = "SSME-17"; :>> title = "SSME LPFP Discharge Pressure Engine Ready Anomaly"; :>> effectivity = "STS-114-999"; :>> changeNo = "050"; :>> measurementCount = 6; :>> numericLimitCount = 6; :>> sourcePage = 437; :>> isCounted = true; }
            part <'LCO-081'> lco_081 : LccItem { doc /* SSME-18 */ :>> ssid = "SSME-18"; :>> title = "SSME LPFP Discharge Temperature Engine Ready Anomaly"; :>> effectivity = "STS-98,100,102,104,105,107-999"; :>> changeNo = "000"; :>> measurementCount = 6; :>> numericLimitCount = 6; :>> sourcePage = 439; :>> isCounted = true; }
            part <'LCO-082'> lco_082 : LccItem { doc /* SSME-19 */ :>> ssid = "SSME-19"; :>> title = "SSME LPOT Discharge Pressure Engine Ready Anomaly"; :>> effectivity = "STS-98,100,102,104,105,107-999"; :>> changeNo = "000"; :>> measurementCount = 6; :>> numericLimitCount = 6; :>> sourcePage = 441; :>> isCounted = true; }
            part <'LCO-083'> lco_083 : LccItem { doc /* SSME-20 */ :>> ssid = "SSME-20"; :>> title = "SSME Preburner Pump Discharge Temperature ENGINE READY Anomaly"; :>> effectivity = "STS-98,100,102,104,105,107-999"; :>> changeNo = "000"; :>> measurementCount = 6; :>> numericLimitCount = 6; :>> sourcePage = 443; :>> isCounted = true; }
            part <'LCO-084'> lco_084 : LccItem { doc /* SSME-21 */ :>> ssid = "SSME-21"; :>> title = "SSME Preburner Purge Pressure Engine Ready Anomaly"; :>> effectivity = "STS-98,100,102,104,105,107-999"; :>> changeNo = "000"; :>> measurementCount = 6; :>> numericLimitCount = 6; :>> sourcePage = 445; :>> isCounted = true; }
            part <'LCO-085'> lco_085 : LccItem { doc /* SSME-22 */ :>> ssid = "SSME-22"; :>> title = "SSME Emergency Shutdown Pressure ENGINE READY Anomaly"; :>> effectivity = "STS-98,100,102,104,105,107-999"; :>> changeNo = "000"; :>> measurementCount = 6; :>> numericLimitCount = 6; :>> sourcePage = 447; :>> isCounted = true; }
            part <'LCO-086'> lco_086 : LccItem { doc /* SSME-23 */ :>> ssid = "SSME-23"; :>> title = "SSME MOV/MFV Hydraulic Temperature ENGINE READY Anomaly"; :>> effectivity = "STS-98,100,102,104,105,107-999"; :>> changeNo = "000"; :>> measurementCount = 12; :>> numericLimitCount = 12; :>> sourcePage = 449; :>> isCounted = true; }
            part <'LCO-087'> lco_087 : LccItem { doc /* SSME-24 */ :>> ssid = "SSME-24"; :>> title = "SSME HPFT Discharge Temperature Qualification Anomaly"; :>> effectivity = "STS-114-999"; :>> changeNo = "050"; :>> measurementCount = 12; :>> numericLimitCount = 12; :>> sourcePage = 451; :>> isCounted = true; }
            part <'LCO-088'> lco_088 : LccItem { doc /* SSME-25 */ :>> ssid = "SSME-25"; :>> title = "SSME HPOT Discharge Temperature Qualification Anomaly"; :>> effectivity = "STS-104,105,107-999"; :>> changeNo = "004"; :>> measurementCount = 12; :>> numericLimitCount = 12; :>> sourcePage = 455; :>> isCounted = true; }
            part <'LCO-089'> lco_089 : LccItem { doc /* SSME-26 */ :>> ssid = "SSME-26"; :>> title = "SSME HPOT Intermediate Seal Purge Pressure Qualification Anomaly"; :>> effectivity = "STS-98,100,102,104,105,107-999"; :>> changeNo = "000"; :>> measurementCount = 6; :>> numericLimitCount = 6; :>> sourcePage = 457; :>> isCounted = true; }
            part <'LCO-090'> lco_090 : LccItem { doc /* SSME-29 */ :>> ssid = "SSME-29"; :>> title = "SSME Fuel Flow Rate Channel Qualification Anomaly"; :>> effectivity = "STS-107-999"; :>> changeNo = "011"; :>> measurementCount = 12; :>> numericLimitCount = 0; :>> sourcePage = 463; :>> isCounted = true; }
            part <'LCO-091'> lco_091 : LccItem { doc /* SSME-30 */ :>> ssid = "SSME-30"; :>> title = "SSME MCC Pressure Interchannel Qualification Anomaly"; :>> effectivity = "STS-98,100,102,104,105,107-999"; :>> changeNo = "000"; :>> measurementCount = 12; :>> numericLimitCount = 0; :>> sourcePage = 465; :>> isCounted = true; }
            part <'LCO-092'> lco_092 : LccItem { doc /* SSME-31 */ :>> ssid = "SSME-31"; :>> title = "SSME MCC Press Channel Qualification Anomaly"; :>> effectivity = "STS-98,100,102,104,105,107-999"; :>> changeNo = "000"; :>> measurementCount = 6; :>> numericLimitCount = 6; :>> sourcePage = 467; :>> isCounted = true; }
            part <'LCO-093'> lco_093 : LccItem { doc /* SSME-32 */ :>> ssid = "SSME-32"; :>> title = "SSME LPFP Discharge Pressure Qualification Anomaly"; :>> effectivity = "STS-98,100,102,104,105,107-999"; :>> changeNo = "000"; :>> measurementCount = 6; :>> numericLimitCount = 6; :>> sourcePage = 469; :>> isCounted = true; }
            part <'LCO-094'> lco_094 : LccItem { doc /* SSME-33 */ :>> ssid = "SSME-33"; :>> title = "SSME Preburner Purge Pressure Qualification Anomaly"; :>> effectivity = "STS-98,100,102,104,105,107-999"; :>> changeNo = "000"; :>> measurementCount = 6; :>> numericLimitCount = 6; :>> sourcePage = 471; :>> isCounted = true; }
            part <'LCO-095'> lco_095 : LccItem { doc /* SSME-34 */ :>> ssid = "SSME-34"; :>> title = "SSME LPFP Discharge Temperature Qualification Anomaly"; :>> effectivity = "STS-98,100,102,104,105,107-999"; :>> changeNo = "000"; :>> measurementCount = 6; :>> numericLimitCount = 6; :>> sourcePage = 473; :>> isCounted = true; }
            part <'LCO-096'> lco_096 : LccItem { doc /* SSME-35 */ :>> ssid = "SSME-35"; :>> title = "SSME Propellant Valve Position Anomaly"; :>> effectivity = "STS-98,100,102,104,105,107-999"; :>> changeNo = "000"; :>> measurementCount = 0; :>> numericLimitCount = 0; :>> sourcePage = 475; :>> isCounted = true; }
            part <'LCO-097'> lco_097 : LccItem { doc /* SSME-36 */ :>> ssid = "SSME-36"; :>> title = "ME Shutdown Switch Contact Disagree"; :>> effectivity = "STS-98,100,102,104,105,107-999"; :>> changeNo = "000"; :>> measurementCount = 3; :>> numericLimitCount = 0; :>> sourcePage = 477; :>> isCounted = true; }
            part <'LCO-098'> lco_098 : LccItem { doc /* SSME-37 */ :>> ssid = "SSME-37"; :>> title = "MPS Engine Limit Control Auto Switch Anomaly"; :>> effectivity = "STS-98,100,102,104,105,107-999"; :>> changeNo = "000"; :>> measurementCount = 3; :>> numericLimitCount = 0; :>> sourcePage = 479; :>> isCounted = true; }
            part <'LCO-099'> lco_099 : LccItem { doc /* SSME-38 */ :>> ssid = "SSME-38"; :>> title = "SSME Preburner Pump Discharge Temperature Sensor Qualification Anomaly"; :>> effectivity = "STS-98,100,102,104,105,107-999"; :>> changeNo = "000"; :>> measurementCount = 6; :>> numericLimitCount = 6; :>> sourcePage = 481; :>> isCounted = true; }
            part <'LCO-100'> lco_100 : LccItem { doc /* SSME-39 */ :>> ssid = "SSME-39"; :>> title = "SSME POGO Precharge Pressure Qualification Anomaly"; :>> effectivity = "STS-98,100,102,104,105,107-999"; :>> changeNo = "000"; :>> measurementCount = 6; :>> numericLimitCount = 6; :>> sourcePage = 483; :>> isCounted = true; }
            part <'LCO-101'> lco_101 : LccItem { doc /* SSME-43 */ :>> ssid = "SSME-43"; :>> title = "SSME MCC Pc Discriminator Qualification Anomaly"; :>> effectivity = "STS-98,100,102,104,105,107-999"; :>> changeNo = "000"; :>> measurementCount = 6; :>> numericLimitCount = 6; :>> sourcePage = 491; :>> isCounted = true; }
            part <'LCO-102'> lco_102 : LccItem { doc /* SSME-44 */ :>> ssid = "SSME-44"; :>> title = "SSME HPFTP Lift-Off Seal Anomaly"; :>> effectivity = "STS-114-999"; :>> changeNo = "050"; :>> measurementCount = 12; :>> numericLimitCount = 12; :>> sourcePage = 493; :>> isCounted = true; }
            part <'LCO-534'> lco_534 : LccItem { doc /* SSME-00 */ :>> ssid = "SSME-00"; :>> title = ""; :>> effectivity = "N/A"; :>> changeNo = "050"; :>> measurementCount = 0; :>> numericLimitCount = 0; :>> sourcePage = 389; :>> isCounted = false; }
            part <'LCO-535'> lco_535 : LccItem { doc /* SSME-06 */ :>> ssid = "SSME-06"; :>> title = ""; :>> effectivity = "STS-98,100,102,104,105,107-999"; :>> changeNo = "000"; :>> measurementCount = 0; :>> numericLimitCount = 0; :>> sourcePage = 407; :>> isCounted = false; }
            part <'LCO-536'> lco_536 : LccItem { doc /* SSME-27 */ :>> ssid = "SSME-27"; :>> title = ""; :>> effectivity = "STS-114-999"; :>> changeNo = "050"; :>> measurementCount = 0; :>> numericLimitCount = 0; :>> sourcePage = 459; :>> isCounted = false; }
            part <'LCO-537'> lco_537 : LccItem { doc /* SSME-28 */ :>> ssid = "SSME-28"; :>> title = ""; :>> effectivity = "STS-114-999"; :>> changeNo = "050"; :>> measurementCount = 0; :>> numericLimitCount = 0; :>> sourcePage = 461; :>> isCounted = false; }
            part <'LCO-538'> lco_538 : LccItem { doc /* SSME-40 */ :>> ssid = "SSME-40"; :>> title = ""; :>> effectivity = "STS-98,100,102,104,105,107-999"; :>> changeNo = "000"; :>> measurementCount = 0; :>> numericLimitCount = 0; :>> sourcePage = 485; :>> isCounted = false; }
            part <'LCO-539'> lco_539 : LccItem { doc /* SSME-41 */ :>> ssid = "SSME-41"; :>> title = ""; :>> effectivity = "STS-98,100,102,104,105,107-999"; :>> changeNo = "000"; :>> measurementCount = 0; :>> numericLimitCount = 0; :>> sourcePage = 487; :>> isCounted = false; }
            part <'LCO-540'> lco_540 : LccItem { doc /* SSME-42 */ :>> ssid = "SSME-42"; :>> title = ""; :>> effectivity = "STS-98,100,102,104,105,107-999"; :>> changeNo = "000"; :>> measurementCount = 0; :>> numericLimitCount = 0; :>> sourcePage = 489; :>> isCounted = false; }
        }
        part sec_mps : LccSection {
            :>> sectionNo = "21";
            :>> sectionTitle = "MAIN PROPULSION SYSTEM";
            :>> ssidPrefix = "MPS";
            part <'LCO-103'> lco_103 : LccItem { doc /* MPS-01 */ :>> ssid = "MPS-01"; :>> title = "MPS Helium Supply Pressure Anomaly"; :>> effectivity = "STS-98,100,102,104,105,107-999"; :>> changeNo = "000"; :>> measurementCount = 5; :>> numericLimitCount = 5; :>> sourcePage = 503; :>> isCounted = true; }
            part <'LCO-104'> lco_104 : LccItem { doc /* MPS-02 */ :>> ssid = "MPS-02"; :>> title = "MPS Aft/Mid Fuselage Helium Supply Temperature Anomaly"; :>> effectivity = "STS-98,100,102,104,105,107-999"; :>> changeNo = "000"; :>> measurementCount = 6; :>> numericLimitCount = 6; :>> sourcePage = 505; :>> isCounted = true; }
            part <'LCO-105'> lco_105 : LccItem { doc /* MPS-03 */ :>> ssid = "MPS-03"; :>> title = "SSME Helium Regulator Outlet Pressure Anomaly"; :>> effectivity = "STS-114-999"; :>> changeNo = "050"; :>> measurementCount = 12; :>> numericLimitCount = 12; :>> sourcePage = 507; :>> isCounted = true; }
            part <'LCO-106'> lco_106 : LccItem { doc /* MPS-04 */ :>> ssid = "MPS-04"; :>> title = "MPS LH2 Inboard Fill and Drain Valve Position/Power Indication Anomaly"; :>> effectivity = "STS-115-999"; :>> changeNo = "059"; :>> measurementCount = 3; :>> numericLimitCount = 0; :>> sourcePage = 511; :>> isCounted = true; }
            part <'LCO-107'> lco_107 : LccItem { doc /* MPS-05 */ :>> ssid = "MPS-05"; :>> title = "MPS LH2 Outboard Fill/Drain Valve Position Anomaly"; :>> effectivity = "STS-115-999"; :>> changeNo = "059"; :>> measurementCount = 1; :>> numericLimitCount = 0; :>> sourcePage = 515; :>> isCounted = true; }
            part <'LCO-108'> lco_108 : LccItem { doc /* MPS-06 */ :>> ssid = "MPS-06"; :>> title = "LH2 Fill Line Drain Anomaly"; :>> effectivity = "STS-98,100,102,104,105,107-999"; :>> changeNo = "000"; :>> measurementCount = 10; :>> numericLimitCount = 2; :>> sourcePage = 517; :>> isCounted = true; }
            part <'LCO-109'> lco_109 : LccItem { doc /* MPS-07 */ :>> ssid = "MPS-07"; :>> title = "MPS LO2 Inboard Fill and Drain Valve Position/ Power Indication Anomaly"; :>> effectivity = "STS-115-999"; :>> changeNo = "059"; :>> measurementCount = 3; :>> numericLimitCount = 0; :>> sourcePage = 519; :>> isCounted = true; }
            part <'LCO-110'> lco_110 : LccItem { doc /* MPS-08 */ :>> ssid = "MPS-08"; :>> title = "MPS LO2 Outboard Fill and Drain Valve Position Indication Anomaly"; :>> effectivity = "STS-115-999"; :>> changeNo = "059"; :>> measurementCount = 1; :>> numericLimitCount = 0; :>> sourcePage = 523; :>> isCounted = true; }
            part <'LCO-111'> lco_111 : LccItem { doc /* MPS-09 */ :>> ssid = "MPS-09"; :>> title = "LO2 Drainback Anomaly"; :>> effectivity = "STS-98,100,102,104,105,107-999"; :>> changeNo = "000"; :>> measurementCount = 6; :>> numericLimitCount = 2; :>> sourcePage = 525; :>> isCounted = true; }
            part <'LCO-112'> lco_112 : LccItem { doc /* MPS-10 */ :>> ssid = "MPS-10"; :>> title = "MPS LH2 Topping Valve Position Indication Anomaly"; :>> effectivity = "STS-98,100,102,104,105,107-999"; :>> changeNo = "000"; :>> measurementCount = 1; :>> numericLimitCount = 0; :>> sourcePage = 527; :>> isCounted = true; }
            part <'LCO-113'> lco_113 : LccItem { doc /* MPS-11 */ :>> ssid = "MPS-11"; :>> title = "MPS LH2 17 Inch Feed Manifold Disconnect Tem- perature/High Point Bleed Temperature Anomaly"; :>> effectivity = "STS-98,100,102,104,105,107-999"; :>> changeNo = "000"; :>> measurementCount = 4; :>> numericLimitCount = 2; :>> sourcePage = 529; :>> isCounted = true; }
            part <'LCO-114'> lco_114 : LccItem { doc /* MPS-12 */ :>> ssid = "MPS-12"; :>> title = "MPS LH2 High Point Bleed Valve Anomaly"; :>> effectivity = "STS-98,100,102,104,105,107-999"; :>> changeNo = "000"; :>> measurementCount = 3; :>> numericLimitCount = 2; :>> sourcePage = 531; :>> isCounted = true; }
            part <'LCO-115'> lco_115 : LccItem { doc /* MPS-13 */ :>> ssid = "MPS-13"; :>> title = "LO2 17 Inch Disconnect Valve/Latch Position Indication Anomaly"; :>> effectivity = "STS-98,100,102,104,105,107-999"; :>> changeNo = "000"; :>> measurementCount = 4; :>> numericLimitCount = 0; :>> sourcePage = 533; :>> isCounted = true; }
            part <'LCO-116'> lco_116 : LccItem { doc /* MPS-14 */ :>> ssid = "MPS-14"; :>> title = "LH2 17 Inch Disconnect Valve/Latch Position Indication Anomaly"; :>> effectivity = "STS-98,100,102,104,105,107-999"; :>> changeNo = "000"; :>> measurementCount = 4; :>> numericLimitCount = 0; :>> sourcePage = 535; :>> isCounted = true; }
            part <'LCO-117'> lco_117 : LccItem { doc /* MPS-15 */ :>> ssid = "MPS-15"; :>> title = "LO2 17 Inch Disconnect Valve/Latch Position Indication Anomaly"; :>> effectivity = "STS-98,100,102,104,105,107-999"; :>> changeNo = "000"; :>> measurementCount = 4; :>> numericLimitCount = 0; :>> sourcePage = 537; :>> isCounted = true; }
            part <'LCO-118'> lco_118 : LccItem { doc /* MPS-16 */ :>> ssid = "MPS-16"; :>> title = "LH2 17 Inch Disconnect Valve/Latch Position Indication Anomaly"; :>> effectivity = "STS-98,100,102,104,105,107-999"; :>> changeNo = "000"; :>> measurementCount = 4; :>> numericLimitCount = 0; :>> sourcePage = 539; :>> isCounted = true; }
            part <'LCO-119'> lco_119 : LccItem { doc /* MPS-17 */ :>> ssid = "MPS-17"; :>> title = "MPS LH2 17 Inch Feedline Disconnect Power/RPC Anomaly"; :>> effectivity = "STS-98,100,102,104,105,107-999"; :>> changeNo = "000"; :>> measurementCount = 12; :>> numericLimitCount = 0; :>> sourcePage = 541; :>> isCounted = true; }
            part <'LCO-120'> lco_120 : LccItem { doc /* MPS-18 */ :>> ssid = "MPS-18"; :>> title = "MPS LO2 17 Inch Feedline Disconnect Power/RPC Anomaly"; :>> effectivity = "STS-98,100,102,104,105,107-999"; :>> changeNo = "000"; :>> measurementCount = 12; :>> numericLimitCount = 0; :>> sourcePage = 543; :>> isCounted = true; }
            part <'LCO-121'> lco_121 : LccItem { doc /* MPS-19 */ :>> ssid = "MPS-19"; :>> title = "MPS LO2/LH2 Feedline Relief Isolation Valve Position/Power Indication Anomaly"; :>> effectivity = "STS-114-999"; :>> changeNo = "050"; :>> measurementCount = 6; :>> numericLimitCount = 0; :>> sourcePage = 545; :>> isCounted = true; }
            part <'LCO-122'> lco_122 : LccItem { doc /* MPS-20 */ :>> ssid = "MPS-20"; :>> title = "MPS RTLS Dump Valve Position Indication Anomaly"; :>> effectivity = "STS-114-999"; :>> changeNo = "050"; :>> measurementCount = 6; :>> numericLimitCount = 0; :>> sourcePage = 549; :>> isCounted = true; }
            part <'LCO-123'> lco_123 : LccItem { doc /* MPS-21 */ :>> ssid = "MPS-21"; :>> title = "MPS LO2 ECO Sensor Anomaly"; :>> effectivity = "STS-115-999"; :>> changeNo = "060"; :>> measurementCount = 4; :>> numericLimitCount = 0; :>> sourcePage = 551; :>> isCounted = true; }
            part <'LCO-124'> lco_124 : LccItem { doc /* MPS-22 */ :>> ssid = "MPS-22"; :>> title = "MPS LH2 Low Level Sensor Anomaly"; :>> effectivity = "STS 116-120,122-999"; :>> changeNo = "071"; :>> measurementCount = 4; :>> numericLimitCount = 0; :>> sourcePage = 553; :>> isCounted = true; }
            part <'LCO-125'> lco_125 : LccItem { doc /* MPS-23 */ :>> ssid = "MPS-23"; :>> title = "MPS ECO Sensor Power Supply Anomaly"; :>> effectivity = "STS-114-999"; :>> changeNo = "052"; :>> measurementCount = 2; :>> numericLimitCount = 0; :>> sourcePage = 557; :>> isCounted = true; }
            part <'LCO-126'> lco_126 : LccItem { doc /* MPS-24 */ :>> ssid = "MPS-24"; :>> title = "MPS LO2 Engine Inlet Temperature Anomaly - High"; :>> effectivity = "STS-98,100,102,104,105,107-999"; :>> changeNo = "000"; :>> measurementCount = 3; :>> numericLimitCount = 3; :>> sourcePage = 561; :>> isCounted = true; }
            part <'LCO-127'> lco_127 : LccItem { doc /* MPS-25 */ :>> ssid = "MPS-25"; :>> title = "MPS LO2 Engine Inlet Temperature Anomaly"; :>> effectivity = "STS-114-999"; :>> changeNo = "056"; :>> measurementCount = 3; :>> numericLimitCount = 3; :>> sourcePage = 563; :>> isCounted = true; }
            part <'LCO-128'> lco_128 : LccItem { doc /* MPS-26 */ :>> ssid = "MPS-26"; :>> title = "MPS Engine 1 LH2 Prevalve Position Indication Anomaly"; :>> effectivity = "STS-98,100,102,104,105,107-999"; :>> changeNo = "000"; :>> measurementCount = 2; :>> numericLimitCount = 0; :>> sourcePage = 567; :>> isCounted = true; }
            part <'LCO-129'> lco_129 : LccItem { doc /* MPS-27 */ :>> ssid = "MPS-27"; :>> title = "MPS Engine 1 LH2 Prevalve Power Indication Anomaly"; :>> effectivity = "STS-98,100,102,104,105,107-999"; :>> changeNo = "000"; :>> measurementCount = 6; :>> numericLimitCount = 0; :>> sourcePage = 569; :>> isCounted = true; }
            part <'LCO-130'> lco_130 : LccItem { doc /* MPS-28 */ :>> ssid = "MPS-28"; :>> title = "MPS Engine 2 LH2 Prevalve Position Indication Anomaly"; :>> effectivity = "STS-98,100,102,104,105,107-999"; :>> changeNo = "000"; :>> measurementCount = 2; :>> numericLimitCount = 0; :>> sourcePage = 571; :>> isCounted = true; }
            part <'LCO-131'> lco_131 : LccItem { doc /* MPS-29 */ :>> ssid = "MPS-29"; :>> title = "MPS Engine 2 LH2 Prevalve Power Indication Anomaly"; :>> effectivity = "STS-98,100,102,104,105,107-999"; :>> changeNo = "000"; :>> measurementCount = 6; :>> numericLimitCount = 0; :>> sourcePage = 573; :>> isCounted = true; }
            part <'LCO-132'> lco_132 : LccItem { doc /* MPS-30 */ :>> ssid = "MPS-30"; :>> title = "MPS Engine 3 LH2 Prevalve Position Indication Anomaly"; :>> effectivity = "STS-98,100,102,104,105,107-999"; :>> changeNo = "000"; :>> measurementCount = 2; :>> numericLimitCount = 0; :>> sourcePage = 575; :>> isCounted = true; }
            part <'LCO-133'> lco_133 : LccItem { doc /* MPS-31 */ :>> ssid = "MPS-31"; :>> title = "MPS Engine 3 LH2 Prevalve Power Indication Anomaly"; :>> effectivity = "STS-98,100,102,104,105,107-999"; :>> changeNo = "000"; :>> measurementCount = 6; :>> numericLimitCount = 0; :>> sourcePage = 577; :>> isCounted = true; }
            part <'LCO-134'> lco_134 : LccItem { doc /* MPS-32 */ :>> ssid = "MPS-32"; :>> title = "LH2 4 Inch Disconnect Valve Power Anomaly"; :>> effectivity = "STS-98,100,102,104,105,107-999"; :>> changeNo = "000"; :>> measurementCount = 2; :>> numericLimitCount = 0; :>> sourcePage = 579; :>> isCounted = true; }
            part <'LCO-135'> lco_135 : LccItem { doc /* MPS-33 */ :>> ssid = "MPS-33"; :>> title = "Main Engine LH2 Recirculation Anomaly"; :>> effectivity = "STS-115-999"; :>> changeNo = "060"; :>> measurementCount = 3; :>> numericLimitCount = 3; :>> sourcePage = 581; :>> isCounted = true; }
            part <'LCO-136'> lco_136 : LccItem { doc /* MPS-34 */ :>> ssid = "MPS-34"; :>> title = "MPS Valve Position Qualification Anomaly"; :>> effectivity = "STS-115-999"; :>> changeNo = "060"; :>> measurementCount = 6; :>> numericLimitCount = 0; :>> sourcePage = 585; :>> isCounted = true; }
            part <'LCO-137'> lco_137 : LccItem { doc /* MPS-35 */ :>> ssid = "MPS-35"; :>> title = "Engine 1 LO2 Prevalve Power Anomaly"; :>> effectivity = "STS 115-999"; :>> changeNo = "061"; :>> measurementCount = 4; :>> numericLimitCount = 0; :>> sourcePage = 589; :>> isCounted = true; }
            part <'LCO-138'> lco_138 : LccItem { doc /* MPS-36 */ :>> ssid = "MPS-36"; :>> title = "Engine 2 LO2 Prevalve Power Anomaly"; :>> effectivity = "STS 115-999"; :>> changeNo = "061"; :>> measurementCount = 4; :>> numericLimitCount = 0; :>> sourcePage = 593; :>> isCounted = true; }
            part <'LCO-139'> lco_139 : LccItem { doc /* MPS-37 */ :>> ssid = "MPS-37"; :>> title = "Engine 3 LO2 Prevalve Power Anomaly"; :>> effectivity = "STS 115-999"; :>> changeNo = "061"; :>> measurementCount = 4; :>> numericLimitCount = 0; :>> sourcePage = 597; :>> isCounted = true; }
            part <'LCO-140'> lco_140 : LccItem { doc /* MPS-38 */ :>> ssid = "MPS-38"; :>> title = "MPS Helium Isolation Valve Open Indication Anomaly"; :>> effectivity = "STS-114-999"; :>> changeNo = "050"; :>> measurementCount = 8; :>> numericLimitCount = 0; :>> sourcePage = 601; :>> isCounted = true; }
            part <'LCO-141'> lco_141 : LccItem { doc /* MPS-39 */ :>> ssid = "MPS-39"; :>> title = "MPS Pneumatic Helium Crossover Valve Power Anomaly"; :>> effectivity = "STS-98,100,102,104,105,107-999"; :>> changeNo = "000"; :>> measurementCount = 1; :>> numericLimitCount = 0; :>> sourcePage = 605; :>> isCounted = true; }
            part <'LCO-142'> lco_142 : LccItem { doc /* MPS-40 */ :>> ssid = "MPS-40"; :>> title = "MPS Helium Interconnect Valve Power Anomaly"; :>> effectivity = "STS-104,105,107-999"; :>> changeNo = "009"; :>> measurementCount = 6; :>> numericLimitCount = 0; :>> sourcePage = 607; :>> isCounted = true; }
            part <'LCO-143'> lco_143 : LccItem { doc /* MPS-41 */ :>> ssid = "MPS-41"; :>> title = "MPS Helium Supply Blowdown Valve Power Anomaly"; :>> effectivity = "STS-98,100,102,104,105,107-999"; :>> changeNo = "000"; :>> measurementCount = 2; :>> numericLimitCount = 0; :>> sourcePage = 609; :>> isCounted = true; }
            part <'LCO-144'> lco_144 : LccItem { doc /* MPS-42 */ :>> ssid = "MPS-42"; :>> title = "MPS Repressurization Valve Power Anomaly"; :>> effectivity = "STS-98,100,102,104,105,107-999"; :>> changeNo = "000"; :>> measurementCount = 6; :>> numericLimitCount = 0; :>> sourcePage = 611; :>> isCounted = true; }
            part <'LCO-145'> lco_145 : LccItem { doc /* MPS-44 */ :>> ssid = "MPS-44"; :>> title = "MPS GH2 Pressure Flow Control Valve Power Anomaly"; :>> effectivity = "STS-98,100,102,104,105,107-999"; :>> changeNo = "000"; :>> measurementCount = 3; :>> numericLimitCount = 0; :>> sourcePage = 615; :>> isCounted = true; }
            part <'LCO-146'> lco_146 : LccItem { doc /* MPS-45 */ :>> ssid = "MPS-45"; :>> title = "MPS GH2 Pressure Flow Control Valve Power Anomaly"; :>> effectivity = "STS-98,100,102,104,105,107-999"; :>> changeNo = "000"; :>> measurementCount = 3; :>> numericLimitCount = 0; :>> sourcePage = 617; :>> isCounted = true; }
            part <'LCO-147'> lco_147 : LccItem { doc /* MPS-46 */ :>> ssid = "MPS-46"; :>> title = "Pneu Helium Regulator Outlet Pressure Anomaly"; :>> effectivity = "STS-114-999"; :>> changeNo = "050"; :>> measurementCount = 4; :>> numericLimitCount = 4; :>> sourcePage = 619; :>> isCounted = true; }
            part <'LCO-148'> lco_148 : LccItem { doc /* MPS-47 */ :>> ssid = "MPS-47"; :>> title = "MPS LO2 Overboard Bleed Valve (PV19) Position Qualification Anomaly"; :>> effectivity = "STS-98,100,102,104,105,107-999"; :>> changeNo = "000"; :>> measurementCount = 2; :>> numericLimitCount = 0; :>> sourcePage = 623; :>> isCounted = true; }
            part <'LCO-149'> lco_149 : LccItem { doc /* MPS-48 */ :>> ssid = "MPS-48"; :>> title = "Orbiter/ET LH2 Disconnect Purge Anomaly"; :>> effectivity = "STS-116-120,122-999"; :>> changeNo = "070"; :>> measurementCount = 12; :>> numericLimitCount = 12; :>> sourcePage = 625; :>> isCounted = true; }
            part <'LCO-150'> lco_150 : LccItem { doc /* MPS-49 */ :>> ssid = "MPS-49"; :>> title = "MPS LO2 Outboard Fill and Drain Valve (PV9) Open and Close Power Anomaly"; :>> effectivity = "STS-119,125-999"; :>> changeNo = "094"; :>> measurementCount = 2; :>> numericLimitCount = 0; :>> sourcePage = 631; :>> isCounted = true; }
            part <'LCO-151'> lco_151 : LccItem { doc /* MPS-50 */ :>> ssid = "MPS-50"; :>> title = "MPS LO2 Inboard Fill and Drain Valve (PV10) Open and Close Power Anomaly"; :>> effectivity = "STS-119,125-999"; :>> changeNo = "094"; :>> measurementCount = 2; :>> numericLimitCount = 0; :>> sourcePage = 635; :>> isCounted = true; }
            part <'LCO-152'> lco_152 : LccItem { doc /* MPS-51 */ :>> ssid = "MPS-51"; :>> title = "MPS LH2 Outboard Fill and Drain Valve (PV11) Open and Close Power Anomaly"; :>> effectivity = "STS-119,125-999"; :>> changeNo = "094"; :>> measurementCount = 2; :>> numericLimitCount = 0; :>> sourcePage = 639; :>> isCounted = true; }
            part <'LCO-153'> lco_153 : LccItem { doc /* MPS-52 */ :>> ssid = "MPS-52"; :>> title = "MPS LH2 Inboard Fill and Drain Valve (PV12) Open and Close Power Anomaly"; :>> effectivity = "STS-119,125-999"; :>> changeNo = "094"; :>> measurementCount = 2; :>> numericLimitCount = 0; :>> sourcePage = 643; :>> isCounted = true; }
            part <'LCO-154'> lco_154 : LccItem { doc /* MPS-53 */ :>> ssid = "MPS-53"; :>> title = "MPS LH2 Low Level Sensor Voltage Anomaly"; :>> effectivity = "STS-119,125-999"; :>> changeNo = "095"; :>> measurementCount = 8; :>> numericLimitCount = 8; :>> sourcePage = 647; :>> isCounted = true; }
            part <'LCO-541'> lco_541 : LccItem { doc /* MPS-00 */ :>> ssid = "MPS-00"; :>> title = ""; :>> effectivity = "N/A"; :>> changeNo = "079"; :>> measurementCount = 0; :>> numericLimitCount = 0; :>> sourcePage = 497; :>> isCounted = false; }
            part <'LCO-542'> lco_542 : LccItem { doc /* MPS-43 */ :>> ssid = "MPS-43"; :>> title = ""; :>> effectivity = "STS-98,100,102,104,105,107-999"; :>> changeNo = "000"; :>> measurementCount = 0; :>> numericLimitCount = 0; :>> sourcePage = 613; :>> isCounted = false; }
        }
        part sec_rcs : LccSection {
            :>> sectionNo = "22";
            :>> sectionTitle = "REACTION CONTROL SUBSYSTEM";
            :>> ssidPrefix = "RCS";
            part <'LCO-155'> lco_155 : LccItem { doc /* RCS-01 */ :>> ssid = "RCS-01"; :>> title = "RCS Helium Tank Anomaly"; :>> effectivity = "STS-107-999"; :>> changeNo = "011"; :>> measurementCount = 18; :>> numericLimitCount = 0; :>> sourcePage = 655; :>> isCounted = true; }
            part <'LCO-156'> lco_156 : LccItem { doc /* RCS-02 */ :>> ssid = "RCS-02"; :>> title = "RCS Propellant Tank Pressure/Temperature Anomaly"; :>> effectivity = "STS-107-999"; :>> changeNo = "011"; :>> measurementCount = 18; :>> numericLimitCount = 0; :>> sourcePage = 659; :>> isCounted = true; }
            part <'LCO-157'> lco_157 : LccItem { doc /* RCS-03 */ :>> ssid = "RCS-03"; :>> title = "RCS Helium Isolation Valve Anomaly"; :>> effectivity = "STS-107-999"; :>> changeNo = "011"; :>> measurementCount = 12; :>> numericLimitCount = 0; :>> sourcePage = 663; :>> isCounted = true; }
            part <'LCO-158'> lco_158 : LccItem { doc /* RCS-04 */ :>> ssid = "RCS-04"; :>> title = "RCS Propellant Tank Isolation Valve Anomaly"; :>> effectivity = "STS-114-999"; :>> changeNo = "036"; :>> measurementCount = 32; :>> numericLimitCount = 0; :>> sourcePage = 665; :>> isCounted = true; }
            part <'LCO-159'> lco_159 : LccItem { doc /* RCS-05 */ :>> ssid = "RCS-05"; :>> title = "RCS Manifold Isolation Valve Anomaly"; :>> effectivity = "STS-107-999"; :>> changeNo = "011"; :>> measurementCount = 60; :>> numericLimitCount = 0; :>> sourcePage = 669; :>> isCounted = true; }
            part <'LCO-160'> lco_160 : LccItem { doc /* RCS-06 */ :>> ssid = "RCS-06"; :>> title = "RCS Thrust Injector Temperature Anomaly"; :>> effectivity = "STS-114-999"; :>> changeNo = "036"; :>> measurementCount = 80; :>> numericLimitCount = 80; :>> sourcePage = 673; :>> isCounted = true; }
            part <'LCO-161'> lco_161 : LccItem { doc /* RCS-07 */ :>> ssid = "RCS-07"; :>> title = "RCS Vernier Thrust Injector Temperature Anomaly"; :>> effectivity = "STS-114-999"; :>> changeNo = "036"; :>> measurementCount = 16; :>> numericLimitCount = 16; :>> sourcePage = 679; :>> isCounted = true; }
            part <'LCO-162'> lco_162 : LccItem { doc /* RCS-08 */ :>> ssid = "RCS-08"; :>> title = "RCS Thrust Chamber Pressure Anomaly"; :>> effectivity = "STS-114-999"; :>> changeNo = "036"; :>> measurementCount = 38; :>> numericLimitCount = 38; :>> sourcePage = 683; :>> isCounted = true; }
            part <'LCO-163'> lco_163 : LccItem { doc /* RCS-09 */ :>> ssid = "RCS-09"; :>> title = "RCS Manifold Pressure Anomaly"; :>> effectivity = "STS-98,100,102,104,105,107-999"; :>> changeNo = "000"; :>> measurementCount = 24; :>> numericLimitCount = 0; :>> sourcePage = 689; :>> isCounted = true; }
            part <'LCO-164'> lco_164 : LccItem { doc /* RCS-10 */ :>> ssid = "RCS-10"; :>> title = "RCS Crossfeed Valve Anomaly"; :>> effectivity = "STS-107-999"; :>> changeNo = "011"; :>> measurementCount = 20; :>> numericLimitCount = 0; :>> sourcePage = 693; :>> isCounted = true; }
            part <'LCO-543'> lco_543 : LccItem { doc /* RCS-00 */ :>> ssid = "RCS-00"; :>> title = ""; :>> effectivity = "N/A"; :>> changeNo = "000"; :>> measurementCount = 0; :>> numericLimitCount = 0; :>> sourcePage = 651; :>> isCounted = false; }
            part <'LCO-544'> lco_544 : LccItem { doc /* RCS-FG01 */ :>> ssid = "RCS-FG01"; :>> title = ""; :>> effectivity = "STS-98,100,102,104,105,107-999"; :>> changeNo = "000"; :>> measurementCount = 0; :>> numericLimitCount = 0; :>> sourcePage = 697; :>> isCounted = false; }
            part <'LCO-545'> lco_545 : LccItem { doc /* RCS-FG02 */ :>> ssid = "RCS-FG02"; :>> title = ""; :>> effectivity = "STS-98,100,102,104,105,107-999"; :>> changeNo = "000"; :>> measurementCount = 0; :>> numericLimitCount = 0; :>> sourcePage = 699; :>> isCounted = false; }
        }
        part sec_oms : LccSection {
            :>> sectionNo = "23";
            :>> sectionTitle = "ORBITAL MANEUVERING SYSTEM";
            :>> ssidPrefix = "OMS";
            part <'LCO-165'> lco_165 : LccItem { doc /* OMS-01 */ :>> ssid = "OMS-01"; :>> title = "OMS Helium Tank Pressure Anomaly"; :>> effectivity = "STS-107-999"; :>> changeNo = "011"; :>> measurementCount = 4; :>> numericLimitCount = 0; :>> sourcePage = 705; :>> isCounted = true; }
            part <'LCO-166'> lco_166 : LccItem { doc /* OMS-02 */ :>> ssid = "OMS-02"; :>> title = "OMS Helium Isolation Valve Anomaly"; :>> effectivity = "STS-107-999"; :>> changeNo = "011"; :>> measurementCount = 4; :>> numericLimitCount = 0; :>> sourcePage = 707; :>> isCounted = true; }
            part <'LCO-167'> lco_167 : LccItem { doc /* OMS-03 */ :>> ssid = "OMS-03"; :>> title = "OMS Vapor Isolation Valve Anomaly"; :>> effectivity = "STS-107-999"; :>> changeNo = "011"; :>> measurementCount = 4; :>> numericLimitCount = 0; :>> sourcePage = 709; :>> isCounted = true; }
            part <'LCO-168'> lco_168 : LccItem { doc /* OMS-04 */ :>> ssid = "OMS-04"; :>> title = "OMS Engine Feedline Temperature Anomaly"; :>> effectivity = "STS-98,100,102,104,105,107-999"; :>> changeNo = "000"; :>> measurementCount = 6; :>> numericLimitCount = 6; :>> sourcePage = 711; :>> isCounted = true; }
            part <'LCO-169'> lco_169 : LccItem { doc /* OMS-05 */ :>> ssid = "OMS-05"; :>> title = "OMS Ullage Pressure Anomaly"; :>> effectivity = "STS-98,100,102,104,105,107-999"; :>> changeNo = "000"; :>> measurementCount = 4; :>> numericLimitCount = 4; :>> sourcePage = 713; :>> isCounted = true; }
            part <'LCO-170'> lco_170 : LccItem { doc /* OMS-06 */ :>> ssid = "OMS-06"; :>> title = "OMS Propellant Tank Isolation Valve Anomaly"; :>> effectivity = "STS-107-999"; :>> changeNo = "011"; :>> measurementCount = 16; :>> numericLimitCount = 0; :>> sourcePage = 715; :>> isCounted = true; }
            part <'LCO-171'> lco_171 : LccItem { doc /* OMS-07 */ :>> ssid = "OMS-07"; :>> title = "OMS Crossfeed Valves Anomaly"; :>> effectivity = "STS-119,120,122-999"; :>> changeNo = "081"; :>> measurementCount = 16; :>> numericLimitCount = 0; :>> sourcePage = 717; :>> isCounted = true; }
            part <'LCO-172'> lco_172 : LccItem { doc /* OMS-08 */ :>> ssid = "OMS-08"; :>> title = "OMS GN2 Tank Pressure Anomaly"; :>> effectivity = "STS-114-999"; :>> changeNo = "036"; :>> measurementCount = 4; :>> numericLimitCount = 0; :>> sourcePage = 721; :>> isCounted = true; }
            part <'LCO-173'> lco_173 : LccItem { doc /* OMS-09 */ :>> ssid = "OMS-09"; :>> title = "OMS GN2 Regulator Pressure Anomaly"; :>> effectivity = "STS-107-999"; :>> changeNo = "011"; :>> measurementCount = 4; :>> numericLimitCount = 4; :>> sourcePage = 725; :>> isCounted = true; }
            part <'LCO-174'> lco_174 : LccItem { doc /* OMS-10 */ :>> ssid = "OMS-10"; :>> title = "OMS GN2 Pressurization Valve Position Anomaly"; :>> effectivity = "STS-107-999"; :>> changeNo = "011"; :>> measurementCount = 2; :>> numericLimitCount = 0; :>> sourcePage = 727; :>> isCounted = true; }
            part <'LCO-175'> lco_175 : LccItem { doc /* OMS-11 */ :>> ssid = "OMS-11"; :>> title = "OMS Engine Purge Valve Anomaly"; :>> effectivity = "STS-107-999"; :>> changeNo = "011"; :>> measurementCount = 4; :>> numericLimitCount = 0; :>> sourcePage = 729; :>> isCounted = true; }
            part <'LCO-176'> lco_176 : LccItem { doc /* OMS-12 */ :>> ssid = "OMS-12"; :>> title = "OMS Engine Injector Temperature Anomaly"; :>> effectivity = "STS-98,100,102,104,105,107-999"; :>> changeNo = "000"; :>> measurementCount = 4; :>> numericLimitCount = 2; :>> sourcePage = 731; :>> isCounted = true; }
            part <'LCO-177'> lco_177 : LccItem { doc /* OMS-13 */ :>> ssid = "OMS-13"; :>> title = "OMS Engine Inlet Pressure Anomaly"; :>> effectivity = "STS-107-999"; :>> changeNo = "011"; :>> measurementCount = 4; :>> numericLimitCount = 0; :>> sourcePage = 733; :>> isCounted = true; }
            part <'LCO-178'> lco_178 : LccItem { doc /* OMS-14 */ :>> ssid = "OMS-14"; :>> title = "OMS Engine Chamber Pressure Anomaly"; :>> effectivity = "STS-98,100,102,104,105,107-999"; :>> changeNo = "000"; :>> measurementCount = 4; :>> numericLimitCount = 4; :>> sourcePage = 735; :>> isCounted = true; }
            part <'LCO-179'> lco_179 : LccItem { doc /* OMS-15 */ :>> ssid = "OMS-15"; :>> title = "OMS Engine Bi-Propellant Valve Anomaly"; :>> effectivity = "STS-98,100,102,104,105,107-999"; :>> changeNo = "000"; :>> measurementCount = 4; :>> numericLimitCount = 0; :>> sourcePage = 737; :>> isCounted = true; }
            part <'LCO-180'> lco_180 : LccItem { doc /* OMS-16 */ :>> ssid = "OMS-16"; :>> title = "OMS Pod Temperature Measurement Anomaly"; :>> effectivity = "STS-107-999"; :>> changeNo = "011"; :>> measurementCount = 34; :>> numericLimitCount = 30; :>> sourcePage = 739; :>> isCounted = true; }
            part <'LCO-181'> lco_181 : LccItem { doc /* OMS-17 */ :>> ssid = "OMS-17"; :>> title = "OMS Crossfeed Temperature Measurement Anomaly"; :>> effectivity = "STS-107-999"; :>> changeNo = "011"; :>> measurementCount = 23; :>> numericLimitCount = 23; :>> sourcePage = 743; :>> isCounted = true; }
            part <'LCO-546'> lco_546 : LccItem { doc /* OMS-00 */ :>> ssid = "OMS-00"; :>> title = ""; :>> effectivity = "N/A"; :>> changeNo = "000"; :>> measurementCount = 0; :>> numericLimitCount = 0; :>> sourcePage = 701; :>> isCounted = false; }
            part <'LCO-547'> lco_547 : LccItem { doc /* OMS-18 */ :>> ssid = "OMS-18"; :>> title = ""; :>> effectivity = "STS-98,100,102,104,105,107-999"; :>> changeNo = "000"; :>> measurementCount = 0; :>> numericLimitCount = 0; :>> sourcePage = 747; :>> isCounted = false; }
            part <'LCO-548'> lco_548 : LccItem { doc /* OMS-FG01 */ :>> ssid = "OMS-FG01"; :>> title = ""; :>> effectivity = "STS-98,100,102,104,105,107-999"; :>> changeNo = "000"; :>> measurementCount = 0; :>> numericLimitCount = 0; :>> sourcePage = 749; :>> isCounted = false; }
        }
        part sec_prsd : LccSection {
            :>> sectionNo = "24";
            :>> sectionTitle = "POWER REACTANT SUPPLY AND DISTRIBUTION";
            :>> ssidPrefix = "PRSD";
            part <'LCO-182'> lco_182 : LccItem { doc /* PRSD-01 */ :>> ssid = "PRSD-01"; :>> title = "PRSD O2 Tank Control Pressure Anomaly"; :>> effectivity = "STS-119,122-999"; :>> changeNo = "084"; :>> measurementCount = 11; :>> numericLimitCount = 11; :>> sourcePage = 755; :>> isCounted = true; }
            part <'LCO-183'> lco_183 : LccItem { doc /* PRSD-02 */ :>> ssid = "PRSD-02"; :>> title = "PRSD Manifold Isolation Valve Anomaly"; :>> effectivity = "STS-107-999"; :>> changeNo = "011"; :>> measurementCount = 4; :>> numericLimitCount = 0; :>> sourcePage = 759; :>> isCounted = true; }
            part <'LCO-184'> lco_184 : LccItem { doc /* PRSD-03 */ :>> ssid = "PRSD-03"; :>> title = "PRSD FCP Reactant Valve Anomaly"; :>> effectivity = "STS-107-999"; :>> changeNo = "011"; :>> measurementCount = 12; :>> numericLimitCount = 0; :>> sourcePage = 761; :>> isCounted = true; }
            part <'LCO-185'> lco_185 : LccItem { doc /* PRSD-04 */ :>> ssid = "PRSD-04"; :>> title = "PRSD O2 Tank Heater Current Sensor Anomaly"; :>> effectivity = "STS-98,100,102,104,105,107-999"; :>> changeNo = "000"; :>> measurementCount = 20; :>> numericLimitCount = 0; :>> sourcePage = 763; :>> isCounted = true; }
            part <'LCO-186'> lco_186 : LccItem { doc /* PRSD-05 */ :>> ssid = "PRSD-05"; :>> title = "PRSD Gas Supply Valve Anomaly"; :>> effectivity = "STS-107-999"; :>> changeNo = "011"; :>> measurementCount = 2; :>> numericLimitCount = 0; :>> sourcePage = 765; :>> isCounted = true; }
            part <'LCO-187'> lco_187 : LccItem { doc /* PRSD-06 */ :>> ssid = "PRSD-06"; :>> title = "PRSD H2 Tank Heater Control Pressure Anomaly"; :>> effectivity = "STS-119,122-999"; :>> changeNo = "084"; :>> measurementCount = 11; :>> numericLimitCount = 11; :>> sourcePage = 767; :>> isCounted = true; }
            part <'LCO-188'> lco_188 : LccItem { doc /* PRSD-07 */ :>> ssid = "PRSD-07"; :>> title = "PRSD O2 Tank Quantity Anomaly"; :>> effectivity = "STS-98,100,102,104,105,107-999"; :>> changeNo = "000"; :>> measurementCount = 9; :>> numericLimitCount = 0; :>> sourcePage = 771; :>> isCounted = true; }
            part <'LCO-189'> lco_189 : LccItem { doc /* PRSD-08 */ :>> ssid = "PRSD-08"; :>> title = "PRSD H2 Tank Quantity Anomaly"; :>> effectivity = "STS-98,100,102,104,105,107-999"; :>> changeNo = "000"; :>> measurementCount = 9; :>> numericLimitCount = 0; :>> sourcePage = 773; :>> isCounted = true; }
            part <'LCO-190'> lco_190 : LccItem { doc /* PRSD-09 */ :>> ssid = "PRSD-09"; :>> title = "PRSD O2 ECS Supply Valve Anomaly"; :>> effectivity = "STS-114-999"; :>> changeNo = "046"; :>> measurementCount = 2; :>> numericLimitCount = 0; :>> sourcePage = 775; :>> isCounted = true; }
            part <'LCO-549'> lco_549 : LccItem { doc /* PRSD-00 */ :>> ssid = "PRSD-00"; :>> title = ""; :>> effectivity = "N/A"; :>> changeNo = "000"; :>> measurementCount = 0; :>> numericLimitCount = 0; :>> sourcePage = 751; :>> isCounted = false; }
        }
        part sec_fcp : LccSection {
            :>> sectionNo = "25";
            :>> sectionTitle = "FUEL CELL POWERPLANT";
            :>> ssidPrefix = "FCP";
            part <'LCO-191'> lco_191 : LccItem { doc /* FCP-01 */ :>> ssid = "FCP-01"; :>> title = "Fuel Cell Performance Anomaly"; :>> effectivity = "STS-114-999"; :>> changeNo = "056"; :>> measurementCount = 9; :>> numericLimitCount = 0; :>> sourcePage = 781; :>> isCounted = true; }
            part <'LCO-192'> lco_192 : LccItem { doc /* FCP-02 */ :>> ssid = "FCP-02"; :>> title = "Fuel Cell Thermal Performance Anomaly"; :>> effectivity = "STS-98,100,102,104,105,107-999"; :>> changeNo = "000"; :>> measurementCount = 12; :>> numericLimitCount = 0; :>> sourcePage = 787; :>> isCounted = true; }
            part <'LCO-193'> lco_193 : LccItem { doc /* FCP-03 */ :>> ssid = "FCP-03"; :>> title = "Fuel Cell Substack Delta Anomaly"; :>> effectivity = "STS-107-999"; :>> changeNo = "011"; :>> measurementCount = 9; :>> numericLimitCount = 0; :>> sourcePage = 791; :>> isCounted = true; }
            part <'LCO-194'> lco_194 : LccItem { doc /* FCP-04 */ :>> ssid = "FCP-04"; :>> title = "Fuel Cell Coolant Pump Anomaly"; :>> effectivity = "STS-107-999"; :>> changeNo = "011"; :>> measurementCount = 6; :>> numericLimitCount = 3; :>> sourcePage = 795; :>> isCounted = true; }
            part <'LCO-195'> lco_195 : LccItem { doc /* FCP-05 */ :>> ssid = "FCP-05"; :>> title = "Fuel Cell Water Condition Anomaly"; :>> effectivity = "STS-107-999"; :>> changeNo = "011"; :>> measurementCount = 4; :>> numericLimitCount = 0; :>> sourcePage = 799; :>> isCounted = true; }
            part <'LCO-196'> lco_196 : LccItem { doc /* FCP-06 */ :>> ssid = "FCP-06"; :>> title = "Fuel Cell Water Relief System Temperature Anomaly"; :>> effectivity = "STS-107-999"; :>> changeNo = "032"; :>> measurementCount = 12; :>> numericLimitCount = 12; :>> sourcePage = 801; :>> isCounted = true; }
            part <'LCO-550'> lco_550 : LccItem { doc /* FCP-00 */ :>> ssid = "FCP-00"; :>> title = ""; :>> effectivity = "N/A"; :>> changeNo = "000"; :>> measurementCount = 0; :>> numericLimitCount = 0; :>> sourcePage = 777; :>> isCounted = false; }
            part <'LCO-551'> lco_551 : LccItem { doc /* FCP-FG01 */ :>> ssid = "FCP-FG01"; :>> title = ""; :>> effectivity = "STS-114-999"; :>> changeNo = "056"; :>> measurementCount = 0; :>> numericLimitCount = 0; :>> sourcePage = 805; :>> isCounted = false; }
            part <'LCO-552'> lco_552 : LccItem { doc /* FCP-FG02 */ :>> ssid = "FCP-FG02"; :>> title = ""; :>> effectivity = "STS-98,100,102,104,105,107-999"; :>> changeNo = "000"; :>> measurementCount = 0; :>> numericLimitCount = 0; :>> sourcePage = 807; :>> isCounted = false; }
            part <'LCO-553'> lco_553 : LccItem { doc /* FCP-FG03 */ :>> ssid = "FCP-FG03"; :>> title = ""; :>> effectivity = "STS-98,100,102,104,105,107-999"; :>> changeNo = "000"; :>> measurementCount = 0; :>> numericLimitCount = 0; :>> sourcePage = 809; :>> isCounted = false; }
        }
        part sec_epdc : LccSection {
            :>> sectionNo = "26";
            :>> sectionTitle = "ELECTRICAL POWER DISTRIBUTION AND CONTROL";
            :>> ssidPrefix = "EPDC";
            part <'LCO-197'> lco_197 : LccItem { doc /* EPDC-01 */ :>> ssid = "EPDC-01"; :>> title = "Orbiter Main Bus Voltage Anomaly"; :>> effectivity = "STS-107-999"; :>> changeNo = "011"; :>> measurementCount = 6; :>> numericLimitCount = 6; :>> sourcePage = 815; :>> isCounted = true; }
            part <'LCO-198'> lco_198 : LccItem { doc /* EPDC-02 */ :>> ssid = "EPDC-02"; :>> title = "Orbiter Control Bus RPC Anomaly"; :>> effectivity = "STS-107,110-999"; :>> changeNo = "021"; :>> measurementCount = 9; :>> numericLimitCount = 0; :>> sourcePage = 819; :>> isCounted = true; }
            part <'LCO-199'> lco_199 : LccItem { doc /* EPDC-03 */ :>> ssid = "EPDC-03"; :>> title = "Orbiter AC Bus Voltage Anomaly"; :>> effectivity = "107,109-999"; :>> changeNo = "018"; :>> measurementCount = 9; :>> numericLimitCount = 9; :>> sourcePage = 821; :>> isCounted = true; }
            part <'LCO-200'> lco_200 : LccItem { doc /* EPDC-04 */ :>> ssid = "EPDC-04"; :>> title = "Orbiter AC Bus Phase Current Anomaly"; :>> effectivity = "STS-107-999"; :>> changeNo = "011"; :>> measurementCount = 9; :>> numericLimitCount = 9; :>> sourcePage = 825; :>> isCounted = true; }
            part <'LCO-201'> lco_201 : LccItem { doc /* EPDC-05 */ :>> ssid = "EPDC-05"; :>> title = "SRB Bus Power Anomaly"; :>> effectivity = "STS-98,100,102,104,105,107-999"; :>> changeNo = "000"; :>> measurementCount = 4; :>> numericLimitCount = 0; :>> sourcePage = 827; :>> isCounted = true; }
            part <'LCO-202'> lco_202 : LccItem { doc /* EPDC-06 */ :>> ssid = "EPDC-06"; :>> title = "Essential Bus Source Anomaly"; :>> effectivity = "STS-107-999"; :>> changeNo = "011"; :>> measurementCount = 6; :>> numericLimitCount = 0; :>> sourcePage = 829; :>> isCounted = true; }
            part <'LCO-203'> lco_203 : LccItem { doc /* EPDC-07 */ :>> ssid = "EPDC-07"; :>> title = "Essential Bus Source Anomaly"; :>> effectivity = "STS-98,100,102,104,105,107-999"; :>> changeNo = "000"; :>> measurementCount = 3; :>> numericLimitCount = 0; :>> sourcePage = 833; :>> isCounted = true; }
            part <'LCO-204'> lco_204 : LccItem { doc /* EPDC-08 */ :>> ssid = "EPDC-08"; :>> title = "Orbiter Master Events Controller (MEC) Power Anomaly"; :>> effectivity = "STS-119,125-999"; :>> changeNo = "097"; :>> measurementCount = 6; :>> numericLimitCount = 0; :>> sourcePage = 835; :>> isCounted = true; }
            part <'LCO-205'> lco_205 : LccItem { doc /* EPDC-09 */ :>> ssid = "EPDC-09"; :>> title = "Orbiter Master Events Controller Preflight BITE Anomaly"; :>> effectivity = "STS-107-999"; :>> changeNo = "011"; :>> measurementCount = 0; :>> numericLimitCount = 0; :>> sourcePage = 839; :>> isCounted = true; }
            part <'LCO-206'> lco_206 : LccItem { doc /* EPDC-10 */ :>> ssid = "EPDC-10"; :>> title = "GSE Main Bus Motor Switch Anomaly"; :>> effectivity = "STS-107-999"; :>> changeNo = "011"; :>> measurementCount = 6; :>> numericLimitCount = 0; :>> sourcePage = 871; :>> isCounted = true; }
            part <'LCO-207'> lco_207 : LccItem { doc /* EPDC-11 */ :>> ssid = "EPDC-11"; :>> title = "Orbiter Fire Extinguisher Pyro Voltage Anomaly"; :>> effectivity = "STS 114-999"; :>> changeNo = "040"; :>> measurementCount = 6; :>> numericLimitCount = 6; :>> sourcePage = 873; :>> isCounted = true; }
            part <'LCO-208'> lco_208 : LccItem { doc /* EPDC-12 */ :>> ssid = "EPDC-12"; :>> title = "Orbiter Landing Gear Pyro Voltage Anomaly"; :>> effectivity = "STS-98,100,102,104,105,107-999"; :>> changeNo = "000"; :>> measurementCount = 16; :>> numericLimitCount = 16; :>> sourcePage = 877; :>> isCounted = true; }
            part <'LCO-209'> lco_209 : LccItem { doc /* EPDC-13 */ :>> ssid = "EPDC-13"; :>> title = "ET/ORB SEPARATION Anomaly"; :>> effectivity = "STS-98,100,102,104,105,107-999"; :>> changeNo = "000"; :>> measurementCount = 4; :>> numericLimitCount = 0; :>> sourcePage = 879; :>> isCounted = true; }
            part <'LCO-210'> lco_210 : LccItem { doc /* EPDC-14 */ :>> ssid = "EPDC-14"; :>> title = "Orbiter Drag Chute Pyro Voltage Anomaly"; :>> effectivity = "STS-107-999"; :>> changeNo = "011"; :>> measurementCount = 4; :>> numericLimitCount = 2; :>> sourcePage = 881; :>> isCounted = true; }
            part <'LCO-554'> lco_554 : LccItem { doc /* EPDC-00 */ :>> ssid = "EPDC-00"; :>> title = ""; :>> effectivity = "N/A"; :>> changeNo = "097"; :>> measurementCount = 0; :>> numericLimitCount = 0; :>> sourcePage = 811; :>> isCounted = false; }
        }
        part sec_apu : LccSection {
            :>> sectionNo = "27";
            :>> sectionTitle = "AUXILIARY POWER UNIT";
            :>> ssidPrefix = "APU";
            part <'LCO-211'> lco_211 : LccItem { doc /* APU-01 */ :>> ssid = "APU-01"; :>> title = "APU Fuel Tank Pressure Anomaly"; :>> effectivity = "STS-107,114-999"; :>> changeNo = "032"; :>> measurementCount = 6; :>> numericLimitCount = 0; :>> sourcePage = 887; :>> isCounted = true; }
            part <'LCO-212'> lco_212 : LccItem { doc /* APU-02 */ :>> ssid = "APU-02"; :>> title = "APU Fuel Line Temperature Anomaly"; :>> effectivity = "STS-107,114-999"; :>> changeNo = "032"; :>> measurementCount = 6; :>> numericLimitCount = 0; :>> sourcePage = 889; :>> isCounted = true; }
            part <'LCO-213'> lco_213 : LccItem { doc /* APU-03 */ :>> ssid = "APU-03"; :>> title = "APU Gas Generator Chamber Pressure Anomaly"; :>> effectivity = "STS-107-999"; :>> changeNo = "011"; :>> measurementCount = 6; :>> numericLimitCount = 6; :>> sourcePage = 893; :>> isCounted = true; }
            part <'LCO-214'> lco_214 : LccItem { doc /* APU-04 */ :>> ssid = "APU-04"; :>> title = "APU Gas Generator Bed/Injector Tube Temperature Anomaly"; :>> effectivity = "STS-107,114-999"; :>> changeNo = "032"; :>> measurementCount = 6; :>> numericLimitCount = 0; :>> sourcePage = 897; :>> isCounted = true; }
            part <'LCO-215'> lco_215 : LccItem { doc /* APU-05 */ :>> ssid = "APU-05"; :>> title = "APU Fuel Line Temp No. 3/Supply Line Temperature Anomaly"; :>> effectivity = "STS-107,114-999"; :>> changeNo = "032"; :>> measurementCount = 6; :>> numericLimitCount = 0; :>> sourcePage = 901; :>> isCounted = true; }
            part <'LCO-216'> lco_216 : LccItem { doc /* APU-06 */ :>> ssid = "APU-06"; :>> title = "APU Turbine Speed Anomaly"; :>> effectivity = "STS-107,114-999"; :>> changeNo = "032"; :>> measurementCount = 3; :>> numericLimitCount = 3; :>> sourcePage = 903; :>> isCounted = true; }
            part <'LCO-217'> lco_217 : LccItem { doc /* APU-08 */ :>> ssid = "APU-08"; :>> title = "Dynamic APU Lube Oil Temperature Anomaly"; :>> effectivity = "STS-107,114-999"; :>> changeNo = "032"; :>> measurementCount = 6; :>> numericLimitCount = 6; :>> sourcePage = 907; :>> isCounted = true; }
            part <'LCO-218'> lco_218 : LccItem { doc /* APU-09 */ :>> ssid = "APU-09"; :>> title = "Static APU Lube Oil Temperature Anomaly"; :>> effectivity = "STS-107,114-999"; :>> changeNo = "032"; :>> measurementCount = 6; :>> numericLimitCount = 6; :>> sourcePage = 909; :>> isCounted = true; }
            part <'LCO-219'> lco_219 : LccItem { doc /* APU-10 */ :>> ssid = "APU-10"; :>> title = "APU Gearbox Pressure Measurement Anomaly"; :>> effectivity = "STS-107,114-999"; :>> changeNo = "032"; :>> measurementCount = 3; :>> numericLimitCount = 0; :>> sourcePage = 911; :>> isCounted = true; }
            part <'LCO-220'> lco_220 : LccItem { doc /* APU-11 */ :>> ssid = "APU-11"; :>> title = "APU Gearbox Pressure Anomaly"; :>> effectivity = "STS-107-999"; :>> changeNo = "011"; :>> measurementCount = 6; :>> numericLimitCount = 6; :>> sourcePage = 913; :>> isCounted = true; }
            part <'LCO-221'> lco_221 : LccItem { doc /* APU-12 */ :>> ssid = "APU-12"; :>> title = "APU Bearing Temperature Anomaly"; :>> effectivity = "STS-107,114-999"; :>> changeNo = "032"; :>> measurementCount = 6; :>> numericLimitCount = 6; :>> sourcePage = 917; :>> isCounted = true; }
            part <'LCO-222'> lco_222 : LccItem { doc /* APU-13 */ :>> ssid = "APU-13"; :>> title = "APU GN2 Bottle Pressure Anomaly"; :>> effectivity = "STS-107,114-999"; :>> changeNo = "032"; :>> measurementCount = 3; :>> numericLimitCount = 0; :>> sourcePage = 919; :>> isCounted = true; }
            part <'LCO-223'> lco_223 : LccItem { doc /* APU-14 */ :>> ssid = "APU-14"; :>> title = "APU Fuel Test Line Temperature Anomaly"; :>> effectivity = "STS-107,114-999"; :>> changeNo = "032"; :>> measurementCount = 6; :>> numericLimitCount = 0; :>> sourcePage = 921; :>> isCounted = true; }
            part <'LCO-224'> lco_224 : LccItem { doc /* APU-15 */ :>> ssid = "APU-15"; :>> title = "APU Fuel Pump Drain Line Temperature Anomaly"; :>> effectivity = "STS-107,114-999"; :>> changeNo = "032"; :>> measurementCount = 9; :>> numericLimitCount = 3; :>> sourcePage = 925; :>> isCounted = true; }
            part <'LCO-225'> lco_225 : LccItem { doc /* APU-16 */ :>> ssid = "APU-16"; :>> title = "APU Fuel Pump Drain Line Pressure"; :>> effectivity = "STS-107,114-999"; :>> changeNo = "032"; :>> measurementCount = 6; :>> numericLimitCount = 0; :>> sourcePage = 929; :>> isCounted = true; }
            part <'LCO-226'> lco_226 : LccItem { doc /* APU-18 */ :>> ssid = "APU-18"; :>> title = "APU Fuel Valve/Fuel Pump Temperature Anomaly"; :>> effectivity = "STS-107,114-999"; :>> changeNo = "032"; :>> measurementCount = 9; :>> numericLimitCount = 0; :>> sourcePage = 933; :>> isCounted = true; }
            part <'LCO-227'> lco_227 : LccItem { doc /* APU-20 */ :>> ssid = "APU-20"; :>> title = "Injector Cooling System Pressure Anomaly"; :>> effectivity = "STS-107,114-999"; :>> changeNo = "032"; :>> measurementCount = 2; :>> numericLimitCount = 1; :>> sourcePage = 937; :>> isCounted = true; }
            part <'LCO-228'> lco_228 : LccItem { doc /* APU-22 */ :>> ssid = "APU-22"; :>> title = "Hot Restart Temperature Anomaly"; :>> effectivity = "STS-107,114-999"; :>> changeNo = "032"; :>> measurementCount = 13; :>> numericLimitCount = 0; :>> sourcePage = 941; :>> isCounted = true; }
            part <'LCO-229'> lco_229 : LccItem { doc /* APU-23 */ :>> ssid = "APU-23"; :>> title = "APU Fuel Tank Isolation Valve Anomaly"; :>> effectivity = "STS-107,114-999"; :>> changeNo = "032"; :>> measurementCount = 6; :>> numericLimitCount = 0; :>> sourcePage = 945; :>> isCounted = true; }
            part <'LCO-230'> lco_230 : LccItem { doc /* APU-24 */ :>> ssid = "APU-24"; :>> title = "PCA APU Controller RPC Power ON Anomaly"; :>> effectivity = "STS-119,124-999"; :>> changeNo = "092"; :>> measurementCount = 6; :>> numericLimitCount = 0; :>> sourcePage = 947; :>> isCounted = true; }
            part <'LCO-231'> lco_231 : LccItem { doc /* APU-25 */ :>> ssid = "APU-25"; :>> title = "APU Fuel Pump Inlet Pressure Anomaly"; :>> effectivity = "STS-114-999"; :>> changeNo = "054"; :>> measurementCount = 3; :>> numericLimitCount = 0; :>> sourcePage = 951; :>> isCounted = true; }
            part <'LCO-555'> lco_555 : LccItem { doc /* APU-00 */ :>> ssid = "APU-00"; :>> title = ""; :>> effectivity = "N/A"; :>> changeNo = "054"; :>> measurementCount = 0; :>> numericLimitCount = 0; :>> sourcePage = 883; :>> isCounted = false; }
            part <'LCO-556'> lco_556 : LccItem { doc /* APU-07 */ :>> ssid = "APU-07"; :>> title = ""; :>> effectivity = "STS-98,100,102,104,105,107-999"; :>> changeNo = "000"; :>> measurementCount = 0; :>> numericLimitCount = 0; :>> sourcePage = 905; :>> isCounted = false; }
            part <'LCO-557'> lco_557 : LccItem { doc /* APU-17 */ :>> ssid = "APU-17"; :>> title = ""; :>> effectivity = "STS-98,100,102,104,105,107-999"; :>> changeNo = "000"; :>> measurementCount = 0; :>> numericLimitCount = 0; :>> sourcePage = 931; :>> isCounted = false; }
            part <'LCO-558'> lco_558 : LccItem { doc /* APU-19 */ :>> ssid = "APU-19"; :>> title = ""; :>> effectivity = "STS-98,100,102,104,105,107-999"; :>> changeNo = "000"; :>> measurementCount = 0; :>> numericLimitCount = 0; :>> sourcePage = 935; :>> isCounted = false; }
            part <'LCO-559'> lco_559 : LccItem { doc /* APU-21 */ :>> ssid = "APU-21"; :>> title = ""; :>> effectivity = "STS-98,100,102,104,105,107-999"; :>> changeNo = "000"; :>> measurementCount = 0; :>> numericLimitCount = 0; :>> sourcePage = 939; :>> isCounted = false; }
            part <'LCO-560'> lco_560 : LccItem { doc /* APU-FG01 */ :>> ssid = "APU-FG01"; :>> title = ""; :>> effectivity = "STS-98,100,102,104,105,107-999"; :>> changeNo = "000"; :>> measurementCount = 0; :>> numericLimitCount = 0; :>> sourcePage = 953; :>> isCounted = false; }
        }
        part sec_hyd : LccSection {
            :>> sectionNo = "28";
            :>> sectionTitle = "HYDRAULICS";
            :>> ssidPrefix = "HYD";
            part <'LCO-232'> lco_232 : LccItem { doc /* HYD-01 */ :>> ssid = "HYD-01"; :>> title = "Hydraulic System Reservoir Fluid Volume Anomaly"; :>> effectivity = "STS-98,100,102,104,105,107-999"; :>> changeNo = "000"; :>> measurementCount = 3; :>> numericLimitCount = 0; :>> sourcePage = 959; :>> isCounted = true; }
            part <'LCO-233'> lco_233 : LccItem { doc /* HYD-02 */ :>> ssid = "HYD-02"; :>> title = "Hydraulic System Supply Pressure Anomaly"; :>> effectivity = "STS-107-999"; :>> changeNo = "015"; :>> measurementCount = 6; :>> numericLimitCount = 6; :>> sourcePage = 961; :>> isCounted = true; }
            part <'LCO-234'> lco_234 : LccItem { doc /* HYD-03 */ :>> ssid = "HYD-03"; :>> title = "Hydraulic System Circulation Pump Pressure Anomaly"; :>> effectivity = "STS-107-999"; :>> changeNo = "011"; :>> measurementCount = 3; :>> numericLimitCount = 0; :>> sourcePage = 965; :>> isCounted = true; }
            part <'LCO-235'> lco_235 : LccItem { doc /* HYD-04 */ :>> ssid = "HYD-04"; :>> title = "Hydraulic System Water Spray Boiler GN2 Tank Anomaly"; :>> effectivity = "STS-107-999"; :>> changeNo = "011"; :>> measurementCount = 9; :>> numericLimitCount = 0; :>> sourcePage = 967; :>> isCounted = true; }
            part <'LCO-236'> lco_236 : LccItem { doc /* HYD-05 */ :>> ssid = "HYD-05"; :>> title = "Hydraulic System Water Spray Boiler Temperature Anomaly"; :>> effectivity = "STS-107,112-999"; :>> changeNo = "027"; :>> measurementCount = 6; :>> numericLimitCount = 6; :>> sourcePage = 971; :>> isCounted = true; }
            part <'LCO-237'> lco_237 : LccItem { doc /* HYD-07 */ :>> ssid = "HYD-07"; :>> title = "Hydraulic Accumulator/Reservoir Fluid Pressure Anomaly"; :>> effectivity = "STS-98,100,102,104,105,107-999"; :>> changeNo = "000"; :>> measurementCount = 6; :>> numericLimitCount = 0; :>> sourcePage = 975; :>> isCounted = true; }
            part <'LCO-238'> lco_238 : LccItem { doc /* HYD-08 */ :>> ssid = "HYD-08"; :>> title = "Hydraulic System 1 Landing Gear Extend Isolation Valve Anomaly"; :>> effectivity = "STS-107-999"; :>> changeNo = "011"; :>> measurementCount = 1; :>> numericLimitCount = 0; :>> sourcePage = 979; :>> isCounted = true; }
            part <'LCO-239'> lco_239 : LccItem { doc /* HYD-09 */ :>> ssid = "HYD-09"; :>> title = "PCA Hydraulic Pump RPC Anomaly"; :>> effectivity = "STS-98,100,102,104,105,107-999"; :>> changeNo = "000"; :>> measurementCount = 6; :>> numericLimitCount = 0; :>> sourcePage = 981; :>> isCounted = true; }
            part <'LCO-240'> lco_240 : LccItem { doc /* HYD-10 */ :>> ssid = "HYD-10"; :>> title = "Hydraulic Water Spray Boiler OK Anomaly"; :>> effectivity = "STS-107-999"; :>> changeNo = "011"; :>> measurementCount = 3; :>> numericLimitCount = 0; :>> sourcePage = 983; :>> isCounted = true; }
            part <'LCO-561'> lco_561 : LccItem { doc /* HYD-00 */ :>> ssid = "HYD-00"; :>> title = ""; :>> effectivity = "N/A"; :>> changeNo = "000"; :>> measurementCount = 0; :>> numericLimitCount = 0; :>> sourcePage = 955; :>> isCounted = false; }
            part <'LCO-562'> lco_562 : LccItem { doc /* HYD-06 */ :>> ssid = "HYD-06"; :>> title = ""; :>> effectivity = "STS-98,100,102,104,105,107-999"; :>> changeNo = "000"; :>> measurementCount = 0; :>> numericLimitCount = 0; :>> sourcePage = 973; :>> isCounted = false; }
            part <'LCO-563'> lco_563 : LccItem { doc /* HYD-FG01 */ :>> ssid = "HYD-FG01"; :>> title = ""; :>> effectivity = "STS-98,100,102,104,105,107-999"; :>> changeNo = "000"; :>> measurementCount = 0; :>> numericLimitCount = 0; :>> sourcePage = 985; :>> isCounted = false; }
        }
        part sec_afm : LccSection {
            :>> sectionNo = "29";
            :>> sectionTitle = "MECHANICAL SYSTEMS";
            :>> ssidPrefix = "AFM";
            part <'LCO-241'> lco_241 : LccItem { doc /* AFM-01 */ :>> ssid = "AFM-01"; :>> title = "ET Centerline Door Latch Indication Anomaly"; :>> effectivity = "STS-107-999"; :>> changeNo = "011"; :>> measurementCount = 8; :>> numericLimitCount = 0; :>> sourcePage = 991; :>> isCounted = true; }
            part <'LCO-242'> lco_242 : LccItem { doc /* AFM-02 */ :>> ssid = "AFM-02"; :>> title = "ET Door Position Indication Anomaly"; :>> effectivity = "STS-107-999"; :>> changeNo = "011"; :>> measurementCount = 8; :>> numericLimitCount = 0; :>> sourcePage = 993; :>> isCounted = true; }
            part <'LCO-243'> lco_243 : LccItem { doc /* AFM-03 */ :>> ssid = "AFM-03"; :>> title = "ET Door Latch Indication Anomaly"; :>> effectivity = "STS-107-999"; :>> changeNo = "011"; :>> measurementCount = 8; :>> numericLimitCount = 0; :>> sourcePage = 995; :>> isCounted = true; }
            part <'LCO-244'> lco_244 : LccItem { doc /* AFM-04 */ :>> ssid = "AFM-04"; :>> title = "Radiator Drive Indication Anomaly"; :>> effectivity = "STS-107-999"; :>> changeNo = "011"; :>> measurementCount = 8; :>> numericLimitCount = 0; :>> sourcePage = 997; :>> isCounted = true; }
            part <'LCO-245'> lco_245 : LccItem { doc /* AFM-05 */ :>> ssid = "AFM-05"; :>> title = "Radiator Latch Indication Anomaly"; :>> effectivity = "STS-107-999"; :>> changeNo = "011"; :>> measurementCount = 16; :>> numericLimitCount = 0; :>> sourcePage = 999; :>> isCounted = true; }
            part <'LCO-246'> lco_246 : LccItem { doc /* AFM-06 */ :>> ssid = "AFM-06"; :>> title = "Payload Bay Door Open Indication Anomaly"; :>> effectivity = "STS-107-999"; :>> changeNo = "011"; :>> measurementCount = 4; :>> numericLimitCount = 0; :>> sourcePage = 1003; :>> isCounted = true; }
            part <'LCO-247'> lco_247 : LccItem { doc /* AFM-07 */ :>> ssid = "AFM-07"; :>> title = "Payload Bay Door Bulkhead Latch Indication Anomaly"; :>> effectivity = "STS-107-999"; :>> changeNo = "011"; :>> measurementCount = 16; :>> numericLimitCount = 0; :>> sourcePage = 1005; :>> isCounted = true; }
            part <'LCO-248'> lco_248 : LccItem { doc /* AFM-08 */ :>> ssid = "AFM-08"; :>> title = "Payload Bay Door Ready-To-Latch Indication Anomaly"; :>> effectivity = "STS-98,100,102,104,105,107-999"; :>> changeNo = "000"; :>> measurementCount = 12; :>> numericLimitCount = 0; :>> sourcePage = 1009; :>> isCounted = true; }
            part <'LCO-249'> lco_249 : LccItem { doc /* AFM-09 */ :>> ssid = "AFM-09"; :>> title = "Payload Bay Door Centerline Latch Indication Anomaly"; :>> effectivity = "STS-107-999"; :>> changeNo = "011"; :>> measurementCount = 16; :>> numericLimitCount = 0; :>> sourcePage = 1011; :>> isCounted = true; }
            part <'LCO-250'> lco_250 : LccItem { doc /* AFM-10 */ :>> ssid = "AFM-10"; :>> title = "Landing Gear Uplock Indication Anomaly"; :>> effectivity = "STS-119,124-999"; :>> changeNo = "092"; :>> measurementCount = 3; :>> numericLimitCount = 0; :>> sourcePage = 1015; :>> isCounted = true; }
            part <'LCO-251'> lco_251 : LccItem { doc /* AFM-11 */ :>> ssid = "AFM-11"; :>> title = "Landing Gear Shuttle Valve Indication Anomaly"; :>> effectivity = "STS-107-999"; :>> changeNo = "011"; :>> measurementCount = 3; :>> numericLimitCount = 0; :>> sourcePage = 1017; :>> isCounted = true; }
            part <'LCO-252'> lco_252 : LccItem { doc /* AFM-12 */ :>> ssid = "AFM-12"; :>> title = "RMS Deploy/Stow Mechanism Indication Anomaly"; :>> effectivity = "STS-107-999"; :>> changeNo = "011"; :>> measurementCount = 10; :>> numericLimitCount = 0; :>> sourcePage = 1019; :>> isCounted = true; }
            part <'LCO-253'> lco_253 : LccItem { doc /* AFM-13 */ :>> ssid = "AFM-13"; :>> title = "RMS Retention Latch Indication Anomaly"; :>> effectivity = "STS-107-999"; :>> changeNo = "011"; :>> measurementCount = 12; :>> numericLimitCount = 0; :>> sourcePage = 1023; :>> isCounted = true; }
            part <'LCO-254'> lco_254 : LccItem { doc /* AFM-14 */ :>> ssid = "AFM-14"; :>> title = "Star Tracker Door Indication Anomaly"; :>> effectivity = "STS-107-999"; :>> changeNo = "011"; :>> measurementCount = 8; :>> numericLimitCount = 0; :>> sourcePage = 1027; :>> isCounted = true; }
            part <'LCO-255'> lco_255 : LccItem { doc /* AFM-15 */ :>> ssid = "AFM-15"; :>> title = "Air Data Probe Deploy/Stow Indication Anomaly"; :>> effectivity = "STS-107-999"; :>> changeNo = "011"; :>> measurementCount = 8; :>> numericLimitCount = 0; :>> sourcePage = 1031; :>> isCounted = true; }
            part <'LCO-256'> lco_256 : LccItem { doc /* AFM-16 */ :>> ssid = "AFM-16"; :>> title = "Forward Motor Control Assembly Operational Status Anomaly"; :>> effectivity = "STS-107-999"; :>> changeNo = "011"; :>> measurementCount = 12; :>> numericLimitCount = 0; :>> sourcePage = 1033; :>> isCounted = true; }
            part <'LCO-257'> lco_257 : LccItem { doc /* AFM-17 */ :>> ssid = "AFM-17"; :>> title = "Mid Motor Control Assembly Operational Status Anomaly"; :>> effectivity = "STS-107-999"; :>> changeNo = "011"; :>> measurementCount = 32; :>> numericLimitCount = 0; :>> sourcePage = 1035; :>> isCounted = true; }
            part <'LCO-258'> lco_258 : LccItem { doc /* AFM-18 */ :>> ssid = "AFM-18"; :>> title = "Aft Motor Control Assembly Operational Status Anomaly"; :>> effectivity = "STS-107-999"; :>> changeNo = "011"; :>> measurementCount = 12; :>> numericLimitCount = 0; :>> sourcePage = 1037; :>> isCounted = true; }
            part <'LCO-259'> lco_259 : LccItem { doc /* AFM-19 */ :>> ssid = "AFM-19"; :>> title = "OBSS Deploy/Stow Mechanism Indication Anomaly"; :>> effectivity = "STS-114-999"; :>> changeNo = "050"; :>> measurementCount = 8; :>> numericLimitCount = 0; :>> sourcePage = 1039; :>> isCounted = true; }
            part <'LCO-260'> lco_260 : LccItem { doc /* AFM-20 */ :>> ssid = "AFM-20"; :>> title = "OBSS Retention Latch Indication Anomaly"; :>> effectivity = "STS-114-999"; :>> changeNo = "050"; :>> measurementCount = 12; :>> numericLimitCount = 0; :>> sourcePage = 1043; :>> isCounted = true; }
            part <'LCO-261'> lco_261 : LccItem { doc /* AFM-30 */ :>> ssid = "AFM-30"; :>> title = "Orbiter Vent Door Indication Anomaly"; :>> effectivity = "STS-115-999"; :>> changeNo = "066"; :>> measurementCount = 48; :>> numericLimitCount = 0; :>> sourcePage = 1049; :>> isCounted = true; }
            part <'LCO-564'> lco_564 : LccItem { doc /* AFM-00 */ :>> ssid = "AFM-00"; :>> title = ""; :>> effectivity = "N/A"; :>> changeNo = "050"; :>> measurementCount = 0; :>> numericLimitCount = 0; :>> sourcePage = 987; :>> isCounted = false; }
            part <'LCO-565'> lco_565 : LccItem { doc /* AFM-21 */ :>> ssid = "AFM-21"; :>> title = ""; :>> effectivity = "STS-114-999"; :>> changeNo = "050"; :>> measurementCount = 0; :>> numericLimitCount = 0; :>> sourcePage = 1047; :>> isCounted = false; }
        }
        part sec_ecl : LccSection {
            :>> sectionNo = "30";
            :>> sectionTitle = "ENVIRONMENTAL CONTROL AND LIFE SUPPORT";
            :>> ssidPrefix = "ECL";
            part <'LCO-262'> lco_262 : LccItem { doc /* ECL-01 */ :>> ssid = "ECL-01"; :>> title = "Orbiter Cabin Vent Valve Anomaly"; :>> effectivity = "STS-107-999"; :>> changeNo = "011"; :>> measurementCount = 2; :>> numericLimitCount = 0; :>> sourcePage = 1059; :>> isCounted = true; }
            part <'LCO-263'> lco_263 : LccItem { doc /* ECL-02 */ :>> ssid = "ECL-02"; :>> title = "Orbiter Nitrogen Supply System Anomaly"; :>> effectivity = "STS-107-999"; :>> changeNo = "011"; :>> measurementCount = 20; :>> numericLimitCount = 10; :>> sourcePage = 1061; :>> isCounted = true; }
            part <'LCO-264'> lco_264 : LccItem { doc /* ECL-03 */ :>> ssid = "ECL-03"; :>> title = "Orbiter Nitrogen System Valve Anomaly"; :>> effectivity = "STS-107,112-999"; :>> changeNo = "030"; :>> measurementCount = 6; :>> numericLimitCount = 0; :>> sourcePage = 1063; :>> isCounted = true; }
            part <'LCO-265'> lco_265 : LccItem { doc /* ECL-04 */ :>> ssid = "ECL-04"; :>> title = "Orbiter Cabin Pressure Anomaly"; :>> effectivity = "119,120,122-999"; :>> changeNo = "081"; :>> measurementCount = 8; :>> numericLimitCount = 7; :>> sourcePage = 1067; :>> isCounted = true; }
            part <'LCO-266'> lco_266 : LccItem { doc /* ECL-05 */ :>> ssid = "ECL-05"; :>> title = "Orbiter Cabin/Airlock Pressure Anomaly"; :>> effectivity = "119,120,122-999"; :>> changeNo = "081"; :>> measurementCount = 10; :>> numericLimitCount = 10; :>> sourcePage = 1073; :>> isCounted = true; }
            part <'LCO-267'> lco_267 : LccItem { doc /* ECL-06 */ :>> ssid = "ECL-06"; :>> title = "Orbiter Cabin Partial Pressure of Oxygen Anomaly"; :>> effectivity = "STS-107-999"; :>> changeNo = "011"; :>> measurementCount = 6; :>> numericLimitCount = 3; :>> sourcePage = 1079; :>> isCounted = true; }
            part <'LCO-268'> lco_268 : LccItem { doc /* ECL-07 */ :>> ssid = "ECL-07"; :>> title = "Orbiter Cabin Fan Anomaly"; :>> effectivity = "STS 115-999"; :>> changeNo = "067"; :>> measurementCount = 6; :>> numericLimitCount = 4; :>> sourcePage = 1081; :>> isCounted = true; }
            part <'LCO-269'> lco_269 : LccItem { doc /* ECL-08 */ :>> ssid = "ECL-08"; :>> title = "Orbiter Water Coolant Loop Leakage Indication"; :>> effectivity = "STS 119,125-999"; :>> changeNo = "094"; :>> measurementCount = 12; :>> numericLimitCount = 4; :>> sourcePage = 1085; :>> isCounted = true; }
            part <'LCO-270'> lco_270 : LccItem { doc /* ECL-09 */ :>> ssid = "ECL-09"; :>> title = "Water Coolant Loop Anomaly"; :>> effectivity = "STS 119,125-999"; :>> changeNo = "094"; :>> measurementCount = 18; :>> numericLimitCount = 18; :>> sourcePage = 1091; :>> isCounted = true; }
            part <'LCO-271'> lco_271 : LccItem { doc /* ECL-10 */ :>> ssid = "ECL-10"; :>> title = "Orbiter Avionics Bay Cooling Anomaly"; :>> effectivity = "STS-119,125-999"; :>> changeNo = "095"; :>> measurementCount = 49; :>> numericLimitCount = 25; :>> sourcePage = 1095; :>> isCounted = true; }
            part <'LCO-272'> lco_272 : LccItem { doc /* ECL-11 */ :>> ssid = "ECL-11"; :>> title = "Orbiter IMU Fan Anomaly"; :>> effectivity = "STS 118-120,122-999"; :>> changeNo = "079"; :>> measurementCount = 5; :>> numericLimitCount = 2; :>> sourcePage = 1103; :>> isCounted = true; }
            part <'LCO-273'> lco_273 : LccItem { doc /* ECL-20 */ :>> ssid = "ECL-20"; :>> title = "Orbiter Potable Water Quantity Anomaly"; :>> effectivity = "STS-107-999"; :>> changeNo = "011"; :>> measurementCount = 8; :>> numericLimitCount = 4; :>> sourcePage = 1109; :>> isCounted = true; }
            part <'LCO-274'> lco_274 : LccItem { doc /* ECL-21 */ :>> ssid = "ECL-21"; :>> title = "Orbiter Waste Water Quantity Anomaly"; :>> effectivity = "STS-107-999"; :>> changeNo = "011"; :>> measurementCount = 4; :>> numericLimitCount = 2; :>> sourcePage = 1111; :>> isCounted = true; }
            part <'LCO-275'> lco_275 : LccItem { doc /* ECL-22 */ :>> ssid = "ECL-22"; :>> title = "Orbiter Waste Water Dump Nozzle Temperature Anomaly"; :>> effectivity = "STS-98,100,102,104,105,107-999"; :>> changeNo = "000"; :>> measurementCount = 4; :>> numericLimitCount = 2; :>> sourcePage = 1113; :>> isCounted = true; }
            part <'LCO-276'> lco_276 : LccItem { doc /* ECL-23 */ :>> ssid = "ECL-23"; :>> title = "Orbiter Supply Water Dump Nozzle Temperature Anomaly"; :>> effectivity = "STS-98,100,102,104,105,107-999"; :>> changeNo = "000"; :>> measurementCount = 4; :>> numericLimitCount = 2; :>> sourcePage = 1115; :>> isCounted = true; }
            part <'LCO-277'> lco_277 : LccItem { doc /* ECL-30 */ :>> ssid = "ECL-30"; :>> title = "Orbiter Crew Cabin Smoke Detector Concentration Measurement Failure"; :>> effectivity = "STS-98,100,102,104,105,107-999"; :>> changeNo = "000"; :>> measurementCount = 6; :>> numericLimitCount = 6; :>> sourcePage = 1119; :>> isCounted = true; }
            part <'LCO-278'> lco_278 : LccItem { doc /* ECL-31 */ :>> ssid = "ECL-31"; :>> title = "Orbiter Crew Cabin Smoke Detector Alarm Indication"; :>> effectivity = "STS-107-999"; :>> changeNo = "011"; :>> measurementCount = 12; :>> numericLimitCount = 6; :>> sourcePage = 1121; :>> isCounted = true; }
            part <'LCO-279'> lco_279 : LccItem { doc /* ECL-32 */ :>> ssid = "ECL-32"; :>> title = "Orbiter Avionics Bay Smoke Detector Concentration Measurement Failure"; :>> effectivity = "STS-98,100,102,104,105,107-999"; :>> changeNo = "000"; :>> measurementCount = 6; :>> numericLimitCount = 6; :>> sourcePage = 1123; :>> isCounted = true; }
            part <'LCO-280'> lco_280 : LccItem { doc /* ECL-33 */ :>> ssid = "ECL-33"; :>> title = "Orbiter Avionics Bay Smoke Detector Alarm Indication"; :>> effectivity = "STS-107-999"; :>> changeNo = "011"; :>> measurementCount = 12; :>> numericLimitCount = 6; :>> sourcePage = 1125; :>> isCounted = true; }
            part <'LCO-281'> lco_281 : LccItem { doc /* ECL-34 */ :>> ssid = "ECL-34"; :>> title = "Orbiter Avionics Bay Fire Bottle Empty Indication"; :>> effectivity = "STS-98,100,102,104,105,107-999"; :>> changeNo = "000"; :>> measurementCount = 3; :>> numericLimitCount = 0; :>> sourcePage = 1127; :>> isCounted = true; }
            part <'LCO-282'> lco_282 : LccItem { doc /* ECL-40 */ :>> ssid = "ECL-40"; :>> title = "Freon Flow Rate Anomaly"; :>> effectivity = "STS-107-999"; :>> changeNo = "011"; :>> measurementCount = 14; :>> numericLimitCount = 8; :>> sourcePage = 1131; :>> isCounted = true; }
            part <'LCO-283'> lco_283 : LccItem { doc /* ECL-41 */ :>> ssid = "ECL-41"; :>> title = "Orbiter Freon Coolant Loop Pressure/Quantity Anomaly"; :>> effectivity = "STS-107-999"; :>> changeNo = "011"; :>> measurementCount = 4; :>> numericLimitCount = 2; :>> sourcePage = 1135; :>> isCounted = true; }
            part <'LCO-284'> lco_284 : LccItem { doc /* ECL-42 */ :>> ssid = "ECL-42"; :>> title = "Orbiter Ammonia System Tank Temperature/ Pressure Anomaly"; :>> effectivity = "STS-98,100,102,104,105,107-999"; :>> changeNo = "000"; :>> measurementCount = 8; :>> numericLimitCount = 4; :>> sourcePage = 1137; :>> isCounted = true; }
            part <'LCO-285'> lco_285 : LccItem { doc /* ECL-43 */ :>> ssid = "ECL-43"; :>> title = "Orbiter Freon Coolant Loop Evaporator Out Temperature Anomaly"; :>> effectivity = "STS-107-999"; :>> changeNo = "011"; :>> measurementCount = 4; :>> numericLimitCount = 4; :>> sourcePage = 1139; :>> isCounted = true; }
            part <'LCO-286'> lco_286 : LccItem { doc /* ECL-44 */ :>> ssid = "ECL-44"; :>> title = "Orbiter Flash Evaporator Water Accumulator Temperature Anomaly"; :>> effectivity = "STS-98,100,102,104,105,107-999"; :>> changeNo = "000"; :>> measurementCount = 4; :>> numericLimitCount = 4; :>> sourcePage = 1141; :>> isCounted = true; }
            part <'LCO-287'> lco_287 : LccItem { doc /* ECL-45 */ :>> ssid = "ECL-45"; :>> title = "Orbiter Flash Evaporator Water Accumulator Anomaly"; :>> effectivity = "STS-107-999"; :>> changeNo = "011"; :>> measurementCount = 2; :>> numericLimitCount = 0; :>> sourcePage = 1143; :>> isCounted = true; }
            part <'LCO-288'> lco_288 : LccItem { doc /* ECL-46 */ :>> ssid = "ECL-46"; :>> title = "Orbiter Flash Evaporator Topping Duct Temperature Anomaly"; :>> effectivity = "STS-98,100,102,104,105,107-999"; :>> changeNo = "000"; :>> measurementCount = 4; :>> numericLimitCount = 4; :>> sourcePage = 1145; :>> isCounted = true; }
            part <'LCO-289'> lco_289 : LccItem { doc /* ECL-47 */ :>> ssid = "ECL-47"; :>> title = "Orbiter Flash Evaporator Hi Load Duct Temperature Anomaly"; :>> effectivity = "STS-98,100,102,104,105,107-999"; :>> changeNo = "000"; :>> measurementCount = 4; :>> numericLimitCount = 4; :>> sourcePage = 1147; :>> isCounted = true; }
            part <'LCO-290'> lco_290 : LccItem { doc /* ECL-48 */ :>> ssid = "ECL-48"; :>> title = "Orbiter Flash Evaporator Water Feedline Temperature Anomaly"; :>> effectivity = "STS-107-999"; :>> changeNo = "011"; :>> measurementCount = 16; :>> numericLimitCount = 16; :>> sourcePage = 1149; :>> isCounted = true; }
            part <'LCO-566'> lco_566 : LccItem { doc /* ECL-00 */ :>> ssid = "ECL-00"; :>> title = ""; :>> effectivity = "N/A"; :>> changeNo = "081"; :>> measurementCount = 0; :>> numericLimitCount = 0; :>> sourcePage = 1055; :>> isCounted = false; }
            part <'LCO-567'> lco_567 : LccItem { doc /* ECL-12 */ :>> ssid = "ECL-12"; :>> title = ""; :>> effectivity = "STS-98,100,102,104,105,107-999"; :>> changeNo = "000"; :>> measurementCount = 0; :>> numericLimitCount = 0; :>> sourcePage = 1107; :>> isCounted = false; }
            part <'LCO-568'> lco_568 : LccItem { doc /* ECL-24 */ :>> ssid = "ECL-24"; :>> title = ""; :>> effectivity = "STS-98,100,102,104,105,107-999"; :>> changeNo = "000"; :>> measurementCount = 0; :>> numericLimitCount = 0; :>> sourcePage = 1117; :>> isCounted = false; }
            part <'LCO-569'> lco_569 : LccItem { doc /* ECL-35 */ :>> ssid = "ECL-35"; :>> title = ""; :>> effectivity = "STS-98,100,102,104,105,107-999"; :>> changeNo = "000"; :>> measurementCount = 0; :>> numericLimitCount = 0; :>> sourcePage = 1129; :>> isCounted = false; }
            part <'LCO-570'> lco_570 : LccItem { doc /* ECL-FG01 */ :>> ssid = "ECL-FG01"; :>> title = ""; :>> effectivity = "STS-98,100,102,104,105,107-999"; :>> changeNo = "000"; :>> measurementCount = 0; :>> numericLimitCount = 0; :>> sourcePage = 1151; :>> isCounted = false; }
        }
        part sec_dps : LccSection {
            :>> sectionNo = "31";
            :>> sectionTitle = "DATA PROCESSING SYSTEM";
            :>> ssidPrefix = "DPS";
            part <'LCO-291'> lco_291 : LccItem { doc /* DPS-01a */ :>> ssid = "DPS-01a"; :>> title = "PASS Multifunction Electronic Display Subsystem (MEDS) Anomaly"; :>> effectivity = "STS-119,123-999"; :>> changeNo = "087"; :>> measurementCount = 12; :>> numericLimitCount = 0; :>> sourcePage = 1159; :>> isCounted = true; }
            part <'LCO-292'> lco_292 : LccItem { doc /* DPS-02 */ :>> ssid = "DPS-02"; :>> title = "PASS GPC Fail Indicator"; :>> effectivity = "STS-107-999"; :>> changeNo = "011"; :>> measurementCount = 4; :>> numericLimitCount = 4; :>> sourcePage = 1173; :>> isCounted = true; }
            part <'LCO-293'> lco_293 : LccItem { doc /* DPS-03 */ :>> ssid = "DPS-03"; :>> title = "MDM BCE Bypass"; :>> effectivity = "STS-107-999"; :>> changeNo = "011"; :>> measurementCount = 27; :>> numericLimitCount = 0; :>> sourcePage = 1177; :>> isCounted = true; }
            part <'LCO-294'> lco_294 : LccItem { doc /* DPS-04 */ :>> ssid = "DPS-04"; :>> title = "MDM Guidance, Navigation and Control Initiation Bypass Anomaly"; :>> effectivity = "STS-98,100,102,104,105,107-999"; :>> changeNo = "000"; :>> measurementCount = 8; :>> numericLimitCount = 0; :>> sourcePage = 1181; :>> isCounted = true; }
            part <'LCO-295'> lco_295 : LccItem { doc /* DPS-05 */ :>> ssid = "DPS-05"; :>> title = "GPC BITE Indication"; :>> effectivity = "STS-98,100,102,104,105,107-999"; :>> changeNo = "000"; :>> measurementCount = 0; :>> numericLimitCount = 0; :>> sourcePage = 1183; :>> isCounted = true; }
            part <'LCO-296'> lco_296 : LccItem { doc /* DPS-06a */ :>> ssid = "DPS-06a"; :>> title = "SSMM Error"; :>> effectivity = "STS-114-999"; :>> changeNo = "045"; :>> measurementCount = 0; :>> numericLimitCount = 0; :>> sourcePage = 1187; :>> isCounted = true; }
            part <'LCO-297'> lco_297 : LccItem { doc /* DPS-07 */ :>> ssid = "DPS-07"; :>> title = "Mass Memory Ready Discrete Anomaly"; :>> effectivity = "STS-107,109-999"; :>> changeNo = "016"; :>> measurementCount = 8; :>> numericLimitCount = 0; :>> sourcePage = 1191; :>> isCounted = true; }
            part <'LCO-298'> lco_298 : LccItem { doc /* DPS-09 */ :>> ssid = "DPS-09"; :>> title = "PASS GPC Error"; :>> effectivity = "STS-115-999"; :>> changeNo = "063"; :>> measurementCount = 4; :>> numericLimitCount = 0; :>> sourcePage = 1195; :>> isCounted = true; }
            part <'LCO-299'> lco_299 : LccItem { doc /* DPS-10 */ :>> ssid = "DPS-10"; :>> title = "PASS Time Source Anomaly"; :>> effectivity = "STS-98,100,102,104,105,107-999"; :>> changeNo = "000"; :>> measurementCount = 8; :>> numericLimitCount = 0; :>> sourcePage = 1199; :>> isCounted = true; }
            part <'LCO-300'> lco_300 : LccItem { doc /* DPS-11 */ :>> ssid = "DPS-11"; :>> title = "PASS BFS Engage Discrete Anomaly."; :>> effectivity = "STS-98,100,102,104,105,107-999"; :>> changeNo = "000"; :>> measurementCount = 12; :>> numericLimitCount = 12; :>> sourcePage = 1201; :>> isCounted = true; }
            part <'LCO-301'> lco_301 : LccItem { doc /* DPS-12 */ :>> ssid = "DPS-12"; :>> title = "IMU Data Bypass"; :>> effectivity = "STS-98,100,102,104,105,107-999"; :>> changeNo = "000"; :>> measurementCount = 6; :>> numericLimitCount = 0; :>> sourcePage = 1203; :>> isCounted = true; }
            part <'LCO-302'> lco_302 : LccItem { doc /* DPS-13 */ :>> ssid = "DPS-13"; :>> title = "IMU BCE String Bypass"; :>> effectivity = "STS-98,100,102,104,105,107-999"; :>> changeNo = "000"; :>> measurementCount = 3; :>> numericLimitCount = 0; :>> sourcePage = 1205; :>> isCounted = true; }
            part <'LCO-303'> lco_303 : LccItem { doc /* DPS-14 */ :>> ssid = "DPS-14"; :>> title = "Network Signal Processor Bus Control Element Bypass"; :>> effectivity = "STS-98,100,102,104,105,107-999"; :>> changeNo = "000"; :>> measurementCount = 4; :>> numericLimitCount = 0; :>> sourcePage = 1207; :>> isCounted = true; }
            part <'LCO-304'> lco_304 : LccItem { doc /* DPS-15 */ :>> ssid = "DPS-15"; :>> title = "Air Data Transducer Assembly BCE Bypass Anomaly"; :>> effectivity = "STS-107,110-999"; :>> changeNo = "020"; :>> measurementCount = 4; :>> numericLimitCount = 4; :>> sourcePage = 1209; :>> isCounted = true; }
            part <'LCO-305'> lco_305 : LccItem { doc /* DPS-16 */ :>> ssid = "DPS-16"; :>> title = "MTU BCE Bypass"; :>> effectivity = "STS-98,100,102,104,105,107-999"; :>> changeNo = "000"; :>> measurementCount = 3; :>> numericLimitCount = 0; :>> sourcePage = 1211; :>> isCounted = true; }
            part <'LCO-306'> lco_306 : LccItem { doc /* DPS-17 */ :>> ssid = "DPS-17"; :>> title = "Tactical Air Navigation/Radar Altimeter BCE Bypass"; :>> effectivity = "STS 118-120,122-999"; :>> changeNo = "078"; :>> measurementCount = 3; :>> numericLimitCount = 0; :>> sourcePage = 1213; :>> isCounted = true; }
            part <'LCO-307'> lco_307 : LccItem { doc /* DPS-18 */ :>> ssid = "DPS-18"; :>> title = "Engine Interface Unit Mid Frequency Executive BCE Bypass"; :>> effectivity = "STS-98,100,102,104,105,107-999"; :>> changeNo = "000"; :>> measurementCount = 3; :>> numericLimitCount = 0; :>> sourcePage = 1217; :>> isCounted = true; }
            part <'LCO-308'> lco_308 : LccItem { doc /* DPS-19 */ :>> ssid = "DPS-19"; :>> title = "MDM BSR Anomaly"; :>> effectivity = "STS-107-999"; :>> changeNo = "011"; :>> measurementCount = 0; :>> numericLimitCount = 0; :>> sourcePage = 1219; :>> isCounted = true; }
            part <'LCO-309'> lco_309 : LccItem { doc /* DPS-20 */ :>> ssid = "DPS-20"; :>> title = "MDM Output Fault Summary Message"; :>> effectivity = "STS-98,100,102,104,105,107-999"; :>> changeNo = "000"; :>> measurementCount = 0; :>> numericLimitCount = 0; :>> sourcePage = 1221; :>> isCounted = true; }
            part <'LCO-310'> lco_310 : LccItem { doc /* DPS-21 */ :>> ssid = "DPS-21"; :>> title = "SUMWORD ICC Fault Summary Message"; :>> effectivity = "STS-98,100,102,104,105,107-999"; :>> changeNo = "000"; :>> measurementCount = 0; :>> numericLimitCount = 0; :>> sourcePage = 1223; :>> isCounted = true; }
            part <'LCO-311'> lco_311 : LccItem { doc /* DPS-22 */ :>> ssid = "DPS-22"; :>> title = "PASS I/O Error Log"; :>> effectivity = "STS-107-999"; :>> changeNo = "015"; :>> measurementCount = 0; :>> numericLimitCount = 0; :>> sourcePage = 1225; :>> isCounted = true; }
            part <'LCO-312'> lco_312 : LccItem { doc /* DPS-26 */ :>> ssid = "DPS-26"; :>> title = "GPC Soft Error Counter Anomaly"; :>> effectivity = "STS-107-999"; :>> changeNo = "011"; :>> measurementCount = 8; :>> numericLimitCount = 0; :>> sourcePage = 1233; :>> isCounted = true; }
            part <'LCO-313'> lco_313 : LccItem { doc /* DPS-27 */ :>> ssid = "DPS-27"; :>> title = "G3 Archive Load Status"; :>> effectivity = "STS-98,100,102,104,105,107-999"; :>> changeNo = "000"; :>> measurementCount = 4; :>> numericLimitCount = 0; :>> sourcePage = 1235; :>> isCounted = true; }
            part <'LCO-314'> lco_314 : LccItem { doc /* DPS-28 */ :>> ssid = "DPS-28"; :>> title = "GPS BCE Bypass Anomaly"; :>> effectivity = "STS 118-120,122-999"; :>> changeNo = "078"; :>> measurementCount = 3; :>> numericLimitCount = 0; :>> sourcePage = 1237; :>> isCounted = true; }
            part <'LCO-315'> lco_315 : LccItem { doc /* DPS-29 */ :>> ssid = "DPS-29"; :>> title = "PASS GPC Downlist Loss"; :>> effectivity = "STS-119,125-999"; :>> changeNo = "095"; :>> measurementCount = 1; :>> numericLimitCount = 0; :>> sourcePage = 1239; :>> isCounted = true; }
            part <'LCO-571'> lco_571 : LccItem { doc /* DPS-00 */ :>> ssid = "DPS-00"; :>> title = ""; :>> effectivity = "N/A"; :>> changeNo = "095"; :>> measurementCount = 0; :>> numericLimitCount = 0; :>> sourcePage = 1153; :>> isCounted = false; }
            part <'LCO-572'> lco_572 : LccItem { doc /* DPS-01 */ :>> ssid = "DPS-01"; :>> title = ""; :>> effectivity = "STS-115-999"; :>> changeNo = "063"; :>> measurementCount = 0; :>> numericLimitCount = 0; :>> sourcePage = 1157; :>> isCounted = false; }
            part <'LCO-573'> lco_573 : LccItem { doc /* DPS-06 */ :>> ssid = "DPS-06"; :>> title = ""; :>> effectivity = "STS-114-999"; :>> changeNo = "045"; :>> measurementCount = 0; :>> numericLimitCount = 0; :>> sourcePage = 1185; :>> isCounted = false; }
            part <'LCO-574'> lco_574 : LccItem { doc /* DPS-08 */ :>> ssid = "DPS-08"; :>> title = ""; :>> effectivity = "STS-98,100,102,104,105,107-999"; :>> changeNo = "000"; :>> measurementCount = 0; :>> numericLimitCount = 0; :>> sourcePage = 1193; :>> isCounted = false; }
            part <'LCO-575'> lco_575 : LccItem { doc /* DPS-23 */ :>> ssid = "DPS-23"; :>> title = ""; :>> effectivity = "STS-115-999"; :>> changeNo = "063"; :>> measurementCount = 0; :>> numericLimitCount = 0; :>> sourcePage = 1227; :>> isCounted = false; }
            part <'LCO-576'> lco_576 : LccItem { doc /* DPS-24 */ :>> ssid = "DPS-24"; :>> title = ""; :>> effectivity = "STS-107-999"; :>> changeNo = "014"; :>> measurementCount = 0; :>> numericLimitCount = 0; :>> sourcePage = 1229; :>> isCounted = false; }
            part <'LCO-577'> lco_577 : LccItem { doc /* DPS-25 */ :>> ssid = "DPS-25"; :>> title = ""; :>> effectivity = "STS-98,100,102,104,105,107-999"; :>> changeNo = "000"; :>> measurementCount = 0; :>> numericLimitCount = 0; :>> sourcePage = 1231; :>> isCounted = false; }
        }
        part sec_ct : LccSection {
            :>> sectionNo = "32";
            :>> sectionTitle = "COMMUNICATIONS AND TRACKING";
            :>> ssidPrefix = "CT";
            part <'LCO-316'> lco_316 : LccItem { doc /* CT-01 */ :>> ssid = "CT-01"; :>> title = "Loss of TACAN Indication"; :>> effectivity = "STS-119,122-999"; :>> changeNo = "082"; :>> measurementCount = 17; :>> numericLimitCount = 0; :>> sourcePage = 1249; :>> isCounted = true; }
            part <'LCO-317'> lco_317 : LccItem { doc /* CT-02 */ :>> ssid = "CT-02"; :>> title = "S-Band PM Transponder AGC Anomaly"; :>> effectivity = "STS-107-999"; :>> changeNo = "011"; :>> measurementCount = 2; :>> numericLimitCount = 2; :>> sourcePage = 1257; :>> isCounted = true; }
            part <'LCO-318'> lco_318 : LccItem { doc /* CT-03 */ :>> ssid = "CT-03"; :>> title = "GCIL Active Anomaly"; :>> effectivity = "STS-107-999"; :>> changeNo = "015"; :>> measurementCount = 1; :>> numericLimitCount = 0; :>> sourcePage = 1259; :>> isCounted = true; }
            part <'LCO-319'> lco_319 : LccItem { doc /* CT-04 */ :>> ssid = "CT-04"; :>> title = "Loss of Network Signal Processor Frame Sync Lock"; :>> effectivity = "STS-107-999"; :>> changeNo = "011"; :>> measurementCount = 2; :>> numericLimitCount = 0; :>> sourcePage = 1261; :>> isCounted = true; }
            part <'LCO-320'> lco_320 : LccItem { doc /* CT-05 */ :>> ssid = "CT-05"; :>> title = "Voice Communication System Anomaly"; :>> effectivity = "STS-107-999"; :>> changeNo = "011"; :>> measurementCount = 0; :>> numericLimitCount = 0; :>> sourcePage = 1263; :>> isCounted = true; }
            part <'LCO-321'> lco_321 : LccItem { doc /* CT-08 */ :>> ssid = "CT-08"; :>> title = "Radar Altimeter Ready Anomaly"; :>> effectivity = "STS-114-999"; :>> changeNo = "035"; :>> measurementCount = 2; :>> numericLimitCount = 0; :>> sourcePage = 1269; :>> isCounted = true; }
            part <'LCO-322'> lco_322 : LccItem { doc /* CT-09 */ :>> ssid = "CT-09"; :>> title = "S-Band Phase Modulated Power Amplifier Anomaly"; :>> effectivity = "STS-107-999"; :>> changeNo = "011"; :>> measurementCount = 4; :>> numericLimitCount = 4; :>> sourcePage = 1271; :>> isCounted = true; }
            part <'LCO-323'> lco_323 : LccItem { doc /* CT-10 */ :>> ssid = "CT-10"; :>> title = "Crew Communication System Anomaly"; :>> effectivity = "STS-114-999"; :>> changeNo = "053"; :>> measurementCount = 0; :>> numericLimitCount = 0; :>> sourcePage = 1273; :>> isCounted = true; }
            part <'LCO-324'> lco_324 : LccItem { doc /* CT-11 */ :>> ssid = "CT-11"; :>> title = "Loss of GPS Indication for Three String GPS Vehicles"; :>> effectivity = "STS 118-120,122-999"; :>> changeNo = "078"; :>> measurementCount = 6; :>> numericLimitCount = 0; :>> sourcePage = 1277; :>> isCounted = true; }
            part <'LCO-578'> lco_578 : LccItem { doc /* CT-00 */ :>> ssid = "CT-00"; :>> title = ""; :>> effectivity = "N/A"; :>> changeNo = "078"; :>> measurementCount = 0; :>> numericLimitCount = 0; :>> sourcePage = 1245; :>> isCounted = false; }
            part <'LCO-579'> lco_579 : LccItem { doc /* CT-06 */ :>> ssid = "CT-06"; :>> title = ""; :>> effectivity = "STS-98,100,102,104,105,107-999"; :>> changeNo = "000"; :>> measurementCount = 0; :>> numericLimitCount = 0; :>> sourcePage = 1265; :>> isCounted = false; }
            part <'LCO-580'> lco_580 : LccItem { doc /* CT-07 */ :>> ssid = "CT-07"; :>> title = ""; :>> effectivity = "STS-98,100,102,104,105,107-999"; :>> changeNo = "000"; :>> measurementCount = 0; :>> numericLimitCount = 0; :>> sourcePage = 1267; :>> isCounted = false; }
        }
        part sec_ins : LccSection {
            :>> sectionNo = "33";
            :>> sectionTitle = "OPERATIONAL INSTRUMENTATION";
            :>> ssidPrefix = "INS";
            part <'LCO-325'> lco_325 : LccItem { doc /* INS-01 */ :>> ssid = "INS-01"; :>> title = "Operational Instrumentation Anomaly"; :>> effectivity = "STS-119,125-999"; :>> changeNo = "095"; :>> measurementCount = 11; :>> numericLimitCount = 11; :>> sourcePage = 1285; :>> isCounted = true; }
            part <'LCO-326'> lco_326 : LccItem { doc /* INS-02a */ :>> ssid = "INS-02a"; :>> title = "SSR Anomaly"; :>> effectivity = "STS-107,109-999"; :>> changeNo = "016"; :>> measurementCount = 2; :>> numericLimitCount = 0; :>> sourcePage = 1293; :>> isCounted = true; }
            part <'LCO-327'> lco_327 : LccItem { doc /* INS-03 */ :>> ssid = "INS-03"; :>> title = "MTU Signal Distribution"; :>> effectivity = "STS-107-999"; :>> changeNo = "011"; :>> measurementCount = 14; :>> numericLimitCount = 0; :>> sourcePage = 1295; :>> isCounted = true; }
            part <'LCO-328'> lco_328 : LccItem { doc /* INS-04 */ :>> ssid = "INS-04"; :>> title = "Operational Instrumentation"; :>> effectivity = "STS-107-999"; :>> changeNo = "011"; :>> measurementCount = 26; :>> numericLimitCount = 15; :>> sourcePage = 1299; :>> isCounted = true; }
            part <'LCO-329'> lco_329 : LccItem { doc /* INS-05 */ :>> ssid = "INS-05"; :>> title = "Operational Instrumentation Anomaly"; :>> effectivity = "STS-107-999"; :>> changeNo = "011"; :>> measurementCount = 7; :>> numericLimitCount = 0; :>> sourcePage = 1303; :>> isCounted = true; }
            part <'LCO-330'> lco_330 : LccItem { doc /* INS-06 */ :>> ssid = "INS-06"; :>> title = "Caution and Warning System Fail Anomaly"; :>> effectivity = "STS-107-999"; :>> changeNo = "011"; :>> measurementCount = 1; :>> numericLimitCount = 0; :>> sourcePage = 1305; :>> isCounted = true; }
            part <'LCO-581'> lco_581 : LccItem { doc /* INS-00 */ :>> ssid = "INS-00"; :>> title = ""; :>> effectivity = "N/A"; :>> changeNo = "045"; :>> measurementCount = 0; :>> numericLimitCount = 0; :>> sourcePage = 1281; :>> isCounted = false; }
            part <'LCO-582'> lco_582 : LccItem { doc /* INS-02 */ :>> ssid = "INS-02"; :>> title = ""; :>> effectivity = "STS-114-999"; :>> changeNo = "045"; :>> measurementCount = 0; :>> numericLimitCount = 0; :>> sourcePage = 1291; :>> isCounted = false; }
        }
        part sec_gnc : LccSection {
            :>> sectionNo = "34";
            :>> sectionTitle = "GUIDANCE, NAVIGATION AND CONTROL";
            :>> ssidPrefix = "GNC";
            part <'LCO-331'> lco_331 : LccItem { doc /* GNC-01 */ :>> ssid = "GNC-01"; :>> title = "Forward Rotational Hand Controller Command Anomaly"; :>> effectivity = "STS-98,100,102,104,105,107-999"; :>> changeNo = "000"; :>> measurementCount = 36; :>> numericLimitCount = 18; :>> sourcePage = 1313; :>> isCounted = true; }
            part <'LCO-332'> lco_332 : LccItem { doc /* GNC-02 */ :>> ssid = "GNC-02"; :>> title = "Forward Translational Hand Controller Output Anomaly"; :>> effectivity = "STS-98,100,102,104,105,107-999"; :>> changeNo = "000"; :>> measurementCount = 18; :>> numericLimitCount = 0; :>> sourcePage = 1317; :>> isCounted = true; }
            part <'LCO-333'> lco_333 : LccItem { doc /* GNC-03 */ :>> ssid = "GNC-03"; :>> title = "Rudder Pedal Command Anomaly"; :>> effectivity = "STS-98,100,102,104,105,107-999"; :>> changeNo = "000"; :>> measurementCount = 6; :>> numericLimitCount = 0; :>> sourcePage = 1319; :>> isCounted = true; }
            part <'LCO-334'> lco_334 : LccItem { doc /* GNC-04 */ :>> ssid = "GNC-04"; :>> title = "Right SBTC CMD and Takeover Anomaly"; :>> effectivity = "STS-98,100,102,104,105,107-999"; :>> changeNo = "000"; :>> measurementCount = 9; :>> numericLimitCount = 4; :>> sourcePage = 1321; :>> isCounted = true; }
            part <'LCO-335'> lco_335 : LccItem { doc /* GNC-08 */ :>> ssid = "GNC-08"; :>> title = "Orbiter Rate Gyro Power Anomaly"; :>> effectivity = "STS 116-120,122-999"; :>> changeNo = "070"; :>> measurementCount = 3; :>> numericLimitCount = 0; :>> sourcePage = 1325; :>> isCounted = true; }
            part <'LCO-336'> lco_336 : LccItem { doc /* GNC-09 */ :>> ssid = "GNC-09"; :>> title = "Accelerometer Power Anomaly"; :>> effectivity = "STS-107,112-999"; :>> changeNo = "029"; :>> measurementCount = 6; :>> numericLimitCount = 0; :>> sourcePage = 1329; :>> isCounted = true; }
            part <'LCO-337'> lco_337 : LccItem { doc /* GNC-10 */ :>> ssid = "GNC-10"; :>> title = "SRB Bus C Power Anomaly"; :>> effectivity = "STS-114-999"; :>> changeNo = "045"; :>> measurementCount = 4; :>> numericLimitCount = 0; :>> sourcePage = 1331; :>> isCounted = true; }
            part <'LCO-338'> lco_338 : LccItem { doc /* GNC-11 */ :>> ssid = "GNC-11"; :>> title = "Orbiter RGA Spin Motor Anomaly"; :>> effectivity = "STS-98,100,102,104,105,107-999"; :>> changeNo = "000"; :>> measurementCount = 12; :>> numericLimitCount = 12; :>> sourcePage = 1333; :>> isCounted = true; }
            part <'LCO-339'> lco_339 : LccItem { doc /* GNC-12 */ :>> ssid = "GNC-12"; :>> title = "Orbiter Rate Gyro Fail"; :>> effectivity = "STS-98,100,102,104,105,107-999"; :>> changeNo = "000"; :>> measurementCount = 4; :>> numericLimitCount = 0; :>> sourcePage = 1335; :>> isCounted = true; }
            part <'LCO-340'> lco_340 : LccItem { doc /* GNC-13 */ :>> ssid = "GNC-13"; :>> title = "Accelerometer Fail"; :>> effectivity = "STS-98,100,102,104,105,107-999"; :>> changeNo = "000"; :>> measurementCount = 4; :>> numericLimitCount = 0; :>> sourcePage = 1337; :>> isCounted = true; }
            part <'LCO-341'> lco_341 : LccItem { doc /* GNC-14 */ :>> ssid = "GNC-14"; :>> title = "SRB RGA Fail Anomaly"; :>> effectivity = "STS-107-999"; :>> changeNo = "011"; :>> measurementCount = 4; :>> numericLimitCount = 0; :>> sourcePage = 1339; :>> isCounted = true; }
            part <'LCO-342'> lco_342 : LccItem { doc /* GNC-15 */ :>> ssid = "GNC-15"; :>> title = "SRB RGA 1, 2, 3, 4 SMRD Anomaly"; :>> effectivity = "STS-107-999"; :>> changeNo = "011"; :>> measurementCount = 8; :>> numericLimitCount = 0; :>> sourcePage = 1341; :>> isCounted = true; }
            part <'LCO-343'> lco_343 : LccItem { doc /* GNC-16 */ :>> ssid = "GNC-16"; :>> title = "SRB RGA Rate Anomaly"; :>> effectivity = "STS-98,100,102,104,105,107-999"; :>> changeNo = "000"; :>> measurementCount = 16; :>> numericLimitCount = 16; :>> sourcePage = 1343; :>> isCounted = true; }
            part <'LCO-344'> lco_344 : LccItem { doc /* GNC-22 */ :>> ssid = "GNC-22"; :>> title = "Elevon Actuator Position Anomaly"; :>> effectivity = "STS-107,112-999"; :>> changeNo = "027"; :>> measurementCount = 16; :>> numericLimitCount = 16; :>> sourcePage = 1347; :>> isCounted = true; }
            part <'LCO-345'> lco_345 : LccItem { doc /* GNC-23 */ :>> ssid = "GNC-23"; :>> title = "Elevon Actuator Primary Delta Pressure Anomaly"; :>> effectivity = "STS-98,100,102,104,105,107-999"; :>> changeNo = "000"; :>> measurementCount = 16; :>> numericLimitCount = 16; :>> sourcePage = 1349; :>> isCounted = true; }
            part <'LCO-346'> lco_346 : LccItem { doc /* GNC-24 */ :>> ssid = "GNC-24"; :>> title = "Elevon Actuator Secondary Delta Pressure Anomaly"; :>> effectivity = "STS-107-999"; :>> changeNo = "011"; :>> measurementCount = 16; :>> numericLimitCount = 16; :>> sourcePage = 1351; :>> isCounted = true; }
            part <'LCO-347'> lco_347 : LccItem { doc /* GNC-25 */ :>> ssid = "GNC-25"; :>> title = "Elevon Aerosurface Profile Anomaly"; :>> effectivity = "STS-107,112-999"; :>> changeNo = "027"; :>> measurementCount = 16; :>> numericLimitCount = 0; :>> sourcePage = 1355; :>> isCounted = true; }
            part <'LCO-348'> lco_348 : LccItem { doc /* GNC-26 */ :>> ssid = "GNC-26"; :>> title = "Rudder/Speedbrake Position Anomaly"; :>> effectivity = "STS-107,112-999"; :>> changeNo = "027"; :>> measurementCount = 8; :>> numericLimitCount = 0; :>> sourcePage = 1357; :>> isCounted = true; }
            part <'LCO-349'> lco_349 : LccItem { doc /* GNC-27 */ :>> ssid = "GNC-27"; :>> title = "Rudder/Speedbrake PDU Secondary Delta Pressure Anomaly"; :>> effectivity = "STS-107-999"; :>> changeNo = "011"; :>> measurementCount = 8; :>> numericLimitCount = 8; :>> sourcePage = 1359; :>> isCounted = true; }
            part <'LCO-350'> lco_350 : LccItem { doc /* GNC-28 */ :>> ssid = "GNC-28"; :>> title = "Rudder Speedbrake Aerosurface Profile - Anomaly"; :>> effectivity = "STS-107,112-999"; :>> changeNo = "027"; :>> measurementCount = 8; :>> numericLimitCount = 0; :>> sourcePage = 1361; :>> isCounted = true; }
            part <'LCO-351'> lco_351 : LccItem { doc /* GNC-29 */ :>> ssid = "GNC-29"; :>> title = "Body Flap Control Discrete Anomaly"; :>> effectivity = "STS-98,100,102,104,105,107-999"; :>> changeNo = "000"; :>> measurementCount = 9; :>> numericLimitCount = 9; :>> sourcePage = 1363; :>> isCounted = true; }
            part <'LCO-352'> lco_352 : LccItem { doc /* GNC-30 */ :>> ssid = "GNC-30"; :>> title = "Body Flap Launch Position"; :>> effectivity = "STS-98,100,102,104,105,107-999"; :>> changeNo = "000"; :>> measurementCount = 4; :>> numericLimitCount = 4; :>> sourcePage = 1365; :>> isCounted = true; }
            part <'LCO-353'> lco_353 : LccItem { doc /* GNC-31 */ :>> ssid = "GNC-31"; :>> title = "Bodyflap Aerosurface Profile - Anomaly"; :>> effectivity = "STS-104,105,107-999"; :>> changeNo = "007"; :>> measurementCount = 4; :>> numericLimitCount = 0; :>> sourcePage = 1367; :>> isCounted = true; }
            part <'LCO-354'> lco_354 : LccItem { doc /* GNC-32 */ :>> ssid = "GNC-32"; :>> title = "Orbiter ASA Power Anomaly"; :>> effectivity = "STS-107,112-999"; :>> changeNo = "029"; :>> measurementCount = 11; :>> numericLimitCount = 0; :>> sourcePage = 1369; :>> isCounted = true; }
            part <'LCO-355'> lco_355 : LccItem { doc /* GNC-38 */ :>> ssid = "GNC-38"; :>> title = "Flight Control System Channel Failure Indication"; :>> effectivity = "STS-107,110-999"; :>> changeNo = "021"; :>> measurementCount = 2; :>> numericLimitCount = 2; :>> sourcePage = 1375; :>> isCounted = true; }
            part <'LCO-356'> lco_356 : LccItem { doc /* GNC-39 */ :>> ssid = "GNC-39"; :>> title = "Orbiter ATVC Power Anomaly"; :>> effectivity = "STS-107,112-999"; :>> changeNo = "029"; :>> measurementCount = 8; :>> numericLimitCount = 0; :>> sourcePage = 1379; :>> isCounted = true; }
            part <'LCO-357'> lco_357 : LccItem { doc /* GNC-40 */ :>> ssid = "GNC-40"; :>> title = "MPS TVC Actuator Position Anomaly"; :>> effectivity = "STS-98,100,102,104,105,107-999"; :>> changeNo = "000"; :>> measurementCount = 9; :>> numericLimitCount = 9; :>> sourcePage = 1381; :>> isCounted = true; }
            part <'LCO-358'> lco_358 : LccItem { doc /* GNC-41 */ :>> ssid = "GNC-41"; :>> title = "MPS TVC Actuator Secondary Delta Pressure Anomaly"; :>> effectivity = "STS-107-999"; :>> changeNo = "011"; :>> measurementCount = 24; :>> numericLimitCount = 24; :>> sourcePage = 1387; :>> isCounted = true; }
            part <'LCO-359'> lco_359 : LccItem { doc /* GNC-42 */ :>> ssid = "GNC-42"; :>> title = "MPS Engine TVC Actuator Profile Anomaly"; :>> effectivity = "STS-98,100,102,104,105,107-999"; :>> changeNo = "000"; :>> measurementCount = 9; :>> numericLimitCount = 3; :>> sourcePage = 1391; :>> isCounted = true; }
            part <'LCO-360'> lco_360 : LccItem { doc /* GNC-43 */ :>> ssid = "GNC-43"; :>> title = "OMS Actuator Launch Position Anomaly"; :>> effectivity = "STS-98,100,102,104,105,107-999"; :>> changeNo = "000"; :>> measurementCount = 16; :>> numericLimitCount = 16; :>> sourcePage = 1393; :>> isCounted = true; }
            part <'LCO-361'> lco_361 : LccItem { doc /* GNC-44 */ :>> ssid = "GNC-44"; :>> title = "OMS Gimbal Profile Anomaly"; :>> effectivity = "STS-98,100,102,104,105,107-999"; :>> changeNo = "000"; :>> measurementCount = 16; :>> numericLimitCount = 8; :>> sourcePage = 1395; :>> isCounted = true; }
            part <'LCO-362'> lco_362 : LccItem { doc /* GNC-45 */ :>> ssid = "GNC-45"; :>> title = "RJD Jet Chamber Pressure Indication Anomaly"; :>> effectivity = "STS-107-999"; :>> changeNo = "011"; :>> measurementCount = 38; :>> numericLimitCount = 0; :>> sourcePage = 1397; :>> isCounted = true; }
            part <'LCO-363'> lco_363 : LccItem { doc /* GNC-46 */ :>> ssid = "GNC-46"; :>> title = "RCS Vernier Driver Out Anomaly"; :>> effectivity = "STS-98,100,102,104,105,107-999"; :>> changeNo = "000"; :>> measurementCount = 6; :>> numericLimitCount = 6; :>> sourcePage = 1401; :>> isCounted = true; }
            part <'LCO-364'> lco_364 : LccItem { doc /* GNC-47 */ :>> ssid = "GNC-47"; :>> title = "RCS Vernier Logic RPC Anomaly"; :>> effectivity = "STS-107-999"; :>> changeNo = "011"; :>> measurementCount = 3; :>> numericLimitCount = 0; :>> sourcePage = 1403; :>> isCounted = true; }
            part <'LCO-365'> lco_365 : LccItem { doc /* GNC-48 */ :>> ssid = "GNC-48"; :>> title = "RCS Driver Power Anomaly"; :>> effectivity = "STS-107-999"; :>> changeNo = "011"; :>> measurementCount = 13; :>> numericLimitCount = 0; :>> sourcePage = 1405; :>> isCounted = true; }
            part <'LCO-366'> lco_366 : LccItem { doc /* GNC-49 */ :>> ssid = "GNC-49"; :>> title = "RJD Trickle Current Anomaly"; :>> effectivity = "STS-107-999"; :>> changeNo = "011"; :>> measurementCount = 8; :>> numericLimitCount = 0; :>> sourcePage = 1407; :>> isCounted = true; }
            part <'LCO-367'> lco_367 : LccItem { doc /* GNC-56 */ :>> ssid = "GNC-56"; :>> title = "IMU Hardware Bite Indication"; :>> effectivity = "STS-107-999"; :>> changeNo = "011"; :>> measurementCount = 3; :>> numericLimitCount = 0; :>> sourcePage = 1411; :>> isCounted = true; }
            part <'LCO-368'> lco_368 : LccItem { doc /* GNC-57 */ :>> ssid = "GNC-57"; :>> title = "Orbiter IMU Power Anomaly"; :>> effectivity = "STS-107,112-999"; :>> changeNo = "029"; :>> measurementCount = 6; :>> numericLimitCount = 0; :>> sourcePage = 1413; :>> isCounted = true; }
            part <'LCO-369'> lco_369 : LccItem { doc /* GNC-58 */ :>> ssid = "GNC-58"; :>> title = "IMU Temperature Ready Anomaly"; :>> effectivity = "STS-107-999"; :>> changeNo = "011"; :>> measurementCount = 6; :>> numericLimitCount = 0; :>> sourcePage = 1415; :>> isCounted = true; }
            part <'LCO-370'> lco_370 : LccItem { doc /* GNC-59 */ :>> ssid = "GNC-59"; :>> title = "IMU Over Temperature Indication"; :>> effectivity = "STS-107-999"; :>> changeNo = "011"; :>> measurementCount = 6; :>> numericLimitCount = 0; :>> sourcePage = 1417; :>> isCounted = true; }
            part <'LCO-371'> lco_371 : LccItem { doc /* GNC-60 */ :>> ssid = "GNC-60"; :>> title = "Redundancy Management IMU Failure Indication"; :>> effectivity = "STS-98,100,102,104,105,107-999"; :>> changeNo = "000"; :>> measurementCount = 3; :>> numericLimitCount = 0; :>> sourcePage = 1419; :>> isCounted = true; }
            part <'LCO-372'> lco_372 : LccItem { doc /* GNC-61 */ :>> ssid = "GNC-61"; :>> title = "IMU Software BITE Anomaly"; :>> effectivity = "STS-107-999"; :>> changeNo = "011"; :>> measurementCount = 21; :>> numericLimitCount = 0; :>> sourcePage = 1421; :>> isCounted = true; }
            part <'LCO-373'> lco_373 : LccItem { doc /* GNC-62 */ :>> ssid = "GNC-62"; :>> title = "IMU Gyrocompass Anomaly"; :>> effectivity = "STS-98,100,102,104,105,107-999"; :>> changeNo = "000"; :>> measurementCount = 3; :>> numericLimitCount = 0; :>> sourcePage = 1423; :>> isCounted = true; }
            part <'LCO-374'> lco_374 : LccItem { doc /* GNC-63 */ :>> ssid = "GNC-63"; :>> title = "IMU Gyrocompass Alignment 1 Anomaly"; :>> effectivity = "STS-107-999"; :>> changeNo = "011"; :>> measurementCount = 3; :>> numericLimitCount = 0; :>> sourcePage = 1425; :>> isCounted = true; }
            part <'LCO-375'> lco_375 : LccItem { doc /* GNC-64 */ :>> ssid = "GNC-64"; :>> title = "IMU Requirements When IRAMS In Use"; :>> effectivity = "STS-119,123-999"; :>> changeNo = "088"; :>> measurementCount = 0; :>> numericLimitCount = 0; :>> sourcePage = 1427; :>> isCounted = true; }
            part <'LCO-376'> lco_376 : LccItem { doc /* GNC-66 */ :>> ssid = "GNC-66"; :>> title = "IMU Transmission Word Failure"; :>> effectivity = "STS-107-999"; :>> changeNo = "011"; :>> measurementCount = 6; :>> numericLimitCount = 0; :>> sourcePage = 1433; :>> isCounted = true; }
            part <'LCO-377'> lco_377 : LccItem { doc /* GNC-67 */ :>> ssid = "GNC-67"; :>> title = "IMU PRESSURE/COMMUNICATION ANOMALY"; :>> effectivity = "STS-107-999"; :>> changeNo = "011"; :>> measurementCount = 3; :>> numericLimitCount = 0; :>> sourcePage = 1435; :>> isCounted = true; }
            part <'LCO-378'> lco_378 : LccItem { doc /* GNC-73 */ :>> ssid = "GNC-73"; :>> title = "Air Data Transducer Assembly BITE Anomaly"; :>> effectivity = "STS-107,109-999"; :>> changeNo = "017"; :>> measurementCount = 4; :>> numericLimitCount = 0; :>> sourcePage = 1439; :>> isCounted = true; }
            part <'LCO-379'> lco_379 : LccItem { doc /* GNC-74 */ :>> ssid = "GNC-74"; :>> title = "Air Data Transducer Assembly (ADTA) Pressure Anomaly"; :>> effectivity = "STS 117-120,122-999"; :>> changeNo = "076"; :>> measurementCount = 32; :>> numericLimitCount = 16; :>> sourcePage = 1443; :>> isCounted = true; }
            part <'LCO-380'> lco_380 : LccItem { doc /* GNC-79 */ :>> ssid = "GNC-79"; :>> title = "Brake Pressure Anomaly"; :>> effectivity = "STS-107-999"; :>> changeNo = "011"; :>> measurementCount = 24; :>> numericLimitCount = 24; :>> sourcePage = 1451; :>> isCounted = true; }
            part <'LCO-381'> lco_381 : LccItem { doc /* GNC-80 */ :>> ssid = "GNC-80"; :>> title = "Brake Power Anomaly"; :>> effectivity = "STS-107-999"; :>> changeNo = "011"; :>> measurementCount = 4; :>> numericLimitCount = 4; :>> sourcePage = 1453; :>> isCounted = true; }
            part <'LCO-382'> lco_382 : LccItem { doc /* GNC-81 */ :>> ssid = "GNC-81"; :>> title = "Landing Gear Anti-Skid Anomaly"; :>> effectivity = "STS-107-999"; :>> changeNo = "011"; :>> measurementCount = 16; :>> numericLimitCount = 0; :>> sourcePage = 1455; :>> isCounted = true; }
            part <'LCO-383'> lco_383 : LccItem { doc /* GNC-82 */ :>> ssid = "GNC-82"; :>> title = "ANTI-SKID FAIL Light Anomaly"; :>> effectivity = "STS-98,100,102,104,105,107-999"; :>> changeNo = "000"; :>> measurementCount = 0; :>> numericLimitCount = 0; :>> sourcePage = 1457; :>> isCounted = true; }
            part <'LCO-384'> lco_384 : LccItem { doc /* GNC-83 */ :>> ssid = "GNC-83"; :>> title = "Nose Wheel Steering Anomaly"; :>> effectivity = "STS-107-999"; :>> changeNo = "015"; :>> measurementCount = 1; :>> numericLimitCount = 0; :>> sourcePage = 1459; :>> isCounted = true; }
            part <'LCO-385'> lco_385 : LccItem { doc /* GNC-84 */ :>> ssid = "GNC-84"; :>> title = "Nosewheel Position Signal Path Anomaly"; :>> effectivity = "STS-98,100,102,104,105,107-999"; :>> changeNo = "000"; :>> measurementCount = 6; :>> numericLimitCount = 6; :>> sourcePage = 1461; :>> isCounted = true; }
            part <'LCO-386'> lco_386 : LccItem { doc /* GNC-85 */ :>> ssid = "GNC-85"; :>> title = "DDU Power Supply Anomaly"; :>> effectivity = "STS-107-999"; :>> changeNo = "014"; :>> measurementCount = 6; :>> numericLimitCount = 0; :>> sourcePage = 1463; :>> isCounted = true; }
            part <'LCO-583'> lco_583 : LccItem { doc /* GNC-00 */ :>> ssid = "GNC-00"; :>> title = ""; :>> effectivity = "N/A"; :>> changeNo = "076"; :>> measurementCount = 0; :>> numericLimitCount = 0; :>> sourcePage = 1307; :>> isCounted = false; }
            part <'LCO-584'> lco_584 : LccItem { doc /* GNC-05 */ :>> ssid = "GNC-05"; :>> title = ""; :>> effectivity = "STS-98,100,102,104,105,107-999"; :>> changeNo = "000"; :>> measurementCount = 0; :>> numericLimitCount = 0; :>> sourcePage = 1323; :>> isCounted = false; }
            part <'LCO-585'> lco_585 : LccItem { doc /* GNC-17 */ :>> ssid = "GNC-17"; :>> title = ""; :>> effectivity = "STS-98,100,102,104,105,107-999"; :>> changeNo = "000"; :>> measurementCount = 0; :>> numericLimitCount = 0; :>> sourcePage = 1345; :>> isCounted = false; }
            part <'LCO-586'> lco_586 : LccItem { doc /* GNC-33 */ :>> ssid = "GNC-33"; :>> title = ""; :>> effectivity = "STS-98,100,102,104,105,107-999"; :>> changeNo = "000"; :>> measurementCount = 0; :>> numericLimitCount = 0; :>> sourcePage = 1373; :>> isCounted = false; }
            part <'LCO-587'> lco_587 : LccItem { doc /* GNC-50 */ :>> ssid = "GNC-50"; :>> title = ""; :>> effectivity = "STS-98,100,102,104,105,107-999"; :>> changeNo = "000"; :>> measurementCount = 0; :>> numericLimitCount = 0; :>> sourcePage = 1409; :>> isCounted = false; }
            part <'LCO-588'> lco_588 : LccItem { doc /* GNC-65 */ :>> ssid = "GNC-65"; :>> title = ""; :>> effectivity = "STS-98,100,102,104,105,107-999"; :>> changeNo = "000"; :>> measurementCount = 0; :>> numericLimitCount = 0; :>> sourcePage = 1431; :>> isCounted = false; }
            part <'LCO-589'> lco_589 : LccItem { doc /* GNC-68 */ :>> ssid = "GNC-68"; :>> title = ""; :>> effectivity = "STS-98,100,102,104,105,107-999"; :>> changeNo = "000"; :>> measurementCount = 0; :>> numericLimitCount = 0; :>> sourcePage = 1437; :>> isCounted = false; }
            part <'LCO-590'> lco_590 : LccItem { doc /* GNC-75 */ :>> ssid = "GNC-75"; :>> title = ""; :>> effectivity = "STS-98,100,102,104,105,107-999"; :>> changeNo = "000"; :>> measurementCount = 0; :>> numericLimitCount = 0; :>> sourcePage = 1447; :>> isCounted = false; }
            part <'LCO-591'> lco_591 : LccItem { doc /* GNC-76 */ :>> ssid = "GNC-76"; :>> title = ""; :>> effectivity = "STS-98,100,102,104,105,107-999"; :>> changeNo = "000"; :>> measurementCount = 0; :>> numericLimitCount = 0; :>> sourcePage = 1449; :>> isCounted = false; }
            part <'LCO-592'> lco_592 : LccItem { doc /* GNC-FG02 */ :>> ssid = "GNC-FG02"; :>> title = ""; :>> effectivity = "STS-98,100,102,104,105,107-999"; :>> changeNo = "000"; :>> measurementCount = 0; :>> numericLimitCount = 0; :>> sourcePage = 1465; :>> isCounted = false; }
            part <'LCO-593'> lco_593 : LccItem { doc /* GNC-FG03 */ :>> ssid = "GNC-FG03"; :>> title = ""; :>> effectivity = "STS-114-999"; :>> changeNo = "045"; :>> measurementCount = 0; :>> numericLimitCount = 0; :>> sourcePage = 1467; :>> isCounted = false; }
        }
        part sec_bfs : LccSection {
            :>> sectionNo = "35";
            :>> sectionTitle = "BACKUP FLIGHT CONTROL SYSTEM";
            :>> ssidPrefix = "BFS";
            part <'LCO-387'> lco_387 : LccItem { doc /* BFS-01 */ :>> ssid = "BFS-01"; :>> title = "BFS Input/Output Terminate B Anomaly"; :>> effectivity = "STS-115-999"; :>> changeNo = "058"; :>> measurementCount = 1; :>> numericLimitCount = 0; :>> sourcePage = 1473; :>> isCounted = true; }
            part <'LCO-388'> lco_388 : LccItem { doc /* BFS-02 */ :>> ssid = "BFS-02"; :>> title = "BFS Engage Discrete Anomaly"; :>> effectivity = "STS-115-999"; :>> changeNo = "058"; :>> measurementCount = 3; :>> numericLimitCount = 0; :>> sourcePage = 1475; :>> isCounted = true; }
            part <'LCO-389'> lco_389 : LccItem { doc /* BFS-03 */ :>> ssid = "BFS-03"; :>> title = "BFS Time Source Faultdown"; :>> effectivity = "STS-115-999"; :>> changeNo = "058"; :>> measurementCount = 1; :>> numericLimitCount = 0; :>> sourcePage = 1477; :>> isCounted = true; }
            part <'LCO-390'> lco_390 : LccItem { doc /* BFS-04 */ :>> ssid = "BFS-04"; :>> title = "BFS GPC BITE Anomaly"; :>> effectivity = "STS-115-999"; :>> changeNo = "058"; :>> measurementCount = 0; :>> numericLimitCount = 0; :>> sourcePage = 1479; :>> isCounted = true; }
            part <'LCO-391'> lco_391 : LccItem { doc /* BFS-05 */ :>> ssid = "BFS-05"; :>> title = "BFS GPC Error Count Anomaly"; :>> effectivity = "STS-115-999"; :>> changeNo = "058"; :>> measurementCount = 1; :>> numericLimitCount = 0; :>> sourcePage = 1481; :>> isCounted = true; }
            part <'LCO-392'> lco_392 : LccItem { doc /* BFS-06 */ :>> ssid = "BFS-06"; :>> title = "BFS Tracking PASS Anomaly"; :>> effectivity = "STS-115-999"; :>> changeNo = "058"; :>> measurementCount = 4; :>> numericLimitCount = 0; :>> sourcePage = 1483; :>> isCounted = true; }
            part <'LCO-393'> lco_393 : LccItem { doc /* BFS-08 */ :>> ssid = "BFS-08"; :>> title = "BFS GPC Fail Indication"; :>> effectivity = "STS-115-999"; :>> changeNo = "058"; :>> measurementCount = 1; :>> numericLimitCount = 0; :>> sourcePage = 1487; :>> isCounted = true; }
            part <'LCO-394'> lco_394 : LccItem { doc /* BFS-09 */ :>> ssid = "BFS-09"; :>> title = "BFS Payload MDM Bypass Indication"; :>> effectivity = "STS-115-999"; :>> changeNo = "058"; :>> measurementCount = 2; :>> numericLimitCount = 0; :>> sourcePage = 1489; :>> isCounted = true; }
            part <'LCO-395'> lco_395 : LccItem { doc /* BFS-10a */ :>> ssid = "BFS-10a"; :>> title = "BFS Multifunction Electronic Display Subsystem (MEDS) Anomaly"; :>> effectivity = "STS-119,123-999"; :>> changeNo = "087"; :>> measurementCount = 3; :>> numericLimitCount = 0; :>> sourcePage = 1495; :>> isCounted = true; }
            part <'LCO-396'> lco_396 : LccItem { doc /* BFS-11 */ :>> ssid = "BFS-11"; :>> title = "BFS IMU Initialization Data Anomaly"; :>> effectivity = "STS-115-999"; :>> changeNo = "058"; :>> measurementCount = 1; :>> numericLimitCount = 1; :>> sourcePage = 1509; :>> isCounted = true; }
            part <'LCO-397'> lco_397 : LccItem { doc /* BFS-12 */ :>> ssid = "BFS-12"; :>> title = "BFS I/O Error Log"; :>> effectivity = "STS-115-999"; :>> changeNo = "058"; :>> measurementCount = 0; :>> numericLimitCount = 0; :>> sourcePage = 1511; :>> isCounted = true; }
            part <'LCO-398'> lco_398 : LccItem { doc /* BFS-14 */ :>> ssid = "BFS-14"; :>> title = "GPC Soft Error Counter Anomaly"; :>> effectivity = "STS-115-999"; :>> changeNo = "058"; :>> measurementCount = 1; :>> numericLimitCount = 0; :>> sourcePage = 1517; :>> isCounted = true; }
            part <'LCO-399'> lco_399 : LccItem { doc /* BFS-15 */ :>> ssid = "BFS-15"; :>> title = "BFS I/O Error PCM Anomaly"; :>> effectivity = "STS-115-999"; :>> changeNo = "058"; :>> measurementCount = 0; :>> numericLimitCount = 0; :>> sourcePage = 1519; :>> isCounted = true; }
            part <'LCO-400'> lco_400 : LccItem { doc /* BFS-16 */ :>> ssid = "BFS-16"; :>> title = "BFS Battery Backup Unit (BBU) Anomaly"; :>> effectivity = "STS 115-999"; :>> changeNo = "065"; :>> measurementCount = 2; :>> numericLimitCount = 0; :>> sourcePage = 1523; :>> isCounted = true; }
            part <'LCO-594'> lco_594 : LccItem { doc /* BFS-00 */ :>> ssid = "BFS-00"; :>> title = ""; :>> effectivity = "N/A"; :>> changeNo = "065"; :>> measurementCount = 0; :>> numericLimitCount = 0; :>> sourcePage = 1469; :>> isCounted = false; }
            part <'LCO-595'> lco_595 : LccItem { doc /* BFS-07 */ :>> ssid = "BFS-07"; :>> title = ""; :>> effectivity = "STS-98,100,102,104,105,107-999"; :>> changeNo = "000"; :>> measurementCount = 0; :>> numericLimitCount = 0; :>> sourcePage = 1485; :>> isCounted = false; }
            part <'LCO-596'> lco_596 : LccItem { doc /* BFS-10 */ :>> ssid = "BFS-10"; :>> title = ""; :>> effectivity = "STS-115-999"; :>> changeNo = "063"; :>> measurementCount = 0; :>> numericLimitCount = 0; :>> sourcePage = 1493; :>> isCounted = false; }
            part <'LCO-597'> lco_597 : LccItem { doc /* BFS-13 */ :>> ssid = "BFS-13"; :>> title = ""; :>> effectivity = "STS-98,100,102,104,105,107-999"; :>> changeNo = "000"; :>> measurementCount = 0; :>> numericLimitCount = 0; :>> sourcePage = 1515; :>> isCounted = false; }
        }
        part sec_rsls : LccSection {
            :>> sectionNo = "36";
            :>> sectionTitle = "REDUNDANT SET LAUNCH SEQUENCER";
            :>> ssidPrefix = "RSLS";
            part <'LCO-401'> lco_401 : LccItem { doc /* RSLS-01 */ :>> ssid = "RSLS-01"; :>> title = "RSLS Hold/Abort"; :>> effectivity = "STS-98,100,102,104,105,107-999"; :>> changeNo = "000"; :>> measurementCount = 84; :>> numericLimitCount = 7; :>> sourcePage = 1531; :>> isCounted = true; }
            part <'LCO-598'> lco_598 : LccItem { doc /* RSLS-00 */ :>> ssid = "RSLS-00"; :>> title = ""; :>> effectivity = "N/A"; :>> changeNo = "000"; :>> measurementCount = 0; :>> numericLimitCount = 0; :>> sourcePage = 1527; :>> isCounted = false; }
        }
        part sec_pay : LccSection {
            :>> sectionNo = "37";
            :>> sectionTitle = "PAYLOADS";
            :>> ssidPrefix = "PAY";
            part <'LCO-402'> lco_402 : LccItem { doc /* PAY-01 */ :>> ssid = "PAY-01"; :>> title = "Payload Latch Anomaly"; :>> effectivity = "STS-115-999"; :>> changeNo = "060"; :>> measurementCount = 60; :>> numericLimitCount = 0; :>> sourcePage = 1539; :>> isCounted = true; }
            part <'LCO-599'> lco_599 : LccItem { doc /* PAY-00 */ :>> ssid = "PAY-00"; :>> title = ""; :>> effectivity = "N/A"; :>> changeNo = "070"; :>> measurementCount = 0; :>> numericLimitCount = 0; :>> sourcePage = 1535; :>> isCounted = false; }
            part <'LCO-600'> lco_600 : LccItem { doc /* PAY-02 */ :>> ssid = "PAY-02"; :>> title = ""; :>> effectivity = "STS-98,100,102,104,105,107-999"; :>> changeNo = "000"; :>> measurementCount = 0; :>> numericLimitCount = 0; :>> sourcePage = 1547; :>> isCounted = false; }
            part <'LCO-601'> lco_601 : LccItem { doc /* PAY-03 */ :>> ssid = "PAY-03"; :>> title = ""; :>> effectivity = "STS-98,100,102,104,105,107-999"; :>> changeNo = "000"; :>> measurementCount = 0; :>> numericLimitCount = 0; :>> sourcePage = 1549; :>> isCounted = false; }
        }
        part sec_roeu : LccSection {
            :>> sectionNo = "—";
            :>> sectionTitle = "目次に接頭辞が無い（付録の節の SSID）";
            :>> ssidPrefix = "ROEU";
            part <'LCO-403'> lco_403 : LccItem { doc /* ROEU-01 */ :>> ssid = "ROEU-01"; :>> title = "ROEU ODA Latch Anomaly"; :>> effectivity = "STS-107-999"; :>> changeNo = "011"; :>> measurementCount = 8; :>> numericLimitCount = 0; :>> sourcePage = 1551; :>> isCounted = true; }
            part <'LCO-404'> lco_404 : LccItem { doc /* ROEU-02 */ :>> ssid = "ROEU-02"; :>> title = "ROEU Relax Anomaly"; :>> effectivity = "STS-107-999"; :>> changeNo = "011"; :>> measurementCount = 4; :>> numericLimitCount = 0; :>> sourcePage = 1553; :>> isCounted = true; }
            part <'LCO-405'> lco_405 : LccItem { doc /* ROEU-03 */ :>> ssid = "ROEU-03"; :>> title = "ROEU Stow Anomaly"; :>> effectivity = "STS-107-999"; :>> changeNo = "011"; :>> measurementCount = 4; :>> numericLimitCount = 0; :>> sourcePage = 1555; :>> isCounted = true; }
        }
        part sec_sh : LccSection {
            :>> sectionNo = "—";
            :>> sectionTitle = "目次に接頭辞が無い（付録の節の SSID）";
            :>> ssidPrefix = "SH";
            part <'LCO-406'> lco_406 : LccItem { doc /* SH-01 */ :>> ssid = "SH-01"; :>> title = "Spacehab ARS(Cabin) Fan Anomaly"; :>> effectivity = "STS-114-999"; :>> changeNo = "037"; :>> measurementCount = 8; :>> numericLimitCount = 8; :>> sourcePage = 1557; :>> isCounted = true; }
            part <'LCO-407'> lco_407 : LccItem { doc /* SH-02 */ :>> ssid = "SH-02"; :>> title = "Spacehab Emergency Bus Voltage Anomaly"; :>> effectivity = "STS-107-999"; :>> changeNo = "013"; :>> measurementCount = 2; :>> numericLimitCount = 2; :>> sourcePage = 1563; :>> isCounted = true; }
            part <'LCO-408'> lco_408 : LccItem { doc /* SH-03 */ :>> ssid = "SH-03"; :>> title = "Spacehab Smoke/Fire Anomaly"; :>> effectivity = "STS-107-999"; :>> changeNo = "013"; :>> measurementCount = 8; :>> numericLimitCount = 0; :>> sourcePage = 1567; :>> isCounted = true; }
            part <'LCO-409'> lco_409 : LccItem { doc /* SH-04 */ :>> ssid = "SH-04"; :>> title = "Spacehab DMU Interface/Power Failure"; :>> effectivity = "STS-107-999"; :>> changeNo = "013"; :>> measurementCount = 2; :>> numericLimitCount = 0; :>> sourcePage = 1575; :>> isCounted = true; }
            part <'LCO-410'> lco_410 : LccItem { doc /* SH-06 */ :>> ssid = "SH-06"; :>> title = "Spacehab Main Power Anomaly"; :>> effectivity = "STS-114-999"; :>> changeNo = "037"; :>> measurementCount = 4; :>> numericLimitCount = 4; :>> sourcePage = 1579; :>> isCounted = true; }
            part <'LCO-411'> lco_411 : LccItem { doc /* SH-07 */ :>> ssid = "SH-07"; :>> title = "Spacehab Individual Halon Bottle Discharge Indication"; :>> effectivity = "STS-107-999"; :>> changeNo = "013"; :>> measurementCount = 10; :>> numericLimitCount = 0; :>> sourcePage = 1585; :>> isCounted = true; }
            part <'LCO-412'> lco_412 : LccItem { doc /* SH-08 */ :>> ssid = "SH-08"; :>> title = "Spacehab Cabin (ARS) HX Flow Rate (low) Anomaly"; :>> effectivity = "STS-114-999"; :>> changeNo = "037"; :>> measurementCount = 4; :>> numericLimitCount = 4; :>> sourcePage = 1587; :>> isCounted = true; }
            part <'LCO-413'> lco_413 : LccItem { doc /* SH-09 */ :>> ssid = "SH-09"; :>> title = "Spacehab Water Pump Accumulator Quantity (high/low) Anomaly"; :>> effectivity = "STS-107-999"; :>> changeNo = "013"; :>> measurementCount = 2; :>> numericLimitCount = 2; :>> sourcePage = 1595; :>> isCounted = true; }
            part <'LCO-414'> lco_414 : LccItem { doc /* SH-10 */ :>> ssid = "SH-10"; :>> title = "Spacehab Water Pump Inlet Pressure (high/low) Anomaly"; :>> effectivity = "STS-107-999"; :>> changeNo = "013"; :>> measurementCount = 2; :>> numericLimitCount = 2; :>> sourcePage = 1599; :>> isCounted = true; }
            part <'LCO-415'> lco_415 : LccItem { doc /* SH-11 */ :>> ssid = "SH-11"; :>> title = "Spacehab Water Pump Outlet Pressure (high/low) Anomaly"; :>> effectivity = "STS-114-999"; :>> changeNo = "037"; :>> measurementCount = 2; :>> numericLimitCount = 2; :>> sourcePage = 1603; :>> isCounted = true; }
            part <'LCO-416'> lco_416 : LccItem { doc /* SH-12 */ :>> ssid = "SH-12"; :>> title = "Payload Aft Main B Power Anomaly"; :>> effectivity = "STS-114-999"; :>> changeNo = "037"; :>> measurementCount = 1; :>> numericLimitCount = 0; :>> sourcePage = 1609; :>> isCounted = true; }
            part <'LCO-602'> lco_602 : LccItem { doc /* SH-05 */ :>> ssid = "SH-05"; :>> title = ""; :>> effectivity = "STS-98,100,102,104,105,107-999"; :>> changeNo = "000"; :>> measurementCount = 0; :>> numericLimitCount = 0; :>> sourcePage = 1577; :>> isCounted = false; }
            part <'LCO-603'> lco_603 : LccItem { doc /* SH-FG05 */ :>> ssid = "SH-FG05"; :>> title = ""; :>> effectivity = "STS-107-999"; :>> changeNo = "013"; :>> measurementCount = 0; :>> numericLimitCount = 0; :>> sourcePage = 1613; :>> isCounted = false; }
        }
        part sec_gse : LccSection {
            :>> sectionNo = "39";
            :>> sectionTitle = "GROUND SUPPORT EQUIPMENT";
            :>> ssidPrefix = "GSE";
            part <'LCO-417'> lco_417 : LccItem { doc /* GSE-01 */ :>> ssid = "GSE-01"; :>> title = "Orbiter Aft Compartment Purge Pressure Anomaly"; :>> effectivity = "STS-119,125-999"; :>> changeNo = "095"; :>> measurementCount = 4; :>> numericLimitCount = 4; :>> sourcePage = 1623; :>> isCounted = true; }
            part <'LCO-418'> lco_418 : LccItem { doc /* GSE-02 */ :>> ssid = "GSE-02"; :>> title = "Orbiter Purge Circuit #1 Pressure Anomaly"; :>> effectivity = "STS-119,125-999"; :>> changeNo = "095"; :>> measurementCount = 4; :>> numericLimitCount = 4; :>> sourcePage = 1627; :>> isCounted = true; }
            part <'LCO-419'> lco_419 : LccItem { doc /* GSE-03 */ :>> ssid = "GSE-03"; :>> title = "Orbiter Payload Bay Purge Pressure Anomaly"; :>> effectivity = "STS-119,125-999"; :>> changeNo = "095"; :>> measurementCount = 4; :>> numericLimitCount = 2; :>> sourcePage = 1631; :>> isCounted = true; }
            part <'LCO-420'> lco_420 : LccItem { doc /* GSE-04 */ :>> ssid = "GSE-04"; :>> title = "GSE PIC Rack Voltage Anomaly"; :>> effectivity = "STS-98,100,102,104,105,107-999"; :>> changeNo = "000"; :>> measurementCount = 8; :>> numericLimitCount = 8; :>> sourcePage = 1635; :>> isCounted = true; }
            part <'LCO-421'> lco_421 : LccItem { doc /* GSE-05 */ :>> ssid = "GSE-05"; :>> title = "TSM PIC Cap Voltage Anomaly"; :>> effectivity = "STS-98,100,102,104,105,107-999"; :>> changeNo = "000"; :>> measurementCount = 16; :>> numericLimitCount = 16; :>> sourcePage = 1637; :>> isCounted = true; }
            part <'LCO-422'> lco_422 : LccItem { doc /* GSE-06 */ :>> ssid = "GSE-06"; :>> title = "ET Vent Arm PIC Cap Voltage Anomaly"; :>> effectivity = "STS-98,100,102,104,105,107-999"; :>> changeNo = "000"; :>> measurementCount = 8; :>> numericLimitCount = 8; :>> sourcePage = 1639; :>> isCounted = true; }
            part <'LCO-423'> lco_423 : LccItem { doc /* GSE-07 */ :>> ssid = "GSE-07"; :>> title = "SRB Hold Down Post PIC Cap Voltage Anomaly"; :>> effectivity = "STS-98,100,102,104,105,107-999"; :>> changeNo = "000"; :>> measurementCount = 64; :>> numericLimitCount = 64; :>> sourcePage = 1641; :>> isCounted = true; }
            part <'LCO-424'> lco_424 : LccItem { doc /* GSE-08 */ :>> ssid = "GSE-08"; :>> title = "H2 Burn System PIC Rack Voltage Anomaly"; :>> effectivity = "STS-98,100,102,104,105,107-999"; :>> changeNo = "000"; :>> measurementCount = 8; :>> numericLimitCount = 8; :>> sourcePage = 1645; :>> isCounted = true; }
            part <'LCO-425'> lco_425 : LccItem { doc /* GSE-09 */ :>> ssid = "GSE-09"; :>> title = "Hydrogen Burn System PIC Cap Voltage Anomaly"; :>> effectivity = "STS-114-999"; :>> changeNo = "049"; :>> measurementCount = 24; :>> numericLimitCount = 24; :>> sourcePage = 1647; :>> isCounted = true; }
            part <'LCO-426'> lco_426 : LccItem { doc /* GSE-10 */ :>> ssid = "GSE-10"; :>> title = "Orbiter Access Arm Accumulator GN2 Pressure Anomaly"; :>> effectivity = "STS-119,124-999"; :>> changeNo = "091"; :>> measurementCount = 6; :>> numericLimitCount = 2; :>> sourcePage = 1651; :>> isCounted = true; }
            part <'LCO-427'> lco_427 : LccItem { doc /* GSE-11 */ :>> ssid = "GSE-11"; :>> title = "OAA Hydraulic Accumulator Level Anomaly"; :>> effectivity = "114-999"; :>> changeNo = "039"; :>> measurementCount = 8; :>> numericLimitCount = 0; :>> sourcePage = 1655; :>> isCounted = true; }
            part <'LCO-428'> lco_428 : LccItem { doc /* GSE-12 */ :>> ssid = "GSE-12"; :>> title = "OAA Retract Indication Anomaly"; :>> effectivity = "114-999"; :>> changeNo = "039"; :>> measurementCount = 8; :>> numericLimitCount = 2; :>> sourcePage = 1659; :>> isCounted = true; }
            part <'LCO-429'> lco_429 : LccItem { doc /* GSE-13 */ :>> ssid = "GSE-13"; :>> title = "GOX Vent Arm Retract Anomaly"; :>> effectivity = "STS-116-120,122-999"; :>> changeNo = "070"; :>> measurementCount = 8; :>> numericLimitCount = 2; :>> sourcePage = 1661; :>> isCounted = true; }
            part <'LCO-430'> lco_430 : LccItem { doc /* GSE-14 */ :>> ssid = "GSE-14"; :>> title = "Sound Suppression Water Valve Actuation Pressure Anomaly"; :>> effectivity = "STS-98,100,102,104,105,107-999"; :>> changeNo = "000"; :>> measurementCount = 4; :>> numericLimitCount = 4; :>> sourcePage = 1665; :>> isCounted = true; }
            part <'LCO-431'> lco_431 : LccItem { doc /* GSE-15 */ :>> ssid = "GSE-15"; :>> title = "Sound Suppression Water Tank Level Anomaly"; :>> effectivity = "STS-98,100,102,104,105,107-999"; :>> changeNo = "000"; :>> measurementCount = 4; :>> numericLimitCount = 4; :>> sourcePage = 1667; :>> isCounted = true; }
            part <'LCO-432'> lco_432 : LccItem { doc /* GSE-16 */ :>> ssid = "GSE-16"; :>> title = "Firing Room/Launch Processing System Command Bus Control Anomaly"; :>> effectivity = "STS-107-999"; :>> changeNo = "011"; :>> measurementCount = 2; :>> numericLimitCount = 0; :>> sourcePage = 1669; :>> isCounted = true; }
            part <'LCO-433'> lco_433 : LccItem { doc /* GSE-17 */ :>> ssid = "GSE-17"; :>> title = "Sound Suppression Solenoid Power Bus Indication Anomaly"; :>> effectivity = "STS-107-999"; :>> changeNo = "011"; :>> measurementCount = 2; :>> numericLimitCount = 0; :>> sourcePage = 1671; :>> isCounted = true; }
            part <'LCO-434'> lco_434 : LccItem { doc /* GSE-18 */ :>> ssid = "GSE-18"; :>> title = "Sound Suppression Postlift-off Vent Valve Open Indication Anomaly"; :>> effectivity = "STS-98,100,102,104,105,107-999"; :>> changeNo = "000"; :>> measurementCount = 3; :>> numericLimitCount = 0; :>> sourcePage = 1673; :>> isCounted = true; }
            part <'LCO-435'> lco_435 : LccItem { doc /* GSE-19 */ :>> ssid = "GSE-19"; :>> title = "Sound Suppression Prelift-off Valves Open Indication Anomaly"; :>> effectivity = "STS-98,100,102,104,105,107-999"; :>> changeNo = "000"; :>> measurementCount = 3; :>> numericLimitCount = 0; :>> sourcePage = 1675; :>> isCounted = true; }
            part <'LCO-436'> lco_436 : LccItem { doc /* GSE-20 */ :>> ssid = "GSE-20"; :>> title = "ETVAS Lanyard PIC Voltage Anomaly"; :>> effectivity = "STS-98,100,102,104,105,107-999"; :>> changeNo = "000"; :>> measurementCount = 8; :>> numericLimitCount = 8; :>> sourcePage = 1677; :>> isCounted = true; }
            part <'LCO-437'> lco_437 : LccItem { doc /* GSE-22 */ :>> ssid = "GSE-22"; :>> title = "SRB Aft Skirt GN2 Purge Anomaly"; :>> effectivity = "STS-119,123-999"; :>> changeNo = "087"; :>> measurementCount = 4; :>> numericLimitCount = 2; :>> sourcePage = 1681; :>> isCounted = true; }
            part <'LCO-438'> lco_438 : LccItem { doc /* GSE-23 */ :>> ssid = "GSE-23"; :>> title = "SRB Ignition Overpressure Water Bag Anomaly"; :>> effectivity = "STS-98,100,102,104,105,107-999"; :>> changeNo = "000"; :>> measurementCount = 0; :>> numericLimitCount = 0; :>> sourcePage = 1685; :>> isCounted = true; }
            part <'LCO-439'> lco_439 : LccItem { doc /* GSE-24 */ :>> ssid = "GSE-24"; :>> title = "Surface Wind Limits"; :>> effectivity = "STS-119,125-999"; :>> changeNo = "094"; :>> measurementCount = 0; :>> numericLimitCount = 0; :>> sourcePage = 1687; :>> isCounted = true; }
            part <'LCO-440'> lco_440 : LccItem { doc /* GSE-25 */ :>> ssid = "GSE-25"; :>> title = "Launch Release PIC Fire 1 Anomaly"; :>> effectivity = "STS-98,100,102,104,105,107-999"; :>> changeNo = "000"; :>> measurementCount = 12; :>> numericLimitCount = 0; :>> sourcePage = 1695; :>> isCounted = true; }
            part <'LCO-441'> lco_441 : LccItem { doc /* GSE-26 */ :>> ssid = "GSE-26"; :>> title = "Photo Optical Control System Anomaly"; :>> effectivity = "STS-114 thru 999"; :>> changeNo = "053"; :>> measurementCount = 0; :>> numericLimitCount = 0; :>> sourcePage = 1697; :>> isCounted = true; }
            part <'LCO-442'> lco_442 : LccItem { doc /* GSE-27 */ :>> ssid = "GSE-27"; :>> title = "GOX Vent Hood Purge Termination Anomaly"; :>> effectivity = "114-999"; :>> changeNo = "051"; :>> measurementCount = 12; :>> numericLimitCount = 12; :>> sourcePage = 1699; :>> isCounted = true; }
            part <'LCO-605'> lco_605 : LccItem { doc /* GSE-00 */ :>> ssid = "GSE-00"; :>> title = ""; :>> effectivity = "N/A"; :>> changeNo = "070"; :>> measurementCount = 0; :>> numericLimitCount = 0; :>> sourcePage = 1619; :>> isCounted = false; }
            part <'LCO-606'> lco_606 : LccItem { doc /* GSE-21 */ :>> ssid = "GSE-21"; :>> title = ""; :>> effectivity = "STS-116-120,122-999"; :>> changeNo = "070"; :>> measurementCount = 0; :>> numericLimitCount = 0; :>> sourcePage = 1679; :>> isCounted = false; }
            part <'LCO-607'> lco_607 : LccItem { doc /* GSE-FG01 */ :>> ssid = "GSE-FG01"; :>> title = ""; :>> effectivity = "STS-98,100,102,104,105,107-999"; :>> changeNo = "000"; :>> measurementCount = 0; :>> numericLimitCount = 0; :>> sourcePage = 1703; :>> isCounted = false; }
            part <'LCO-608'> lco_608 : LccItem { doc /* GSE-FG02 */ :>> ssid = "GSE-FG02"; :>> title = ""; :>> effectivity = "STS-98,100,102,104,105,107-999"; :>> changeNo = "000"; :>> measurementCount = 0; :>> numericLimitCount = 0; :>> sourcePage = 1705; :>> isCounted = false; }
            part <'LCO-609'> lco_609 : LccItem { doc /* GSE-FG03 */ :>> ssid = "GSE-FG03"; :>> title = ""; :>> effectivity = "STS-98,100,102,104,105,107-999"; :>> changeNo = "000"; :>> measurementCount = 0; :>> numericLimitCount = 0; :>> sourcePage = 1707; :>> isCounted = false; }
        }
        part sec_haz : LccSection {
            :>> sectionNo = "40";
            :>> sectionTitle = "HAZARDOUS GAS DETECTION SYSTEM";
            :>> ssidPrefix = "HAZ";
            part <'LCO-443'> lco_443 : LccItem { doc /* HAZ-01 */ :>> ssid = "HAZ-01"; :>> title = "Hazardous Gas Detection System Anomaly"; :>> effectivity = "STS-107,109-999"; :>> changeNo = "018"; :>> measurementCount = 0; :>> numericLimitCount = 0; :>> sourcePage = 1713; :>> isCounted = true; }
            part <'LCO-444'> lco_444 : LccItem { doc /* HAZ-02 */ :>> ssid = "HAZ-02"; :>> title = "Aft Compartment Helium Concentration Anomaly"; :>> effectivity = "STS-107,109-999"; :>> changeNo = "018"; :>> measurementCount = 0; :>> numericLimitCount = 0; :>> sourcePage = 1715; :>> isCounted = true; }
            part <'LCO-445'> lco_445 : LccItem { doc /* HAZ-03 */ :>> ssid = "HAZ-03"; :>> title = "Aft Compartment Hydrogen Concentration Anomaly"; :>> effectivity = "STS-107,109-999"; :>> changeNo = "018"; :>> measurementCount = 0; :>> numericLimitCount = 0; :>> sourcePage = 1717; :>> isCounted = true; }
            part <'LCO-446'> lco_446 : LccItem { doc /* HAZ-04 */ :>> ssid = "HAZ-04"; :>> title = "ET Intertank Hydrogen Concentration Anomaly"; :>> effectivity = "STS 115-999"; :>> changeNo = "065"; :>> measurementCount = 0; :>> numericLimitCount = 0; :>> sourcePage = 1721; :>> isCounted = true; }
            part <'LCO-447'> lco_447 : LccItem { doc /* HAZ-05 */ :>> ssid = "HAZ-05"; :>> title = "Mid Fuselage and Payload Bay Hydrogen Concentration Anomaly"; :>> effectivity = "STS-107,109-999"; :>> changeNo = "018"; :>> measurementCount = 0; :>> numericLimitCount = 0; :>> sourcePage = 1725; :>> isCounted = true; }
            part <'LCO-448'> lco_448 : LccItem { doc /* HAZ-06 */ :>> ssid = "HAZ-06"; :>> title = "Aft Compartment Oxygen Concentration Anomaly"; :>> effectivity = "STS-107,109-999"; :>> changeNo = "018"; :>> measurementCount = 0; :>> numericLimitCount = 0; :>> sourcePage = 1729; :>> isCounted = true; }
            part <'LCO-449'> lco_449 : LccItem { doc /* HAZ-07 */ :>> ssid = "HAZ-07"; :>> title = "ET Intertank Oxygen Concentration Anomaly"; :>> effectivity = "STS 115-999"; :>> changeNo = "065"; :>> measurementCount = 0; :>> numericLimitCount = 0; :>> sourcePage = 1731; :>> isCounted = true; }
            part <'LCO-450'> lco_450 : LccItem { doc /* HAZ-08 */ :>> ssid = "HAZ-08"; :>> title = "Mid Fuselage and Payload Bay Oxygen Concentration Anomaly"; :>> effectivity = "STS-107,109-999"; :>> changeNo = "018"; :>> measurementCount = 0; :>> numericLimitCount = 0; :>> sourcePage = 1735; :>> isCounted = true; }
            part <'LCO-451'> lco_451 : LccItem { doc /* HAZ-09 */ :>> ssid = "HAZ-09"; :>> title = "Excessive Hydrogen Concentration At ET Ground Umbilical Carrier Assembly"; :>> effectivity = "STS-114-999"; :>> changeNo = "046"; :>> measurementCount = 8; :>> numericLimitCount = 4; :>> sourcePage = 1737; :>> isCounted = true; }
            part <'LCO-452'> lco_452 : LccItem { doc /* HAZ-10 */ :>> ssid = "HAZ-10"; :>> title = "Excessive Hydrogen Concentration At LH2 T-0 Umbilical Carrier Plate Cavity"; :>> effectivity = "STS 115-999"; :>> changeNo = "065"; :>> measurementCount = 8; :>> numericLimitCount = 4; :>> sourcePage = 1741; :>> isCounted = true; }
            part <'LCO-453'> lco_453 : LccItem { doc /* HAZ-11 */ :>> ssid = "HAZ-11"; :>> title = "Excessive Hydrogen Concentration At T-0 8-inch Fill and Drain Line Purge Shroud"; :>> effectivity = "STS-114-999"; :>> changeNo = "046"; :>> measurementCount = 8; :>> numericLimitCount = 4; :>> sourcePage = 1745; :>> isCounted = true; }
            part <'LCO-454'> lco_454 : LccItem { doc /* HAZ-12 */ :>> ssid = "HAZ-12"; :>> title = "Excessive Hydrogen Concentration at Orbiter/ET Disconnect"; :>> effectivity = "STS-114-999"; :>> changeNo = "046"; :>> measurementCount = 8; :>> numericLimitCount = 4; :>> sourcePage = 1749; :>> isCounted = true; }
            part <'LCO-455'> lco_455 : LccItem { doc /* HAZ-13 */ :>> ssid = "HAZ-13"; :>> title = "Excessive Hydrogen Concentration Inside LH2 TSM"; :>> effectivity = "STS-114-999"; :>> changeNo = "046"; :>> measurementCount = 8; :>> numericLimitCount = 4; :>> sourcePage = 1753; :>> isCounted = true; }
            part <'LCO-610'> lco_610 : LccItem { doc /* HAZ-00 */ :>> ssid = "HAZ-00"; :>> title = ""; :>> effectivity = "N/A"; :>> changeNo = "046"; :>> measurementCount = 0; :>> numericLimitCount = 0; :>> sourcePage = 1709; :>> isCounted = false; }
            part <'LCO-611'> lco_611 : LccItem { doc /* HAZ-05a */ :>> ssid = "HAZ-05a"; :>> title = ""; :>> effectivity = "STS-98,100,102,104,105,107-999"; :>> changeNo = "000"; :>> measurementCount = 0; :>> numericLimitCount = 0; :>> sourcePage = 1727; :>> isCounted = false; }
            part <'LCO-612'> lco_612 : LccItem { doc /* HAZ-FG01 */ :>> ssid = "HAZ-FG01"; :>> title = ""; :>> effectivity = "STS-114-999"; :>> changeNo = "046"; :>> measurementCount = 0; :>> numericLimitCount = 0; :>> sourcePage = 1757; :>> isCounted = false; }
            part <'LCO-613'> lco_613 : LccItem { doc /* HAZ-FG02 */ :>> ssid = "HAZ-FG02"; :>> title = ""; :>> effectivity = "STS-107,109-999"; :>> changeNo = "018"; :>> measurementCount = 0; :>> numericLimitCount = 0; :>> sourcePage = 1759; :>> isCounted = false; }
            part <'LCO-614'> lco_614 : LccItem { doc /* HAZ-FG03 */ :>> ssid = "HAZ-FG03"; :>> title = ""; :>> effectivity = "STS-114-999"; :>> changeNo = "046"; :>> measurementCount = 0; :>> numericLimitCount = 0; :>> sourcePage = 1761; :>> isCounted = false; }
            part <'LCO-615'> lco_615 : LccItem { doc /* HAZ-FG04 */ :>> ssid = "HAZ-FG04"; :>> title = ""; :>> effectivity = "STS-119,125-999"; :>> changeNo = "094"; :>> measurementCount = 0; :>> numericLimitCount = 0; :>> sourcePage = 1763; :>> isCounted = false; }
        }
        part sec_lps : LccSection {
            :>> sectionNo = "41";
            :>> sectionTitle = "LAUNCH PROCESSING SYSTEM";
            :>> ssidPrefix = "LPS";
            part <'LCO-456'> lco_456 : LccItem { doc /* LPS-02 */ :>> ssid = "LPS-02"; :>> title = "Integration Console Anomaly"; :>> effectivity = "STS-98,100,102,104,105,107-999"; :>> changeNo = "000"; :>> measurementCount = 0; :>> numericLimitCount = 0; :>> sourcePage = 1771; :>> isCounted = true; }
            part <'LCO-457'> lco_457 : LccItem { doc /* LPS-03 */ :>> ssid = "LPS-03"; :>> title = "Backup Console Anomaly"; :>> effectivity = "STS-98,100,102,104,105,107-999"; :>> changeNo = "000"; :>> measurementCount = 0; :>> numericLimitCount = 0; :>> sourcePage = 1773; :>> isCounted = true; }
            part <'LCO-458'> lco_458 : LccItem { doc /* LPS-06 */ :>> ssid = "LPS-06"; :>> title = "Operations Console (C3) (LOX, MPL and SSME) Anomaly"; :>> effectivity = "STS-98,100,102,104,105,107-999"; :>> changeNo = "000"; :>> measurementCount = 0; :>> numericLimitCount = 0; :>> sourcePage = 1779; :>> isCounted = true; }
            part <'LCO-459'> lco_459 : LccItem { doc /* LPS-07 */ :>> ssid = "LPS-07"; :>> title = "Operations Console (C4) (LH2 and MPS) Anomaly"; :>> effectivity = "STS-98,100,102,104,105,107-999"; :>> changeNo = "000"; :>> measurementCount = 0; :>> numericLimitCount = 0; :>> sourcePage = 1781; :>> isCounted = true; }
            part <'LCO-460'> lco_460 : LccItem { doc /* LPS-17 */ :>> ssid = "LPS-17"; :>> title = "Launch Data Bus (LDB) Anomaly"; :>> effectivity = "STS-114-999"; :>> changeNo = "051"; :>> measurementCount = 2; :>> numericLimitCount = 0; :>> sourcePage = 1801; :>> isCounted = true; }
            part <'LCO-461'> lco_461 : LccItem { doc /* LPS-18 */ :>> ssid = "LPS-18"; :>> title = "GPC PCM Front End Processor (FEP) Anomaly"; :>> effectivity = "STS-119,125-999"; :>> changeNo = "095"; :>> measurementCount = 0; :>> numericLimitCount = 0; :>> sourcePage = 1805; :>> isCounted = true; }
            part <'LCO-462'> lco_462 : LccItem { doc /* LPS-19 */ :>> ssid = "LPS-19"; :>> title = "OI PCM Front End Processor (FEP) Anomaly"; :>> effectivity = "STS-119,125-999"; :>> changeNo = "095"; :>> measurementCount = 0; :>> numericLimitCount = 0; :>> sourcePage = 1809; :>> isCounted = true; }
            part <'LCO-463'> lco_463 : LccItem { doc /* LPS-20 */ :>> ssid = "LPS-20"; :>> title = "GS1 Front End Processor (FEP) Anomaly"; :>> effectivity = "STS-107,112-999"; :>> changeNo = "030"; :>> measurementCount = 1; :>> numericLimitCount = 0; :>> sourcePage = 1813; :>> isCounted = true; }
            part <'LCO-464'> lco_464 : LccItem { doc /* LPS-21 */ :>> ssid = "LPS-21"; :>> title = "GS2 Front End Processor (FEP) Anomaly"; :>> effectivity = "STS-107,112-999"; :>> changeNo = "030"; :>> measurementCount = 1; :>> numericLimitCount = 0; :>> sourcePage = 1815; :>> isCounted = true; }
            part <'LCO-465'> lco_465 : LccItem { doc /* LPS-25 */ :>> ssid = "LPS-25"; :>> title = "GS3 Front End Processor (FEP) Anomaly"; :>> effectivity = "STS-107,112-999"; :>> changeNo = "030"; :>> measurementCount = 1; :>> numericLimitCount = 0; :>> sourcePage = 1823; :>> isCounted = true; }
            part <'LCO-616'> lco_616 : LccItem { doc /* LPS-00 */ :>> ssid = "LPS-00"; :>> title = ""; :>> effectivity = "N/A"; :>> changeNo = "030"; :>> measurementCount = 0; :>> numericLimitCount = 0; :>> sourcePage = 1765; :>> isCounted = false; }
            part <'LCO-617'> lco_617 : LccItem { doc /* LPS-01 */ :>> ssid = "LPS-01"; :>> title = ""; :>> effectivity = "STS-98,100,102,104,105,107-999"; :>> changeNo = "000"; :>> measurementCount = 0; :>> numericLimitCount = 0; :>> sourcePage = 1769; :>> isCounted = false; }
            part <'LCO-618'> lco_618 : LccItem { doc /* LPS-04 */ :>> ssid = "LPS-04"; :>> title = ""; :>> effectivity = "STS-98,100,102,104,105,107-999"; :>> changeNo = "000"; :>> measurementCount = 0; :>> numericLimitCount = 0; :>> sourcePage = 1775; :>> isCounted = false; }
            part <'LCO-619'> lco_619 : LccItem { doc /* LPS-05 */ :>> ssid = "LPS-05"; :>> title = ""; :>> effectivity = "STS-98,100,102,104,105,107-999"; :>> changeNo = "000"; :>> measurementCount = 0; :>> numericLimitCount = 0; :>> sourcePage = 1777; :>> isCounted = false; }
            part <'LCO-620'> lco_620 : LccItem { doc /* LPS-08 */ :>> ssid = "LPS-08"; :>> title = ""; :>> effectivity = "STS-98,100,102,104,105,107-999"; :>> changeNo = "000"; :>> measurementCount = 0; :>> numericLimitCount = 0; :>> sourcePage = 1783; :>> isCounted = false; }
            part <'LCO-621'> lco_621 : LccItem { doc /* LPS-09 */ :>> ssid = "LPS-09"; :>> title = ""; :>> effectivity = "STS-98,100,102,104,105,107-999"; :>> changeNo = "000"; :>> measurementCount = 0; :>> numericLimitCount = 0; :>> sourcePage = 1785; :>> isCounted = false; }
            part <'LCO-622'> lco_622 : LccItem { doc /* LPS-10 */ :>> ssid = "LPS-10"; :>> title = ""; :>> effectivity = "STS-98,100,102,104,105,107-999"; :>> changeNo = "000"; :>> measurementCount = 0; :>> numericLimitCount = 0; :>> sourcePage = 1787; :>> isCounted = false; }
            part <'LCO-623'> lco_623 : LccItem { doc /* LPS-11 */ :>> ssid = "LPS-11"; :>> title = ""; :>> effectivity = "STS-98,100,102,104,105,107-999"; :>> changeNo = "000"; :>> measurementCount = 0; :>> numericLimitCount = 0; :>> sourcePage = 1789; :>> isCounted = false; }
            part <'LCO-624'> lco_624 : LccItem { doc /* LPS-12 */ :>> ssid = "LPS-12"; :>> title = ""; :>> effectivity = "STS-98,100,102,104,105,107-999"; :>> changeNo = "000"; :>> measurementCount = 0; :>> numericLimitCount = 0; :>> sourcePage = 1791; :>> isCounted = false; }
            part <'LCO-625'> lco_625 : LccItem { doc /* LPS-13 */ :>> ssid = "LPS-13"; :>> title = ""; :>> effectivity = "STS-98,100,102,104,105,107-999"; :>> changeNo = "000"; :>> measurementCount = 0; :>> numericLimitCount = 0; :>> sourcePage = 1793; :>> isCounted = false; }
            part <'LCO-626'> lco_626 : LccItem { doc /* LPS-14 */ :>> ssid = "LPS-14"; :>> title = ""; :>> effectivity = "STS-98,100,102,104,105,107-999"; :>> changeNo = "000"; :>> measurementCount = 0; :>> numericLimitCount = 0; :>> sourcePage = 1795; :>> isCounted = false; }
            part <'LCO-627'> lco_627 : LccItem { doc /* LPS-15 */ :>> ssid = "LPS-15"; :>> title = ""; :>> effectivity = "STS-98,100,102,104,105,107-999"; :>> changeNo = "000"; :>> measurementCount = 0; :>> numericLimitCount = 0; :>> sourcePage = 1797; :>> isCounted = false; }
            part <'LCO-628'> lco_628 : LccItem { doc /* LPS-16 */ :>> ssid = "LPS-16"; :>> title = ""; :>> effectivity = "STS-98,100,102,104,105,107-999"; :>> changeNo = "000"; :>> measurementCount = 0; :>> numericLimitCount = 0; :>> sourcePage = 1799; :>> isCounted = false; }
            part <'LCO-629'> lco_629 : LccItem { doc /* LPS-22 */ :>> ssid = "LPS-22"; :>> title = ""; :>> effectivity = "STS-98,100,102,104,105,107-999"; :>> changeNo = "000"; :>> measurementCount = 0; :>> numericLimitCount = 0; :>> sourcePage = 1817; :>> isCounted = false; }
            part <'LCO-630'> lco_630 : LccItem { doc /* LPS-23 */ :>> ssid = "LPS-23"; :>> title = ""; :>> effectivity = "STS-98,100,102,104,105,107-999"; :>> changeNo = "000"; :>> measurementCount = 0; :>> numericLimitCount = 0; :>> sourcePage = 1819; :>> isCounted = false; }
            part <'LCO-631'> lco_631 : LccItem { doc /* LPS-24 */ :>> ssid = "LPS-24"; :>> title = ""; :>> effectivity = "STS-98,100,102,104,105,107-999"; :>> changeNo = "000"; :>> measurementCount = 0; :>> numericLimitCount = 0; :>> sourcePage = 1821; :>> isCounted = false; }
        }
        part sec_com : LccSection {
            :>> sectionNo = "42";
            :>> sectionTitle = "COMMUNICATIONS";
            :>> ssidPrefix = "COM";
            part <'LCO-466'> lco_466 : LccItem { doc /* COM-01 */ :>> ssid = "COM-01"; :>> title = "Astrocomm Voice Anomaly"; :>> effectivity = "STS-98,100,102,104,105,107-999"; :>> changeNo = "000"; :>> measurementCount = 0; :>> numericLimitCount = 0; :>> sourcePage = 1829; :>> isCounted = true; }
            part <'LCO-467'> lco_467 : LccItem { doc /* COM-02 */ :>> ssid = "COM-02"; :>> title = "Voice Command Channel Anomaly"; :>> effectivity = "STS-98,100,102,104,105,107-999"; :>> changeNo = "000"; :>> measurementCount = 0; :>> numericLimitCount = 0; :>> sourcePage = 1831; :>> isCounted = true; }
            part <'LCO-468'> lco_468 : LccItem { doc /* COM-03 */ :>> ssid = "COM-03"; :>> title = "Voice Communication NASA Test Director (NTD) and Flight Director Anomaly"; :>> effectivity = "STS-98,100,102,104,105,107-999"; :>> changeNo = "000"; :>> measurementCount = 0; :>> numericLimitCount = 0; :>> sourcePage = 1833; :>> isCounted = true; }
            part <'LCO-469'> lco_469 : LccItem { doc /* COM-04 */ :>> ssid = "COM-04"; :>> title = "Range Safety Officer (RSO) Communications Anomaly"; :>> effectivity = "STS-98,100,102,104,105,107-999"; :>> changeNo = "000"; :>> measurementCount = 0; :>> numericLimitCount = 0; :>> sourcePage = 1835; :>> isCounted = true; }
            part <'LCO-632'> lco_632 : LccItem { doc /* COM-00 */ :>> ssid = "COM-00"; :>> title = ""; :>> effectivity = "N/A"; :>> changeNo = "000"; :>> measurementCount = 0; :>> numericLimitCount = 0; :>> sourcePage = 1825; :>> isCounted = false; }
        }
        part sec_egr : LccSection {
            :>> sectionNo = "43";
            :>> sectionTitle = "EGRESS";
            :>> ssidPrefix = "EGR";
            part <'LCO-470'> lco_470 : LccItem { doc /* EGR-01 */ :>> ssid = "EGR-01"; :>> title = "Slidewire System Anomaly"; :>> effectivity = "STS-98,100,102,104,105,107-999"; :>> changeNo = "000"; :>> measurementCount = 0; :>> numericLimitCount = 0; :>> sourcePage = 1841; :>> isCounted = true; }
            part <'LCO-471'> lco_471 : LccItem { doc /* EGR-02 */ :>> ssid = "EGR-02"; :>> title = "Armored Personnel Carriers Anomaly"; :>> effectivity = "STS-98,100,102,104,105,107-999"; :>> changeNo = "000"; :>> measurementCount = 0; :>> numericLimitCount = 0; :>> sourcePage = 1843; :>> isCounted = true; }
            part <'LCO-472'> lco_472 : LccItem { doc /* EGR-03 */ :>> ssid = "EGR-03"; :>> title = "Firex Loop & Tank T-3 Pressure Anomaly"; :>> effectivity = "STS-114-999"; :>> changeNo = "053"; :>> measurementCount = 0; :>> numericLimitCount = 0; :>> sourcePage = 1845; :>> isCounted = true; }
            part <'LCO-473'> lco_473 : LccItem { doc /* EGR-04 */ :>> ssid = "EGR-04"; :>> title = "Pad Elevators Anomaly"; :>> effectivity = "STS-98,100,102,104,105,107-999"; :>> changeNo = "000"; :>> measurementCount = 0; :>> numericLimitCount = 0; :>> sourcePage = 1849; :>> isCounted = true; }
            part <'LCO-633'> lco_633 : LccItem { doc /* EGR-00 */ :>> ssid = "EGR-00"; :>> title = ""; :>> effectivity = "N/A"; :>> changeNo = "066"; :>> measurementCount = 0; :>> numericLimitCount = 0; :>> sourcePage = 1837; :>> isCounted = false; }
            part <'LCO-634'> lco_634 : LccItem { doc /* EGR-05 */ :>> ssid = "EGR-05"; :>> title = ""; :>> effectivity = "STS-115-999"; :>> changeNo = "066"; :>> measurementCount = 0; :>> numericLimitCount = 0; :>> sourcePage = 1851; :>> isCounted = false; }
            part <'LCO-635'> lco_635 : LccItem { doc /* EGR-06 */ :>> ssid = "EGR-06"; :>> title = ""; :>> effectivity = "STS-115-999"; :>> changeNo = "066"; :>> measurementCount = 0; :>> numericLimitCount = 0; :>> sourcePage = 1853; :>> isCounted = false; }
            part <'LCO-636'> lco_636 : LccItem { doc /* EGR-07 */ :>> ssid = "EGR-07"; :>> title = ""; :>> effectivity = "STS-115-999"; :>> changeNo = "066"; :>> measurementCount = 0; :>> numericLimitCount = 0; :>> sourcePage = 1855; :>> isCounted = false; }
            part <'LCO-637'> lco_637 : LccItem { doc /* EGR-08 */ :>> ssid = "EGR-08"; :>> title = ""; :>> effectivity = "STS-115-999"; :>> changeNo = "066"; :>> measurementCount = 0; :>> numericLimitCount = 0; :>> sourcePage = 1857; :>> isCounted = false; }
            part <'LCO-638'> lco_638 : LccItem { doc /* EGR-09 */ :>> ssid = "EGR-09"; :>> title = ""; :>> effectivity = "STS-115-999"; :>> changeNo = "066"; :>> measurementCount = 0; :>> numericLimitCount = 0; :>> sourcePage = 1859; :>> isCounted = false; }
        }
        part sec_mila : LccSection {
            :>> sectionNo = "44";
            :>> sectionTitle = "MERRITT ISLAND LAUNCH AREA";
            :>> ssidPrefix = "MILA";
            part <'LCO-474'> lco_474 : LccItem { doc /* MILA-01 */ :>> ssid = "MILA-01"; :>> title = "Forward Link System Anomaly"; :>> effectivity = "STS-98,100,102,104,105,107-999"; :>> changeNo = "000"; :>> measurementCount = 0; :>> numericLimitCount = 0; :>> sourcePage = 1865; :>> isCounted = true; }
            part <'LCO-475'> lco_475 : LccItem { doc /* MILA-02 */ :>> ssid = "MILA-02"; :>> title = "S-Band Return Link System Anomaly"; :>> effectivity = "STS-98,100,102,104,105,107-999"; :>> changeNo = "000"; :>> measurementCount = 0; :>> numericLimitCount = 0; :>> sourcePage = 1867; :>> isCounted = true; }
            part <'LCO-476'> lco_476 : LccItem { doc /* MILA-03 */ :>> ssid = "MILA-03"; :>> title = "MILA UHF High Gain Tracking System Anomaly"; :>> effectivity = "STS-98,100,102,104,105,107-999"; :>> changeNo = "000"; :>> measurementCount = 0; :>> numericLimitCount = 0; :>> sourcePage = 1869; :>> isCounted = true; }
            part <'LCO-639'> lco_639 : LccItem { doc /* MILA-00 */ :>> ssid = "MILA-00"; :>> title = ""; :>> effectivity = "N/A"; :>> changeNo = "000"; :>> measurementCount = 0; :>> numericLimitCount = 0; :>> sourcePage = 1861; :>> isCounted = false; }
        }
        part sec_guid : LccSection {
            :>> sectionNo = "C";
            :>> sectionTitle = "GUIDELINES AND DEFINITIONS";
            :>> ssidPrefix = "GUID";
            part <'LCO-477'> lco_477 : LccItem { doc /* GUID-FG01 */ :>> ssid = "GUID-FG01"; :>> title = "(2)"; :>> effectivity = "STS-114-999"; :>> changeNo = "038"; :>> measurementCount = 0; :>> numericLimitCount = 0; :>> sourcePage = 1935; :>> isCounted = true; }
            part <'LCO-647'> lco_647 : LccItem { doc /* GUID-00 */ :>> ssid = "GUID-00"; :>> title = ""; :>> effectivity = "N/A"; :>> changeNo = "038"; :>> measurementCount = 0; :>> numericLimitCount = 0; :>> sourcePage = 1915; :>> isCounted = false; }
            part <'LCO-648'> lco_648 : LccItem { doc /* GUID-01 */ :>> ssid = "GUID-01"; :>> title = ""; :>> effectivity = "STS-115-999"; :>> changeNo = "064"; :>> measurementCount = 0; :>> numericLimitCount = 0; :>> sourcePage = 1919; :>> isCounted = false; }
        }
        part sec_ice : LccSection {
            :>> sectionNo = "F";
            :>> sectionTitle = "ICE LAUNCH COMMIT CRITERIA";
            :>> ssidPrefix = "ICE";
            part <'LCO-478'> lco_478 : LccItem { doc /* ICE-01 */ :>> ssid = "ICE-01"; :>> title = "Pre-Launch Debris and ET TPS Damage/Defects"; :>> effectivity = "STS-114-999"; :>> changeNo = "052"; :>> measurementCount = 0; :>> numericLimitCount = 0; :>> sourcePage = 1977; :>> isCounted = true; }
            part <'LCO-479'> lco_479 : LccItem { doc /* ICE-04 */ :>> ssid = "ICE-04"; :>> title = "Cryogenic Propellant Visual Leakage Anomaly"; :>> effectivity = "STS-107,114-999"; :>> changeNo = "033"; :>> measurementCount = 0; :>> numericLimitCount = 0; :>> sourcePage = 1983; :>> isCounted = true; }
            part <'LCO-662'> lco_662 : LccItem { doc /* ICE-00 */ :>> ssid = "ICE-00"; :>> title = ""; :>> effectivity = "N/A"; :>> changeNo = "052"; :>> measurementCount = 0; :>> numericLimitCount = 0; :>> sourcePage = 1973; :>> isCounted = false; }
            part <'LCO-663'> lco_663 : LccItem { doc /* ICE-02 */ :>> ssid = "ICE-02"; :>> title = ""; :>> effectivity = "STS-98,100,102,104,105,107-999"; :>> changeNo = "000"; :>> measurementCount = 0; :>> numericLimitCount = 0; :>> sourcePage = 1979; :>> isCounted = false; }
            part <'LCO-664'> lco_664 : LccItem { doc /* ICE-03 */ :>> ssid = "ICE-03"; :>> title = ""; :>> effectivity = "STS-98,100,102,104,105,107-999"; :>> changeNo = "000"; :>> measurementCount = 0; :>> numericLimitCount = 0; :>> sourcePage = 1981; :>> isCounted = false; }
            part <'LCO-665'> lco_665 : LccItem { doc /* ICE-FG01 */ :>> ssid = "ICE-FG01"; :>> title = ""; :>> effectivity = "STS-114-999"; :>> changeNo = "052"; :>> measurementCount = 0; :>> numericLimitCount = 0; :>> sourcePage = 1985; :>> isCounted = false; }
            part <'LCO-666'> lco_666 : LccItem { doc /* ICE-FG02 */ :>> ssid = "ICE-FG02"; :>> title = ""; :>> effectivity = "STS-114-999"; :>> changeNo = "052"; :>> measurementCount = 0; :>> numericLimitCount = 0; :>> sourcePage = 1987; :>> isCounted = false; }
            part <'LCO-667'> lco_667 : LccItem { doc /* ICE-FG03 */ :>> ssid = "ICE-FG03"; :>> title = ""; :>> effectivity = "STS-114-999"; :>> changeNo = "052"; :>> measurementCount = 0; :>> numericLimitCount = 0; :>> sourcePage = 1989; :>> isCounted = false; }
            part <'LCO-668'> lco_668 : LccItem { doc /* ICE-FG04 */ :>> ssid = "ICE-FG04"; :>> title = ""; :>> effectivity = "STS-114-999"; :>> changeNo = "052"; :>> measurementCount = 0; :>> numericLimitCount = 0; :>> sourcePage = 1991; :>> isCounted = false; }
        }
        part sec_tlp : LccSection {
            :>> sectionNo = "—";
            :>> sectionTitle = "目次に接頭辞が無い（付録の節の SSID）";
            :>> ssidPrefix = "TLP";
            part <'LCO-480'> lco_480 : LccItem { doc /* TLP-01 */ :>> ssid = "TLP-01"; :>> title = ""; :>> effectivity = "N/A"; :>> changeNo = "000"; :>> measurementCount = 0; :>> numericLimitCount = 0; :>> sourcePage = 1; :>> isCounted = false; }
        }
        part sec_cs : LccSection {
            :>> sectionNo = "—";
            :>> sectionTitle = "目次に接頭辞が無い（付録の節の SSID）";
            :>> ssidPrefix = "CS";
            part <'LCO-481'> lco_481 : LccItem { doc /* CS-01 */ :>> ssid = "CS-01"; :>> title = ""; :>> effectivity = "N/A"; :>> changeNo = "097"; :>> measurementCount = 0; :>> numericLimitCount = 0; :>> sourcePage = 3; :>> isCounted = false; }
        }
        part sec_fwd : LccSection {
            :>> sectionNo = "—";
            :>> sectionTitle = "目次に接頭辞が無い（付録の節の SSID）";
            :>> ssidPrefix = "FWD";
            part <'LCO-482'> lco_482 : LccItem { doc /* FWD-01 */ :>> ssid = "FWD-01"; :>> title = ""; :>> effectivity = "STS-98,100,102,104,105,107-999"; :>> changeNo = "000"; :>> measurementCount = 0; :>> numericLimitCount = 0; :>> sourcePage = 5; :>> isCounted = false; }
        }
        part sec_toc : LccSection {
            :>> sectionNo = "—";
            :>> sectionTitle = "目次に接頭辞が無い（付録の節の SSID）";
            :>> ssidPrefix = "TOC";
            part <'LCO-483'> lco_483 : LccItem { doc /* TOC-01 */ :>> ssid = "TOC-01"; :>> title = ""; :>> effectivity = "N/A"; :>> changeNo = "046"; :>> measurementCount = 0; :>> numericLimitCount = 0; :>> sourcePage = 7; :>> isCounted = false; }
        }
        part sec_loc : LccSection {
            :>> sectionNo = "—";
            :>> sectionTitle = "目次に接頭辞が無い（付録の節の SSID）";
            :>> ssidPrefix = "LOC";
            part <'LCO-484'> lco_484 : LccItem { doc /* LOC-01 */ :>> ssid = "LOC-01"; :>> title = ""; :>> effectivity = "STS-98,100,102,104,105,107-999"; :>> changeNo = "000"; :>> measurementCount = 0; :>> numericLimitCount = 0; :>> sourcePage = 11; :>> isCounted = false; }
            part <'LCO-485'> lco_485 : LccItem { doc /* LOC-02 */ :>> ssid = "LOC-02"; :>> title = ""; :>> effectivity = "STS-98,100,102,104,105,107-999"; :>> changeNo = "000"; :>> measurementCount = 0; :>> numericLimitCount = 0; :>> sourcePage = 23; :>> isCounted = false; }
            part <'LCO-486'> lco_486 : LccItem { doc /* LOC-03 */ :>> ssid = "LOC-03"; :>> title = ""; :>> effectivity = "STS-98,100,102,104,105,107-999"; :>> changeNo = "000"; :>> measurementCount = 0; :>> numericLimitCount = 0; :>> sourcePage = 31; :>> isCounted = false; }
            part <'LCO-487'> lco_487 : LccItem { doc /* LOC-04 */ :>> ssid = "LOC-04"; :>> title = ""; :>> effectivity = "STS-98,100,102,104,105,107-999"; :>> changeNo = "000"; :>> measurementCount = 0; :>> numericLimitCount = 0; :>> sourcePage = 43; :>> isCounted = false; }
            part <'LCO-488'> lco_488 : LccItem { doc /* LOC-05 */ :>> ssid = "LOC-05"; :>> title = ""; :>> effectivity = "N/A"; :>> changeNo = "097"; :>> measurementCount = 0; :>> numericLimitCount = 0; :>> sourcePage = 49; :>> isCounted = false; }
        }
        part sec_gen : LccSection {
            :>> sectionNo = "1";
            :>> sectionTitle = "INTRODUCTION AND GENERAL CRITERIA";
            :>> ssidPrefix = "GEN";
            part <'LCO-489'> lco_489 : LccItem { doc /* GEN-00 */ :>> ssid = "GEN-00"; :>> title = ""; :>> effectivity = "N/A"; :>> changeNo = "000"; :>> measurementCount = 0; :>> numericLimitCount = 0; :>> sourcePage = 59; :>> isCounted = false; }
            part <'LCO-490'> lco_490 : LccItem { doc /* GEN-01 */ :>> ssid = "GEN-01"; :>> title = ""; :>> effectivity = "STS-119,124-999"; :>> changeNo = "091"; :>> measurementCount = 0; :>> numericLimitCount = 0; :>> sourcePage = 61; :>> isCounted = false; }
        }
        part sec_impl : LccSection {
            :>> sectionNo = "2";
            :>> sectionTitle = "KSC GENERAL LAUNCH COMMIT CRITERIA IMPLEMENTATION";
            :>> ssidPrefix = "IMPL";
            part <'LCO-491'> lco_491 : LccItem { doc /* IMPL-00 */ :>> ssid = "IMPL-00"; :>> title = ""; :>> effectivity = "N/A"; :>> changeNo = "000"; :>> measurementCount = 0; :>> numericLimitCount = 0; :>> sourcePage = 69; :>> isCounted = false; }
            part <'LCO-492'> lco_492 : LccItem { doc /* IMPL-01 */ :>> ssid = "IMPL-01"; :>> title = ""; :>> effectivity = "STS-119, 125-999"; :>> changeNo = "094"; :>> measurementCount = 0; :>> numericLimitCount = 0; :>> sourcePage = 71; :>> isCounted = false; }
        }
        part sec_crew : LccSection {
            :>> sectionNo = "3";
            :>> sectionTitle = "LAUNCH/LANDING WINDOW AND CREW RESTRICTIONS";
            :>> ssidPrefix = "CREW";
            part <'LCO-493'> lco_493 : LccItem { doc /* CREW-00 */ :>> ssid = "CREW-00"; :>> title = ""; :>> effectivity = "N/A"; :>> changeNo = "000"; :>> measurementCount = 0; :>> numericLimitCount = 0; :>> sourcePage = 75; :>> isCounted = false; }
            part <'LCO-494'> lco_494 : LccItem { doc /* CREW-01 */ :>> ssid = "CREW-01"; :>> title = ""; :>> effectivity = "STS-119,125-999"; :>> changeNo = "094"; :>> measurementCount = 0; :>> numericLimitCount = 0; :>> sourcePage = 77; :>> isCounted = false; }
        }
        part sec_wea : LccSection {
            :>> sectionNo = "4";
            :>> sectionTitle = "WEATHER RULES";
            :>> ssidPrefix = "WEA";
            part <'LCO-495'> lco_495 : LccItem { doc /* WEA-00 */ :>> ssid = "WEA-00"; :>> title = ""; :>> effectivity = "N/A"; :>> changeNo = "000"; :>> measurementCount = 0; :>> numericLimitCount = 0; :>> sourcePage = 79; :>> isCounted = false; }
            part <'LCO-496'> lco_496 : LccItem { doc /* WEA-01 */ :>> ssid = "WEA-01"; :>> title = ""; :>> effectivity = "STS-114-999"; :>> changeNo = "056"; :>> measurementCount = 0; :>> numericLimitCount = 0; :>> sourcePage = 81; :>> isCounted = false; }
        }
        part sec_etr : LccSection {
            :>> sectionNo = "5";
            :>> sectionTitle = "RANGE SAFETY CRITERIA";
            :>> ssidPrefix = "ETR";
            part <'LCO-497'> lco_497 : LccItem { doc /* ETR-00 */ :>> ssid = "ETR-00"; :>> title = ""; :>> effectivity = "N/A"; :>> changeNo = "000"; :>> measurementCount = 0; :>> numericLimitCount = 0; :>> sourcePage = 97; :>> isCounted = false; }
            part <'LCO-498'> lco_498 : LccItem { doc /* ETR-01 */ :>> ssid = "ETR-01"; :>> title = ""; :>> effectivity = "STS-114-999"; :>> changeNo = "038"; :>> measurementCount = 0; :>> numericLimitCount = 0; :>> sourcePage = 99; :>> isCounted = false; }
        }
        part sec_safe : LccSection {
            :>> sectionNo = "6";
            :>> sectionTitle = "KSC FLIGHT CREW AND PAD PERSONNEL SAFETY";
            :>> ssidPrefix = "SAFE";
            part <'LCO-499'> lco_499 : LccItem { doc /* SAFE-00 */ :>> ssid = "SAFE-00"; :>> title = ""; :>> effectivity = "N/A"; :>> changeNo = "000"; :>> measurementCount = 0; :>> numericLimitCount = 0; :>> sourcePage = 107; :>> isCounted = false; }
            part <'LCO-500'> lco_500 : LccItem { doc /* SAFE-01 */ :>> ssid = "SAFE-01"; :>> title = ""; :>> effectivity = "STS-115-999"; :>> changeNo = "066"; :>> measurementCount = 0; :>> numericLimitCount = 0; :>> sourcePage = 109; :>> isCounted = false; }
        }
        part sec_hold : LccSection {
            :>> sectionNo = "7";
            :>> sectionTitle = "HOLD/CUTOFF GUIDELINES";
            :>> ssidPrefix = "HOLD";
            part <'LCO-501'> lco_501 : LccItem { doc /* HOLD-00 */ :>> ssid = "HOLD-00"; :>> title = ""; :>> effectivity = "N/A"; :>> changeNo = "000"; :>> measurementCount = 0; :>> numericLimitCount = 0; :>> sourcePage = 123; :>> isCounted = false; }
            part <'LCO-502'> lco_502 : LccItem { doc /* HOLD-01 */ :>> ssid = "HOLD-01"; :>> title = ""; :>> effectivity = "STS-115-999"; :>> changeNo = "064"; :>> measurementCount = 0; :>> numericLimitCount = 0; :>> sourcePage = 125; :>> isCounted = false; }
        }
        part sec_seq : LccSection {
            :>> sectionNo = "8";
            :>> sectionTitle = "SPACE SHUTTLE VEHICLE FUNCTIONAL SEQUENCE";
            :>> ssidPrefix = "SEQ";
            part <'LCO-503'> lco_503 : LccItem { doc /* SEQ-00 */ :>> ssid = "SEQ-00"; :>> title = ""; :>> effectivity = "N/A"; :>> changeNo = "000"; :>> measurementCount = 0; :>> numericLimitCount = 0; :>> sourcePage = 127; :>> isCounted = false; }
            part <'LCO-504'> lco_504 : LccItem { doc /* SEQ-01 */ :>> ssid = "SEQ-01"; :>> title = ""; :>> effectivity = "STS 119,120,122-999"; :>> changeNo = "081"; :>> measurementCount = 0; :>> numericLimitCount = 0; :>> sourcePage = 129; :>> isCounted = false; }
        }
        part sec_trss : LccSection {
            :>> sectionNo = "18";
            :>> sectionTitle = "EXTERNAL TANK RANGE SAFETY SUBSYSTEM";
            :>> ssidPrefix = "TRSS";
            part <'LCO-533'> lco_533 : LccItem { doc /* TRSS-00 */ :>> ssid = "TRSS-00"; :>> title = ""; :>> effectivity = "N/A"; :>> changeNo = "000"; :>> measurementCount = 0; :>> numericLimitCount = 0; :>> sourcePage = 385; :>> isCounted = false; }
        }
        part sec_sl : LccSection {
            :>> sectionNo = "38";
            :>> sectionTitle = "SPACELAB";
            :>> ssidPrefix = "SL";
            part <'LCO-604'> lco_604 : LccItem { doc /* SL-00 */ :>> ssid = "SL-00"; :>> title = ""; :>> effectivity = "N/A"; :>> changeNo = "000"; :>> measurementCount = 0; :>> numericLimitCount = 0; :>> sourcePage = 1615; :>> isCounted = false; }
        }
        part sec_aa : LccSection {
            :>> sectionNo = "A";
            :>> sectionTitle = "ABBREVIATIONS AND ACRONYMS";
            :>> ssidPrefix = "AA";
            part <'LCO-640'> lco_640 : LccItem { doc /* AA-00 */ :>> ssid = "AA-00"; :>> title = ""; :>> effectivity = "N/A"; :>> changeNo = "000"; :>> measurementCount = 0; :>> numericLimitCount = 0; :>> sourcePage = 1871; :>> isCounted = false; }
            part <'LCO-641'> lco_641 : LccItem { doc /* AA-01 */ :>> ssid = "AA-01"; :>> title = ""; :>> effectivity = "STS-119,123-999"; :>> changeNo = "088"; :>> measurementCount = 0; :>> numericLimitCount = 0; :>> sourcePage = 1873; :>> isCounted = false; }
        }
        part sec_chg : LccSection {
            :>> sectionNo = "B";
            :>> sectionTitle = "CHANGE PROCEDURES";
            :>> ssidPrefix = "CHG";
            part <'LCO-642'> lco_642 : LccItem { doc /* CHG-00 */ :>> ssid = "CHG-00"; :>> title = ""; :>> effectivity = "N/A"; :>> changeNo = "000"; :>> measurementCount = 0; :>> numericLimitCount = 0; :>> sourcePage = 1901; :>> isCounted = false; }
            part <'LCO-643'> lco_643 : LccItem { doc /* CHG-01 */ :>> ssid = "CHG-01"; :>> title = ""; :>> effectivity = "STS-119,124-999"; :>> changeNo = "091"; :>> measurementCount = 0; :>> numericLimitCount = 0; :>> sourcePage = 1903; :>> isCounted = false; }
            part <'LCO-644'> lco_644 : LccItem { doc /* CHG-FG01 */ :>> ssid = "CHG-FG01"; :>> title = ""; :>> effectivity = "STS-114-999"; :>> changeNo = "038"; :>> measurementCount = 0; :>> numericLimitCount = 0; :>> sourcePage = 1909; :>> isCounted = false; }
            part <'LCO-645'> lco_645 : LccItem { doc /* CHG-FG02 */ :>> ssid = "CHG-FG02"; :>> title = ""; :>> effectivity = "STS-114-999"; :>> changeNo = "038"; :>> measurementCount = 0; :>> numericLimitCount = 0; :>> sourcePage = 1911; :>> isCounted = false; }
            part <'LCO-646'> lco_646 : LccItem { doc /* CHG-FG03 */ :>> ssid = "CHG-FG03"; :>> title = ""; :>> effectivity = "STS-98,100,102,104,105,107-999"; :>> changeNo = "000"; :>> measurementCount = 0; :>> numericLimitCount = 0; :>> sourcePage = 1913; :>> isCounted = false; }
        }
        part sec_ref : LccSection {
            :>> sectionNo = "D";
            :>> sectionTitle = "REFERENCES";
            :>> ssidPrefix = "REF";
            part <'LCO-649'> lco_649 : LccItem { doc /* REF-00 */ :>> ssid = "REF-00"; :>> title = ""; :>> effectivity = "N/A"; :>> changeNo = "000"; :>> measurementCount = 0; :>> numericLimitCount = 0; :>> sourcePage = 1937; :>> isCounted = false; }
            part <'LCO-650'> lco_650 : LccItem { doc /* REF-01 */ :>> ssid = "REF-01"; :>> title = ""; :>> effectivity = "STS-119,125-999"; :>> changeNo = "094"; :>> measurementCount = 0; :>> numericLimitCount = 0; :>> sourcePage = 1939; :>> isCounted = false; }
        }
        part sec_fsum : LccSection {
            :>> sectionNo = "E";
            :>> sectionTitle = "FAULT SUMMARY MESSAGE AND CAUTION AND WARNING LISTINGS";
            :>> ssidPrefix = "FSUM";
            part <'LCO-651'> lco_651 : LccItem { doc /* FSUM-00 */ :>> ssid = "FSUM-00"; :>> title = ""; :>> effectivity = "N/A"; :>> changeNo = "000"; :>> measurementCount = 0; :>> numericLimitCount = 0; :>> sourcePage = 1941; :>> isCounted = false; }
            part <'LCO-652'> lco_652 : LccItem { doc /* FSUM-01 */ :>> ssid = "FSUM-01"; :>> title = ""; :>> effectivity = "STS-119,125-999"; :>> changeNo = "094"; :>> measurementCount = 0; :>> numericLimitCount = 0; :>> sourcePage = 1945; :>> isCounted = false; }
            part <'LCO-653'> lco_653 : LccItem { doc /* FSUM-02 */ :>> ssid = "FSUM-02"; :>> title = ""; :>> effectivity = "STS-98,100,102,104,105,107-999"; :>> changeNo = "000"; :>> measurementCount = 0; :>> numericLimitCount = 0; :>> sourcePage = 1947; :>> isCounted = false; }
            part <'LCO-654'> lco_654 : LccItem { doc /* FSUM-03 */ :>> ssid = "FSUM-03"; :>> title = ""; :>> effectivity = "STS-98,100,102,104,105,107-999"; :>> changeNo = "000"; :>> measurementCount = 0; :>> numericLimitCount = 0; :>> sourcePage = 1949; :>> isCounted = false; }
            part <'LCO-655'> lco_655 : LccItem { doc /* FSUM-04 */ :>> ssid = "FSUM-04"; :>> title = ""; :>> effectivity = "STS-98,100,102,104,105,107-999"; :>> changeNo = "000"; :>> measurementCount = 0; :>> numericLimitCount = 0; :>> sourcePage = 1951; :>> isCounted = false; }
            part <'LCO-656'> lco_656 : LccItem { doc /* FSUM-05 */ :>> ssid = "FSUM-05"; :>> title = ""; :>> effectivity = "STS-98,100,102,104,105,107-999"; :>> changeNo = "000"; :>> measurementCount = 0; :>> numericLimitCount = 0; :>> sourcePage = 1953; :>> isCounted = false; }
            part <'LCO-657'> lco_657 : LccItem { doc /* FSUM-06 */ :>> ssid = "FSUM-06"; :>> title = ""; :>> effectivity = "STS-98,100,102,104,105,107-999"; :>> changeNo = "000"; :>> measurementCount = 0; :>> numericLimitCount = 0; :>> sourcePage = 1955; :>> isCounted = false; }
            part <'LCO-658'> lco_658 : LccItem { doc /* FSUM-07 */ :>> ssid = "FSUM-07"; :>> title = ""; :>> effectivity = "STS-98,100,102,104,105,107-999"; :>> changeNo = "000"; :>> measurementCount = 0; :>> numericLimitCount = 0; :>> sourcePage = 1957; :>> isCounted = false; }
            part <'LCO-659'> lco_659 : LccItem { doc /* FSUM-08 */ :>> ssid = "FSUM-08"; :>> title = ""; :>> effectivity = "STS 118-120,122-999"; :>> changeNo = "078"; :>> measurementCount = 0; :>> numericLimitCount = 0; :>> sourcePage = 1959; :>> isCounted = false; }
        }
        part sec_cw : LccSection {
            :>> sectionNo = "—";
            :>> sectionTitle = "目次に接頭辞が無い（付録の節の SSID）";
            :>> ssidPrefix = "CW";
            part <'LCO-660'> lco_660 : LccItem { doc /* CW-01 */ :>> ssid = "CW-01"; :>> title = ""; :>> effectivity = "STS-119,125-999"; :>> changeNo = "094"; :>> measurementCount = 0; :>> numericLimitCount = 0; :>> sourcePage = 1961; :>> isCounted = false; }
            part <'LCO-661'> lco_661 : LccItem { doc /* CW-02 */ :>> ssid = "CW-02"; :>> title = ""; :>> effectivity = "STS-98,100,102,104,105,107-999"; :>> changeNo = "000"; :>> measurementCount = 0; :>> numericLimitCount = 0; :>> sourcePage = 1969; :>> isCounted = false; }
        }
        part sec_ttest : LccSection {
            :>> sectionNo = "—";
            :>> sectionTitle = "目次に接頭辞が無い（付録の節の SSID）";
            :>> ssidPrefix = "TTEST";
            part <'LCO-669'> lco_669 : LccItem { doc /* TTEST-00 */ :>> ssid = "TTEST-00"; :>> title = ""; :>> effectivity = "N/A"; :>> changeNo = "070"; :>> measurementCount = 0; :>> numericLimitCount = 0; :>> sourcePage = 1993; :>> isCounted = false; }
        }
        part sec_mel : LccSection {
            :>> sectionNo = "H";
            :>> sectionTitle = "MINIMUM EQUIPMENT LIST";
            :>> ssidPrefix = "MEL";
            part <'LCO-670'> lco_670 : LccItem { doc /* MEL-00 */ :>> ssid = "MEL-00"; :>> title = ""; :>> effectivity = "N/A"; :>> changeNo = "096"; :>> measurementCount = 0; :>> numericLimitCount = 0; :>> sourcePage = 1997; :>> isCounted = false; }
            part <'LCO-671'> lco_671 : LccItem { doc /* MEL-01 */ :>> ssid = "MEL-01"; :>> title = ""; :>> effectivity = "STS-115-999"; :>> changeNo = "063"; :>> measurementCount = 0; :>> numericLimitCount = 0; :>> sourcePage = 2001; :>> isCounted = false; }
            part <'LCO-672'> lco_672 : LccItem { doc /* MEL-02 */ :>> ssid = "MEL-02"; :>> title = ""; :>> effectivity = "STS-115-999"; :>> changeNo = "063"; :>> measurementCount = 0; :>> numericLimitCount = 0; :>> sourcePage = 2005; :>> isCounted = false; }
            part <'LCO-673'> lco_673 : LccItem { doc /* MEL-03 */ :>> ssid = "MEL-03"; :>> title = ""; :>> effectivity = "STS-115-999"; :>> changeNo = "063"; :>> measurementCount = 0; :>> numericLimitCount = 0; :>> sourcePage = 2009; :>> isCounted = false; }
            part <'LCO-674'> lco_674 : LccItem { doc /* MEL-04 */ :>> ssid = "MEL-04"; :>> title = ""; :>> effectivity = "STS 118-120,122-999"; :>> changeNo = "078"; :>> measurementCount = 0; :>> numericLimitCount = 0; :>> sourcePage = 2013; :>> isCounted = false; }
            part <'LCO-675'> lco_675 : LccItem { doc /* MEL-05 */ :>> ssid = "MEL-05"; :>> title = ""; :>> effectivity = "STS-115-999"; :>> changeNo = "063"; :>> measurementCount = 0; :>> numericLimitCount = 0; :>> sourcePage = 2021; :>> isCounted = false; }
            part <'LCO-676'> lco_676 : LccItem { doc /* MEL-06 */ :>> ssid = "MEL-06"; :>> title = ""; :>> effectivity = "STS-98,100,102,104,105,107-999"; :>> changeNo = "000"; :>> measurementCount = 0; :>> numericLimitCount = 0; :>> sourcePage = 2037; :>> isCounted = false; }
            part <'LCO-677'> lco_677 : LccItem { doc /* MEL-07 */ :>> ssid = "MEL-07"; :>> title = ""; :>> effectivity = "STS-98,100,102,104,105,107-999"; :>> changeNo = "000"; :>> measurementCount = 0; :>> numericLimitCount = 0; :>> sourcePage = 2039; :>> isCounted = false; }
            part <'LCO-678'> lco_678 : LccItem { doc /* MEL-08 */ :>> ssid = "MEL-08"; :>> title = ""; :>> effectivity = "STS-98,100,102,104,105,107-999"; :>> changeNo = "000"; :>> measurementCount = 0; :>> numericLimitCount = 0; :>> sourcePage = 2043; :>> isCounted = false; }
            part <'LCO-679'> lco_679 : LccItem { doc /* MEL-09 */ :>> ssid = "MEL-09"; :>> title = ""; :>> effectivity = "STS-98,100,102,104,105,107-999"; :>> changeNo = "000"; :>> measurementCount = 0; :>> numericLimitCount = 0; :>> sourcePage = 2051; :>> isCounted = false; }
            part <'LCO-680'> lco_680 : LccItem { doc /* MEL-10 */ :>> ssid = "MEL-10"; :>> title = ""; :>> effectivity = "STS-119,123-999"; :>> changeNo = "087"; :>> measurementCount = 0; :>> numericLimitCount = 0; :>> sourcePage = 2061; :>> isCounted = false; }
            part <'LCO-681'> lco_681 : LccItem { doc /* MEL-11 */ :>> ssid = "MEL-11"; :>> title = ""; :>> effectivity = "STS-114-999"; :>> changeNo = "053"; :>> measurementCount = 0; :>> numericLimitCount = 0; :>> sourcePage = 2063; :>> isCounted = false; }
            part <'LCO-682'> lco_682 : LccItem { doc /* MEL-12 */ :>> ssid = "MEL-12"; :>> title = ""; :>> effectivity = "STS-114-999"; :>> changeNo = "056"; :>> measurementCount = 0; :>> numericLimitCount = 0; :>> sourcePage = 2067; :>> isCounted = false; }
            part <'LCO-683'> lco_683 : LccItem { doc /* MEL-13(124) */ :>> ssid = "MEL-13(124)"; :>> title = ""; :>> effectivity = "STS-124"; :>> changeNo = "090"; :>> measurementCount = 0; :>> numericLimitCount = 0; :>> sourcePage = 2069; :>> isCounted = false; }
            part <'LCO-684'> lco_684 : LccItem { doc /* MEL-13(125) */ :>> ssid = "MEL-13(125)"; :>> title = ""; :>> effectivity = "STS-125"; :>> changeNo = "096"; :>> measurementCount = 0; :>> numericLimitCount = 0; :>> sourcePage = 2079; :>> isCounted = false; }
            part <'LCO-685'> lco_685 : LccItem { doc /* MEL-13(126) */ :>> ssid = "MEL-13(126)"; :>> title = ""; :>> effectivity = "STS-126"; :>> changeNo = "096"; :>> measurementCount = 0; :>> numericLimitCount = 0; :>> sourcePage = 2089; :>> isCounted = false; }
            part <'LCO-686'> lco_686 : LccItem { doc /* MEL-13(400) */ :>> ssid = "MEL-13(400)"; :>> title = ""; :>> effectivity = "STS-400"; :>> changeNo = "096"; :>> measurementCount = 0; :>> numericLimitCount = 0; :>> sourcePage = 2099; :>> isCounted = false; }
        }
        part sec_mil : LccSection {
            :>> sectionNo = "I";
            :>> sectionTitle = "MANDATORY INSTRUMENTATION LIST";
            :>> ssidPrefix = "MIL";
            part <'LCO-687'> lco_687 : LccItem { doc /* MIL-00 */ :>> ssid = "MIL-00"; :>> title = ""; :>> effectivity = "N/A"; :>> changeNo = "000"; :>> measurementCount = 0; :>> numericLimitCount = 0; :>> sourcePage = 2109; :>> isCounted = false; }
            part <'LCO-688'> lco_688 : LccItem { doc /* MIL-01 */ :>> ssid = "MIL-01"; :>> title = ""; :>> effectivity = "STS-98,100,102,104,105,107-999"; :>> changeNo = "000"; :>> measurementCount = 0; :>> numericLimitCount = 0; :>> sourcePage = 2113; :>> isCounted = false; }
            part <'LCO-689'> lco_689 : LccItem { doc /* MIL-02 */ :>> ssid = "MIL-02"; :>> title = ""; :>> effectivity = "STS 118-120,122-999"; :>> changeNo = "078"; :>> measurementCount = 850; :>> numericLimitCount = 24; :>> sourcePage = 2115; :>> isCounted = false; }
            part <'LCO-690'> lco_690 : LccItem { doc /* MIL-03 */ :>> ssid = "MIL-03"; :>> title = ""; :>> effectivity = "STS-98,100,102,104,105,107-999"; :>> changeNo = "000"; :>> measurementCount = 510; :>> numericLimitCount = 0; :>> sourcePage = 2153; :>> isCounted = false; }
            part <'LCO-691'> lco_691 : LccItem { doc /* MIL-04 */ :>> ssid = "MIL-04"; :>> title = ""; :>> effectivity = "STS-98,100,102,104,105,107-999"; :>> changeNo = "000"; :>> measurementCount = 71; :>> numericLimitCount = 0; :>> sourcePage = 2195; :>> isCounted = false; }
            part <'LCO-692'> lco_692 : LccItem { doc /* MIL-05 */ :>> ssid = "MIL-05"; :>> title = ""; :>> effectivity = "STS-114-999"; :>> changeNo = "056"; :>> measurementCount = 96; :>> numericLimitCount = 0; :>> sourcePage = 2203; :>> isCounted = false; }
            part <'LCO-693'> lco_693 : LccItem { doc /* MIL-06 */ :>> ssid = "MIL-06"; :>> title = ""; :>> effectivity = "STS-98,100,102,104,105,107-999"; :>> changeNo = "000"; :>> measurementCount = 79; :>> numericLimitCount = 1; :>> sourcePage = 2211; :>> isCounted = false; }
            part <'LCO-694'> lco_694 : LccItem { doc /* MIL-07 */ :>> ssid = "MIL-07"; :>> title = ""; :>> effectivity = "STS-114-999"; :>> changeNo = "054"; :>> measurementCount = 227; :>> numericLimitCount = 0; :>> sourcePage = 2219; :>> isCounted = false; }
            part <'LCO-695'> lco_695 : LccItem { doc /* MIL-08 */ :>> ssid = "MIL-08"; :>> title = ""; :>> effectivity = "STS-98,100,102,104,105,107-999"; :>> changeNo = "000"; :>> measurementCount = 0; :>> numericLimitCount = 0; :>> sourcePage = 2235; :>> isCounted = false; }
            part <'LCO-696'> lco_696 : LccItem { doc /* MIL-09 */ :>> ssid = "MIL-09"; :>> title = ""; :>> effectivity = "STS-98,100,102,104,105,107-999"; :>> changeNo = "000"; :>> measurementCount = 3; :>> numericLimitCount = 0; :>> sourcePage = 2237; :>> isCounted = false; }
        }
        part sec_waiv : LccSection {
            :>> sectionNo = "J";
            :>> sectionTitle = "WAIVERS/DEVIATIONS";
            :>> ssidPrefix = "WAIV";
            part <'LCO-697'> lco_697 : LccItem { doc /* WAIV-00 */ :>> ssid = "WAIV-00"; :>> title = ""; :>> effectivity = "N/A"; :>> changeNo = "000"; :>> measurementCount = 0; :>> numericLimitCount = 0; :>> sourcePage = 2239; :>> isCounted = false; }
            part <'LCO-698'> lco_698 : LccItem { doc /* WAIV-01 */ :>> ssid = "WAIV-01"; :>> title = ""; :>> effectivity = "STS-98,100,102,104,105,107-999"; :>> changeNo = "000"; :>> measurementCount = 0; :>> numericLimitCount = 0; :>> sourcePage = 2241; :>> isCounted = false; }
            part <'LCO-699'> lco_699 : LccItem { doc /* WAIV-02 */ :>> ssid = "WAIV-02"; :>> title = ""; :>> effectivity = "STS-119,124-999"; :>> changeNo = "090"; :>> measurementCount = 0; :>> numericLimitCount = 0; :>> sourcePage = 2257; :>> isCounted = false; }
        }
    }
    part lccWeather {
        doc /* LCC 本体 WEA-01 の数値つき規則（§1.1〜§1.4）。条項どうしの対応は 2010 の雷の基準とは取らない */
        part <'LWR-001'> lwr_001 : WeatherRule { doc /* WEA-01 1.1.A.1 */ :>> clause = "1.1.A.1"; :>> limitValues = "24 時間・41.3 °F"; :>> ruleText = "Propellant loading of the ET shall not be initiated if the average temperature for the 24 hours prior to tanking is below 41.3 degrees Fahrenheit (F)."; :>> sourcePage = 81; }
        part <'LWR-002'> lwr_002 : WeatherRule { doc /* WEA-01 1.1.A.2 */ :>> clause = "1.1.A.2"; :>> limitValues = "24 時間・33 °F"; :>> ruleText = "Propellant loading of the ET shall not be initiated if the temperature anytime during the 24 hours prior to tanking drops below 33 degrees F."; :>> sourcePage = 81; }
        part <'LWR-003'> lwr_003 : WeatherRule { doc /* WEA-01 1.1.B.1 */ :>> clause = "1.1.B.1"; :>> limitValues = "99 °F・30 分"; :>> ruleText = "The countdown shall not be continued nor the SSV launched if the ambient temperature during this time period exceeds 99 degrees F for more than 30 consecutive minutes."; :>> sourcePage = 82; }
        part <'LWR-004'> lwr_004 : WeatherRule { doc /* WEA-01 1.1.B.2 */ :>> clause = "1.1.B.2"; :>> limitValues = "30 分・64 %"; :>> ruleText = "The SSV shall not be launched if the ambient temperature (Tamb) is lower than the minimum temperature limit (Tmin) (Table 1.1A), for more than 30 consecutive minutes unless the Preplanned Contingency "; :>> sourcePage = 82; }
        part <'LWR-005'> lwr_005 : WeatherRule { doc /* WEA-01 1.1.B.2 表1.1A 風速 0-1 kt */ :>> clause = "1.1.B.2 表1.1A 風速 0-1 kt"; :>> limitValues = "48 °F・47 °F・46 °F・45 °F・44 °F"; :>> ruleText = "最低外気温（°F）。相対湿度 0-64%・65-74%・75-79%・80-89%・90-100% の順に 48・47・46・45・44"; :>> sourcePage = 82; }
        part <'LWR-006'> lwr_006 : WeatherRule { doc /* WEA-01 1.1.B.2 表1.1A 風速 2 kt */ :>> clause = "1.1.B.2 表1.1A 風速 2 kt"; :>> limitValues = "47 °F・46 °F・45 °F・44 °F・43 °F"; :>> ruleText = "最低外気温（°F）。相対湿度 0-64%・65-74%・75-79%・80-89%・90-100% の順に 47・46・45・44・43"; :>> sourcePage = 82; }
        part <'LWR-007'> lwr_007 : WeatherRule { doc /* WEA-01 1.1.B.2 表1.1A 風速 3 kt */ :>> clause = "1.1.B.2 表1.1A 風速 3 kt"; :>> limitValues = "41 °F・40 °F・39 °F"; :>> ruleText = "最低外気温（°F）。相対湿度 0-64%・65-74%・75-79%・80-89%・90-100% の順に 41・41・41・40・39"; :>> sourcePage = 82; }
        part <'LWR-008'> lwr_008 : WeatherRule { doc /* WEA-01 1.1.B.2 表1.1A 風速 4 kt */ :>> clause = "1.1.B.2 表1.1A 風速 4 kt"; :>> limitValues = "39 °F・38 °F"; :>> ruleText = "最低外気温（°F）。相対湿度 0-64%・65-74%・75-79%・80-89%・90-100% の順に 39・39・39・39・38"; :>> sourcePage = 82; }
        part <'LWR-009'> lwr_009 : WeatherRule { doc /* WEA-01 1.1.B.2 表1.1A 風速 5-7 kt */ :>> clause = "1.1.B.2 表1.1A 風速 5-7 kt"; :>> limitValues = "38 °F"; :>> ruleText = "最低外気温（°F）。相対湿度 0-64%・65-74%・75-79%・80-89%・90-100% の順に 38・38・38・38・38"; :>> sourcePage = 82; }
        part <'LWR-010'> lwr_010 : WeatherRule { doc /* WEA-01 1.1.B.2 表1.1A 風速 8-14 kt */ :>> clause = "1.1.B.2 表1.1A 風速 8-14 kt"; :>> limitValues = "37 °F"; :>> ruleText = "最低外気温（°F）。相対湿度 0-64%・65-74%・75-79%・80-89%・90-100% の順に 37・37・37・37・37"; :>> sourcePage = 82; }
        part <'LWR-011'> lwr_011 : WeatherRule { doc /* WEA-01 1.1.B.2 表1.1A 風速 >14 kt */ :>> clause = "1.1.B.2 表1.1A 風速 >14 kt"; :>> limitValues = "36 °F"; :>> ruleText = "最低外気温（°F）。相対湿度 0-64%・65-74%・75-79%・80-89%・90-100% の順に 36・36・36・36・36"; :>> sourcePage = 82; }
        part <'LWR-012'> lwr_012 : WeatherRule { doc /* WEA-01 1.3 */ :>> clause = "1.3"; :>> limitValues = "60 ft"; :>> ruleText = "Surface Wind Limits. Surface wind limits for launch (Measured at 60 feet above natural grade). Surface wind criteria are specified in LCC GSE-24."; :>> sourcePage = 85; }
        part <'LWR-013'> lwr_013 : WeatherRule { doc /* WEA-01 1.4.A.1 */ :>> clause = "1.4.A.1"; :>> limitValues = "30 分"; :>> ruleText = "Do not launch for 30 minutes after any type of lightning occurs in a thunderstorm if the flight path will carry the SSV within 10 Nautical Miles (NM) of that thunderstorm."; :>> sourcePage = 86; }
        part <'LWR-014'> lwr_014 : WeatherRule { doc /* WEA-01 1.4.A.2 */ :>> clause = "1.4.A.2"; :>> limitValues = "30 分・10 NM"; :>> ruleText = "Do not launch for 30 minutes after any type of lightning occurs within 10 NM of the flight path unless:"; :>> sourcePage = 86; }
        part <'LWR-015'> lwr_015 : WeatherRule { doc /* WEA-01 1.4.A.2.a */ :>> clause = "1.4.A.2.a"; :>> limitValues = "10 NM"; :>> ruleText = "The cloud that produced the lightning is not within 10 NM of flight path; -and-"; :>> sourcePage = 86; }
        part <'LWR-016'> lwr_016 : WeatherRule { doc /* WEA-01 1.4.A.2.b */ :>> clause = "1.4.A.2.b"; :>> limitValues = "5 NM"; :>> ruleText = "There is at least one working field mill within 5 NM of each such lightning flash; -and-"; :>> sourcePage = 86; }
        part <'LWR-017'> lwr_017 : WeatherRule { doc /* WEA-01 1.4.A.2.c */ :>> clause = "1.4.A.2.c"; :>> limitValues = "5 NM・1000 V/m・15 分"; :>> ruleText = "The absolute values of all electric field measurements at the surface, within 5 NM of the flight path and at the mill(s) specified in subparagraph 1.4.A.2.b, have been less than 1000 Volts/meter (V/m)"; :>> sourcePage = 86; }
        part <'LWR-018'> lwr_018 : WeatherRule { doc /* WEA-01 1.4.A.2.c (注ii) */ :>> clause = "1.4.A.2.c (注ii)"; :>> limitValues = "30 分"; :>> ruleText = "If a cumulus cloud remains 30 minutes after the last lightning occurs in a thunderstorm, then section 1.4.B. applies. Definitions: Anvil, Electric Field Measurement at the Surface, Flight Path, Thunde"; :>> sourcePage = 86; }
        part <'LWR-019'> lwr_019 : WeatherRule { doc /* WEA-01 1.4.B.1 */ :>> clause = "1.4.B.1"; :>> limitValues = "10 NM・-20 °C"; :>> ruleText = "Do not launch if the flight path will carry the SSV within 10 NM of any cumulus cloud with its cloud top higher than the -20 degrees Celsius (C) level."; :>> sourcePage = 86; }
        part <'LWR-020'> lwr_020 : WeatherRule { doc /* WEA-01 1.4.B.2 */ :>> clause = "1.4.B.2"; :>> limitValues = "5 NM・-10 °C"; :>> ruleText = "Do not launch if the flight path will carry the SSV within 5 NM of any cumulus cloud with its cloud top higher than the -10 degrees C level."; :>> sourcePage = 86; }
        part <'LWR-021'> lwr_021 : WeatherRule { doc /* WEA-01 1.4.B.3 */ :>> clause = "1.4.B.3"; :>> limitValues = "-5 °C"; :>> ruleText = "Do not launch if the flight path will carry the SSV through any cumulus cloud with its cloud top higher than the -5 degrees C level."; :>> sourcePage = 86; }
        part <'LWR-022'> lwr_022 : WeatherRule { doc /* WEA-01 1.4.B.4 */ :>> clause = "1.4.B.4"; :>> limitValues = "5 °C・-5 °C"; :>> ruleText = "Do not launch if the flight path will carry the SSV through any cumulus cloud with its cloud top between the +5 degrees C and -5 degrees C levels unless:"; :>> sourcePage = 86; }
        part <'LWR-023'> lwr_023 : WeatherRule { doc /* WEA-01 1.4.B.4.b */ :>> clause = "1.4.B.4.b"; :>> limitValues = "2 NM"; :>> ruleText = "The horizontal distance from the center of the cloud top to at least one working field mill is less than 2 NM; -and-"; :>> sourcePage = 86; }
        part <'LWR-024'> lwr_024 : WeatherRule { doc /* WEA-01 1.4.B.4.c */ :>> clause = "1.4.B.4.c"; :>> limitValues = "5 NM"; :>> ruleText = "All electric field measurements at the surface within 5 NM of the flight path and at the mill(s) specified in subparagraph"; :>> sourcePage = 87; }
        part <'LWR-025'> lwr_025 : WeatherRule { doc /* WEA-01 1.4 */ :>> clause = "1.4"; :>> limitValues = "-100 V/m・500 V/m・15 分"; :>> ruleText = ".B.4.b. above have been between -100 V/m and +500 V/m for 15 minutes. Note: Cumulus clouds in section 1.4.B. do not include altocumulus, cirrocumulus or stratocumulus. Definitions: Cloud Top, Electric"; :>> sourcePage = 87; }
        part <'LWR-026'> lwr_026 : WeatherRule { doc /* WEA-01 1.4.C.1.a */ :>> clause = "1.4.C.1.a"; :>> limitValues = "10 NM・30 分"; :>> ruleText = "Do not launch if the flight path will carry the SSV through or within 10 NM of a nontransparent part of any attached anvil cloud for the first 30 minutes after the last lightning discharge in or from "; :>> sourcePage = 87; }
        part <'LWR-027'> lwr_027 : WeatherRule { doc /* WEA-01 1.4.C.1.b */ :>> clause = "1.4.C.1.b"; :>> limitValues = "5 NM・30 分"; :>> ruleText = "Do not launch if the flight path will carry the SSV through or within 5 NM of a nontransparent part of any attached anvil cloud between 30 minutes and three hours after the last lightning discharge in"; :>> sourcePage = 87; }
        part <'LWR-028'> lwr_028 : WeatherRule { doc /* WEA-01 1.4.C.1.b)1 */ :>> clause = "1.4.C.1.b)1"; :>> limitValues = "5 NM・0 °C"; :>> ruleText = "The portion of the attached anvil cloud within 5 NM of the flight path is located entirely at altitudes where the temperature is colder than 0 degrees C; -and-"; :>> sourcePage = 87; }
        part <'LWR-029'> lwr_029 : WeatherRule { doc /* WEA-01 1.4.C.1.b)2 */ :>> clause = "1.4.C.1.b)2"; :>> limitValues = "10 dBZ"; :>> ruleText = "The VAHIRR is less than +33 Range Corrected Reflectivity (dBZ)-thousand feet(kft) (+10 dBZ-kilometers (km)) everywhere along the portion of the flight path where any part of the attached anvil cloud i"; :>> sourcePage = 87; }
        part <'LWR-030'> lwr_030 : WeatherRule { doc /* WEA-01 1.4.C.1.c */ :>> clause = "1.4.C.1.c"; :>> limitValues = "3 時間"; :>> ruleText = "Do not launch if the flight path will carry the SSV through a nontransparent part of any attached anvil cloud more than 3 hours after the last lightning discharge in or from the parent cloud or anvil "; :>> sourcePage = 87; }
        part <'LWR-031'> lwr_031 : WeatherRule { doc /* WEA-01 1.4.C.1.c)1 */ :>> clause = "1.4.C.1.c)1"; :>> limitValues = "5 NM・0 °C"; :>> ruleText = "The portion of the attached anvil cloud within 5 NM miles of the flight path is located entirely at altitudes where the temperature is colder than 0 degrees C; -and-"; :>> sourcePage = 87; }
        part <'LWR-032'> lwr_032 : WeatherRule { doc /* WEA-01 1.4.C.1.c)2 */ :>> clause = "1.4.C.1.c)2"; :>> limitValues = "33 dBZ-kft・10 dBZ-km"; :>> ruleText = "The VAHIRR is less than +33 dBZ-kft (+10 dBZ-km) everywhere along the portion of the flight path where any part of the attached anvil cloud is within the specified volume."; :>> sourcePage = 87; }
        part <'LWR-033'> lwr_033 : WeatherRule { doc /* WEA-01 1.4.C.2.a */ :>> clause = "1.4.C.2.a"; :>> limitValues = "10 NM・30 分"; :>> ruleText = "Do not launch if the flight path will carry the SSV through or within 10 NM of a nontransparent part of a detached anvil cloud for the first 30 minutes after the last lightning discharge in or from th"; :>> sourcePage = 88; }
        part <'LWR-034'> lwr_034 : WeatherRule { doc /* WEA-01 1.4.C.2.b */ :>> clause = "1.4.C.2.b"; :>> limitValues = "5 NM・30 分・3 時間"; :>> ruleText = "Do not launch if the flight path will carry the SSV between 0 (zero) and 5 NM from a nontransparent part of a detached anvil cloud between 30 minutes and 3 hours after the time of the last lightning d"; :>> sourcePage = 88; }
        part <'LWR-035'> lwr_035 : WeatherRule { doc /* WEA-01 1.4.C.2.b)1)a */ :>> clause = "1.4.C.2.b)1)a"; :>> limitValues = "5 NM"; :>> ruleText = "There is at least one working field mill within 5 NM of the detached anvil cloud; -and-"; :>> sourcePage = 88; }
        part <'LWR-036'> lwr_036 : WeatherRule { doc /* WEA-01 1.4.C.2.b)1)b */ :>> clause = "1.4.C.2.b)1)b"; :>> limitValues = "5 NM"; :>> ruleText = "The absolute values of all electric field measurements at the surface within 5 NM of the flight path and at each field mill specified in subparagraph"; :>> sourcePage = 88; }
        part <'LWR-037'> lwr_037 : WeatherRule { doc /* WEA-01 1.4 */ :>> clause = "1.4"; :>> limitValues = "1000 V/m・15 分"; :>> ruleText = ".C.2.b.1)a) have been less than 1000 V/m for 15 minutes; -and-"; :>> sourcePage = 88; }
        part <'LWR-038'> lwr_038 : WeatherRule { doc /* WEA-01 1.4)c */ :>> clause = "1.4)c"; :>> limitValues = "5 NM・10 dBZ・15 分"; :>> ruleText = "The maximum radar return from any part of the detached anvil cloud within 5 NM of the flight path has been less than 10 dBZ for 15 minutes."; :>> sourcePage = 88; }
        part <'LWR-039'> lwr_039 : WeatherRule { doc /* WEA-01 1.4)2)a */ :>> clause = "1.4)2)a"; :>> limitValues = "5 NM・0 °C"; :>> ruleText = "The portion of the detached anvil cloud within 5 NM of the flight path is located entirely at altitudes where the temperature is colder than 0 degrees C; -and-"; :>> sourcePage = 88; }
        part <'LWR-040'> lwr_040 : WeatherRule { doc /* WEA-01 1.4)2)b */ :>> clause = "1.4)2)b"; :>> limitValues = "33 dBZ-kft・10 dBZ-km"; :>> ruleText = "The VAHIRR is less than +33 dBZ-kft (+10 dBZ-km) everywhere along the portion of the flight path where any part of the detached anvil cloud is within the specified volume."; :>> sourcePage = 88; }
        part <'LWR-041'> lwr_041 : WeatherRule { doc /* WEA-01 1.4.c)1)a */ :>> clause = "1.4.c)1)a"; :>> limitValues = "4 時間"; :>> ruleText = "At least 4 hours have passed since the last lightning discharge in or from the detached anvil cloud; -and-"; :>> sourcePage = 89; }
        part <'LWR-042'> lwr_042 : WeatherRule { doc /* WEA-01 1.4.c)1)b */ :>> clause = "1.4.c)1)b"; :>> limitValues = "3 時間"; :>> ruleText = "At least 3 hours have passed since the time that the anvil cloud is observed to be detached from the parent cloud."; :>> sourcePage = 89; }
        part <'LWR-043'> lwr_043 : WeatherRule { doc /* WEA-01 1.4.c)2)a */ :>> clause = "1.4.c)2)a"; :>> limitValues = "5 NM・0 °C"; :>> ruleText = "The portion of the detached anvil cloud within 5 nautical miles of the flight path is located entirely at altitudes where the temperature is colder than 0 degrees C; -and-"; :>> sourcePage = 89; }
        part <'LWR-044'> lwr_044 : WeatherRule { doc /* WEA-01 1.4.c)2)b */ :>> clause = "1.4.c)2)b"; :>> limitValues = "33 dBZ-kft・10 dBZ-km"; :>> ruleText = "The Volume-Averaged, Height-Integrated Radar Reflectivity (VAHIRR) is less than +33 dBZ-kft (+10 dBZ-km) everywhere along the portion of the flight path where any part of the detached anvil cloud is w"; :>> sourcePage = 89; }
        part <'LWR-045'> lwr_045 : WeatherRule { doc /* WEA-01 1.4.D.1 */ :>> clause = "1.4.D.1"; :>> limitValues = "3 時間"; :>> ruleText = "Do not launch if the flight path will carry the SSV through any nontransparent parts of a debris cloud during the 3 hour period defined below."; :>> sourcePage = 89; }
        part <'LWR-046'> lwr_046 : WeatherRule { doc /* WEA-01 1.4.D.2 */ :>> clause = "1.4.D.2"; :>> limitValues = "5 NM・3 時間"; :>> ruleText = "Do not launch if the flight path will carry the vehicle within 5 NM of any nontransparent parts of a debris cloud during the 3 hour period defined below, unless:"; :>> sourcePage = 89; }
        part <'LWR-047'> lwr_047 : WeatherRule { doc /* WEA-01 1.4.D.2.a */ :>> clause = "1.4.D.2.a"; :>> limitValues = "5 NM"; :>> ruleText = "There is at least one working field mill within 5 NM of the debris cloud; -and-"; :>> sourcePage = 89; }
        part <'LWR-048'> lwr_048 : WeatherRule { doc /* WEA-01 1.4.D.2.b */ :>> clause = "1.4.D.2.b"; :>> limitValues = "5 NM・1000 V/m・15 分"; :>> ruleText = "The absolute values of all electric field measurements at the surface within 5 NM of the flight path and at the mill(s) specified in section 1.4.D.2.a. have been less than 1000 V/m for 15 minutes; -an"; :>> sourcePage = 90; }
        part <'LWR-049'> lwr_049 : WeatherRule { doc /* WEA-01 1.4.D.2.c */ :>> clause = "1.4.D.2.c"; :>> limitValues = "5 NM・10 dBZ・15 分・3 時間・-10 °C"; :>> ruleText = "The maximum radar return from any part of the debris cloud within 5 NM of the flight path has been less than 10 dBZ for 15 minutes. The 3 hour period in subparagraphs 1.4.D.2.a. and 1.4.D.2.b. begins "; :>> sourcePage = 90; }
        part <'LWR-050'> lwr_050 : WeatherRule { doc /* WEA-01 1.4.E */ :>> clause = "1.4.E"; :>> limitValues = "0 °C・5 NM"; :>> ruleText = "Disturbed Weather Do not launch if the flight path will carry the vehicle through any nontransparent clouds that are associated with a weather disturbance having clouds that extend to altitudes at or "; :>> sourcePage = 90; }
        part <'LWR-051'> lwr_051 : WeatherRule { doc /* WEA-01 1.4.F.1 */ :>> clause = "1.4.F.1"; :>> limitValues = "4500 ft・0 °C・-20 °C"; :>> ruleText = "Greater than 4,500 foot thick and any part of the cloud layer along flight path is located between the 0 degrees C and the -20 degrees C levels; -or-"; :>> sourcePage = 90; }
        part <'LWR-052'> lwr_052 : WeatherRule { doc /* WEA-01 1.4.F.2 */ :>> clause = "1.4.F.2"; :>> limitValues = "5 NM・4500 ft・0 °C・-20 °C・-15 °C"; :>> ruleText = "Connected to a cloud layer that, within 5 NM of the flight path, is greater than 4,500 foot thick and has any part located between the 0 degrees C and the -20 degrees C levels; unless the cloud layer "; :>> sourcePage = 90; }
        part <'LWR-053'> lwr_053 : WeatherRule { doc /* WEA-01 1.4.G */ :>> clause = "1.4.G"; :>> limitValues = "60 分"; :>> ruleText = "Smoke Plumes Do not launch if the flight path will carry the SSV through any cumulus cloud that has developed from a smoke plume while the cloud is attached to the smoke plume, or for the first 60 min"; :>> sourcePage = 91; }
        part <'LWR-054'> lwr_054 : WeatherRule { doc /* WEA-01 1.4.H.1 */ :>> clause = "1.4.H.1"; :>> limitValues = "15 分・5 NM・1500 V/m"; :>> ruleText = "Do not launch for 15 minutes after the absolute value of any electric field measurement at the surface within 5 NM of the flight path has been greater than 1500 V/m."; :>> sourcePage = 91; }
        part <'LWR-055'> lwr_055 : WeatherRule { doc /* WEA-01 1.4.H.2 */ :>> clause = "1.4.H.2"; :>> limitValues = "15 分・5 NM・1000 V/m"; :>> ruleText = "Do not launch for 15 minutes after the absolute value of any electric field measurement at the surface within 5 NM of the flight path has been greater than 1000 V/m unless:"; :>> sourcePage = 91; }
        part <'LWR-056'> lwr_056 : WeatherRule { doc /* WEA-01 1.4.H.2.a */ :>> clause = "1.4.H.2.a"; :>> limitValues = "10 NM"; :>> ruleText = "All clouds within 10 NM of the flight path are transparent; -or-"; :>> sourcePage = 91; }
        part <'LWR-057'> lwr_057 : WeatherRule { doc /* WEA-01 1.4.H.2.b */ :>> clause = "1.4.H.2.b"; :>> limitValues = "10 NM・5 °C・-10 °C・3 時間"; :>> ruleText = "All nontransparent clouds within 10 NM of the flight path have cloud tops below the +5 degrees C level and have not been part of convective clouds with cloud tops above the -10 degrees C level within "; :>> sourcePage = 91; }
    }
    part def LccJoin {
        doc /* Mission Report の LCC 違反の記録（SSD-LCC-ORB-001）1件と LCC 本体の SSID の結び。結べた 25件だけ（結び直しはしない）。測定値は持たない。effectivity は MISSION 欄の字面との照合 */
        attribute ddRecord : String;
        attribute flight : String;
        attribute ssid : String;
        attribute joinKey : String;
        attribute missionText : String;
        attribute effectivity : String;
        attribute limitNumberCheck : String;
    }
    part lccJoins {
        part join_lcc_002 : LccJoin { doc /* LCC-002 → ECL-04 */ :>> ddRecord = "LCC-002"; :>> flight = "STS-1"; :>> ssid = "ECL-04"; :>> joinKey = "K2"; :>> missionText = "119,120,122-999"; :>> effectivity = "Rev H 適用外"; :>> limitNumberCheck = "—"; }
        part join_lcc_010 : LccJoin { doc /* LCC-010 → HYD-05 */ :>> ddRecord = "LCC-010"; :>> flight = "STS-27"; :>> ssid = "HYD-05"; :>> joinKey = "K2"; :>> missionText = "STS-107,112-999"; :>> effectivity = "Rev H 適用外"; :>> limitNumberCheck = "—"; }
        part join_lcc_011 : LccJoin { doc /* LCC-011 → ET-01 */ :>> ddRecord = "LCC-011"; :>> flight = "STS-27"; :>> ssid = "ET-01"; :>> joinKey = "K2"; :>> missionText = "STS-104,105,107-999"; :>> effectivity = "Rev H 適用外"; :>> limitNumberCheck = "—"; }
        part join_lcc_018 : LccJoin { doc /* LCC-018 → APU-06 */ :>> ddRecord = "LCC-018"; :>> flight = "STS-31"; :>> ssid = "APU-06"; :>> joinKey = "K2"; :>> missionText = "STS-107,114-999"; :>> effectivity = "Rev H 適用外"; :>> limitNumberCheck = "—"; }
        part join_lcc_019 : LccJoin { doc /* LCC-019 → MPS-48 */ :>> ddRecord = "LCC-019"; :>> flight = "STS-31"; :>> ssid = "MPS-48"; :>> joinKey = "K2"; :>> missionText = "STS-116-120,122-999"; :>> effectivity = "Rev H 適用外"; :>> limitNumberCheck = "—"; }
        part join_lcc_022 : LccJoin { doc /* LCC-022 → APU-14 */ :>> ddRecord = "LCC-022"; :>> flight = "STS-33"; :>> ssid = "APU-14"; :>> joinKey = "K2"; :>> missionText = "STS-107,114-999"; :>> effectivity = "Rev H 適用外"; :>> limitNumberCheck = "—"; }
        part join_lcc_028 : LccJoin { doc /* LCC-028 → MPS-25 */ :>> ddRecord = "LCC-028"; :>> flight = "STS-36"; :>> ssid = "MPS-25"; :>> joinKey = "K2"; :>> missionText = "STS-114-999"; :>> effectivity = "Rev H 適用外"; :>> limitNumberCheck = "—"; }
        part join_lcc_044 : LccJoin { doc /* LCC-044 → HAZ-03 */ :>> ddRecord = "LCC-044"; :>> flight = "STS-47"; :>> ssid = "HAZ-03"; :>> joinKey = "K2"; :>> missionText = "STS-107,109-999"; :>> effectivity = "Rev H 適用外"; :>> limitNumberCheck = "—"; }
        part join_lcc_055 : LccJoin { doc /* LCC-055 → MPS-12 */ :>> ddRecord = "LCC-055"; :>> flight = "STS-56"; :>> ssid = "MPS-12"; :>> joinKey = "K2"; :>> missionText = "STS-98,100,102,104,105,107-999"; :>> effectivity = "Rev H 適用外"; :>> limitNumberCheck = "—"; }
        part join_lcc_060 : LccJoin { doc /* LCC-060 → HAZ-07 */ :>> ddRecord = "LCC-060"; :>> flight = "STS-58"; :>> ssid = "HAZ-07"; :>> joinKey = "K2"; :>> missionText = "STS 115-999"; :>> effectivity = "Rev H 適用外"; :>> limitNumberCheck = "—"; }
        part join_lcc_065 : LccJoin { doc /* LCC-065 → FCP-01 */ :>> ddRecord = "LCC-065"; :>> flight = "STS-67"; :>> ssid = "FCP-01"; :>> joinKey = "K2"; :>> missionText = "STS-114-999"; :>> effectivity = "Rev H 適用外"; :>> limitNumberCheck = "—"; }
        part join_lcc_068 : LccJoin { doc /* LCC-068 → SSME-25 */ :>> ddRecord = "LCC-068"; :>> flight = "STS-68"; :>> ssid = "SSME-25"; :>> joinKey = "K2"; :>> missionText = "STS-104,105,107-999"; :>> effectivity = "Rev H 適用外"; :>> limitNumberCheck = "—"; }
        part join_lcc_069 : LccJoin { doc /* LCC-069 → BRSS-15 */ :>> ddRecord = "LCC-069"; :>> flight = "STS-70"; :>> ssid = "BRSS-15"; :>> joinKey = "K2"; :>> missionText = "STS-119,120,122-999"; :>> effectivity = "Rev H 適用外"; :>> limitNumberCheck = "—"; }
        part join_lcc_072 : LccJoin { doc /* LCC-072 → HAZ-03 */ :>> ddRecord = "LCC-072"; :>> flight = "STS-80"; :>> ssid = "HAZ-03"; :>> joinKey = "K2"; :>> missionText = "STS-107,109-999"; :>> effectivity = "Rev H 適用外"; :>> limitNumberCheck = "—"; }
        part join_lcc_087 : LccJoin { doc /* LCC-087 → MPS-22 */ :>> ddRecord = "LCC-087"; :>> flight = "STS-114"; :>> ssid = "MPS-22"; :>> joinKey = "K1"; :>> missionText = "STS 116-120,122-999"; :>> effectivity = "Rev H 適用外"; :>> limitNumberCheck = "—"; }
        part join_lcc_088 : LccJoin { doc /* LCC-088 → MPS-22 */ :>> ddRecord = "LCC-088"; :>> flight = "STS-115"; :>> ssid = "MPS-22"; :>> joinKey = "K1"; :>> missionText = "STS 116-120,122-999"; :>> effectivity = "Rev H 適用外"; :>> limitNumberCheck = "—"; }
        part join_lcc_092 : LccJoin { doc /* LCC-092 → ICE-01 */ :>> ddRecord = "LCC-092"; :>> flight = "STS-118"; :>> ssid = "ICE-01"; :>> joinKey = "K1"; :>> missionText = "STS-114-999"; :>> effectivity = "範囲内"; :>> limitNumberCheck = "数が無い"; }
        part join_lcc_095 : LccJoin { doc /* LCC-095 → ICE-01 */ :>> ddRecord = "LCC-095"; :>> flight = "STS-119"; :>> ssid = "ICE-01"; :>> joinKey = "K1"; :>> missionText = "STS-114-999"; :>> effectivity = "範囲内"; :>> limitNumberCheck = "数が無い"; }
        part join_lcc_096 : LccJoin { doc /* LCC-096 → ICE-01 */ :>> ddRecord = "LCC-096"; :>> flight = "STS-120"; :>> ssid = "ICE-01"; :>> joinKey = "K1"; :>> missionText = "STS-114-999"; :>> effectivity = "範囲内"; :>> limitNumberCheck = "数が無い"; }
        part join_lcc_102 : LccJoin { doc /* LCC-102 → ICE-01 */ :>> ddRecord = "LCC-102"; :>> flight = "STS-128"; :>> ssid = "ICE-01"; :>> joinKey = "K1"; :>> missionText = "STS-114-999"; :>> effectivity = "範囲内"; :>> limitNumberCheck = "数が無い"; }
        part join_lcc_103 : LccJoin { doc /* LCC-103 → MPS-04 */ :>> ddRecord = "LCC-103"; :>> flight = "STS-128"; :>> ssid = "MPS-04"; :>> joinKey = "K1"; :>> missionText = "STS-115-999"; :>> effectivity = "範囲内"; :>> limitNumberCheck = "数が無い"; }
        part join_lcc_104 : LccJoin { doc /* LCC-104 → ICE-01 */ :>> ddRecord = "LCC-104"; :>> flight = "STS-128"; :>> ssid = "ICE-01"; :>> joinKey = "K1"; :>> missionText = "STS-114-999"; :>> effectivity = "範囲内"; :>> limitNumberCheck = "数が無い"; }
        part join_lcc_107 : LccJoin { doc /* LCC-107 → ICE-01 */ :>> ddRecord = "LCC-107"; :>> flight = "STS-132"; :>> ssid = "ICE-01"; :>> joinKey = "K1"; :>> missionText = "STS-114-999"; :>> effectivity = "範囲内"; :>> limitNumberCheck = "数が無い"; }
        part join_lcc_110 : LccJoin { doc /* LCC-110 → APU-14 */ :>> ddRecord = "LCC-110"; :>> flight = "STS-134"; :>> ssid = "APU-14"; :>> joinKey = "K1"; :>> missionText = "STS-107,114-999"; :>> effectivity = "範囲内"; :>> limitNumberCheck = "現れる"; }
        part join_lcc_111 : LccJoin { doc /* LCC-111 → ICE-01 */ :>> ddRecord = "LCC-111"; :>> flight = "STS-134"; :>> ssid = "ICE-01"; :>> joinKey = "K1"; :>> missionText = "STS-114-999"; :>> effectivity = "範囲内"; :>> limitNumberCheck = "数が無い"; }
    }
}
