// SysML v2 テキスト：飛行中異常記録定義書（Mission Report の番号つき異常と、系・故障モード・機能ブロック・処置のつなぎ）
// SSD-IFA-ORB-001 飛行中異常記録定義書（Mission Report の番号つき異常と、系・故障モード・機能ブロック・処置のつなぎ） の表から生成（lib/build_docs_co.py・rev_co/codata.py）。根拠の頁は SSD-IFA-ORB-001 にある。
package SSD_IFA_ORB_001 {
    doc /* SSD-IFA-ORB-001 飛行中異常記録定義書（Mission Report の番号つき異常と、系・故障モード・機能ブロック・処置のつなぎ）。飛行中異常を occurrence def InFlightAnomaly の使用として持ち、観測された故障モードへ #ObservedAs の dependency でつなぐ。系・機能行・処置・要求・出典は文書の表に置き、要求への関係（導出・充足・検証）は張らず、トレースの外に置く。 */
    private import ScalarValues::*;
    metadata def ObservedAs { doc /* 異常が観測された故障モード（故障解析表の行・機能の故障モード。本書の対応づけ） */ }
    occurrence def InFlightAnomaly {
        doc /* Mission Report の番号つきの飛行中異常（種別 V＝オービタ） */
        attribute reportNumber : String;
        attribute flight : String;
        attribute subsystem : String;
        attribute causeState : String;
        attribute actionClass : String;
        attribute phase : String;
    }
    package Anomalies {
        doc /* 異常の使用（飛行・系・原因の状態・処置の区分） */
        occurrence <'IFA-001'> ifa_001 : InFlightAnomaly { doc /* STS-47-V-01 水素の高速充填中に後部コンパートメントの水素濃度が打上げ判断基準を超過 */ attribute :>> reportNumber = "STS-47-V-01"; attribute :>> flight = "STS-47"; attribute :>> subsystem = "MPS"; attribute :>> causeState = "推定"; attribute :>> actionClass = "許容・そのまま飛行"; attribute :>> phase = "PH-1"; }
        occurrence <'IFA-002'> ifa_002 : InFlightAnomaly { doc /* STS-47-V-02 打上げ前に APU 3 の燃料テストライン温度が LCC の下限を下回る */ attribute :>> reportNumber = "STS-47-V-02"; attribute :>> flight = "STS-47"; attribute :>> subsystem = "APU"; attribute :>> causeState = "記載なし"; attribute :>> actionClass = "許容・そのまま飛行"; attribute :>> phase = "PH-1"; }
        occurrence <'IFA-003'> ifa_003 : InFlightAnomaly { doc /* STS-47-V-03 ET 分離の機動中に RCS 主スラスタ L3A が作動せず */ attribute :>> reportNumber = "STS-47-V-03"; attribute :>> flight = "STS-47"; attribute :>> subsystem = "RCS"; attribute :>> causeState = "推定"; attribute :>> actionClass = "許容・そのまま飛行"; attribute :>> phase = "PH-2"; }
        occurrence <'IFA-004'> ifa_004 : InFlightAnomaly { doc /* STS-47-V-04 SSME 1 の LH2 入口圧の計測値が最低値側に振り切れ */ attribute :>> reportNumber = "STS-47-V-04"; attribute :>> flight = "STS-47"; attribute :>> subsystem = "MPS"; attribute :>> causeState = "記載なし"; attribute :>> actionClass = "記載なし"; attribute :>> phase = "PH-2"; }
        occurrence <'IFA-005'> ifa_005 : InFlightAnomaly { doc /* STS-47-V-05 上昇中に WSB 1 が APU 1 の潤滑油の冷却を遅らせる */ attribute :>> reportNumber = "STS-47-V-05"; attribute :>> flight = "STS-47"; attribute :>> subsystem = "APU"; attribute :>> causeState = "推定"; attribute :>> actionClass = "再点検・再試験"; attribute :>> phase = "PH-2"; }
        occurrence <'IFA-006'> ifa_006 : InFlightAnomaly { doc /* STS-47-V-06 PRSD の酸素タンク 4 のヒータ制御圧の指示が最低値側に振り切れ */ attribute :>> reportNumber = "STS-47-V-06"; attribute :>> flight = "STS-47"; attribute :>> subsystem = "EPS"; attribute :>> causeState = "推定"; attribute :>> actionClass = "再点検・再試験"; attribute :>> phase = "PH-2"; }
        occurrence <'IFA-007'> ifa_007 : InFlightAnomaly { doc /* STS-47-V-07 上昇中に WSB 3 が冷却せず APU 3 を早期に停止 */ attribute :>> reportNumber = "STS-47-V-07"; attribute :>> flight = "STS-47"; attribute :>> subsystem = "APU"; attribute :>> causeState = "推定"; attribute :>> actionClass = "記載なし"; attribute :>> phase = "PH-2"; }
        occurrence <'IFA-008'> ifa_008 : InFlightAnomaly { doc /* STS-47-V-08 燃料電池の水リリーフラインの温度が低下し不安定になる */ attribute :>> reportNumber = "STS-47-V-08"; attribute :>> flight = "STS-47"; attribute :>> subsystem = "ECLSS"; attribute :>> causeState = "推定"; attribute :>> actionClass = "手順・規則の変更"; attribute :>> phase = "PH-2"; }
        occurrence <'IFA-009'> ifa_009 : InFlightAnomaly { doc /* STS-47-V-09 バーニア・スラスタ L5D のチャンバ圧が低下 */ attribute :>> reportNumber = "STS-47-V-09"; attribute :>> flight = "STS-47"; attribute :>> subsystem = "RCS"; attribute :>> causeState = "推定"; attribute :>> actionClass = "再点検・再試験"; attribute :>> phase = "PH-3"; }
        occurrence <'IFA-010'> ifa_010 : InFlightAnomaly { doc /* STS-47-V-10 WSB 2 のレギュレータ出口圧センサが実際の低下に追従せず */ attribute :>> reportNumber = "STS-47-V-10"; attribute :>> flight = "STS-47"; attribute :>> subsystem = "APU"; attribute :>> causeState = "推定"; attribute :>> actionClass = "許容・そのまま飛行"; attribute :>> phase = "PH-2"; }
        occurrence <'IFA-011'> ifa_011 : InFlightAnomaly { doc /* STS-47-V-11 Ku 帯の距離変化率・方位の表示で十の位が消える */ attribute :>> reportNumber = "STS-47-V-11"; attribute :>> flight = "STS-47"; attribute :>> subsystem = "CT"; attribute :>> causeState = "記載なし"; attribute :>> actionClass = "再点検・再試験"; attribute :>> phase = "PH-3"; }
        occurrence <'IFA-012'> ifa_012 : InFlightAnomaly { doc /* STS-47-V-12 左外側主脚のタイヤ圧センサ 1・2 が新しい較正曲線に対して過大にバイアス */ attribute :>> reportNumber = "STS-47-V-12"; attribute :>> flight = "STS-47"; attribute :>> subsystem = "MECH"; attribute :>> causeState = "記載なし"; attribute :>> actionClass = "再点検・再試験"; attribute :>> phase = "PH-6"; }
        occurrence <'IFA-013'> ifa_013 : InFlightAnomaly { doc /* STS-47-V-13 上下スピードブレーキ分割線の熱バリアが外板から約 1 インチ浮く */ attribute :>> reportNumber = "STS-47-V-13"; attribute :>> flight = "STS-47"; attribute :>> subsystem = "TPS"; attribute :>> causeState = "記載なし"; attribute :>> actionClass = "許容・そのまま飛行"; attribute :>> phase = "PH-3"; }
        occurrence <'IFA-014'> ifa_014 : InFlightAnomaly { doc /* STS-47-V-14 燃料電池 2 の酸素流量計の指示が不安定 */ attribute :>> reportNumber = "STS-47-V-14"; attribute :>> flight = "STS-47"; attribute :>> subsystem = "EPS"; attribute :>> causeState = "記載なし"; attribute :>> actionClass = "記載なし"; attribute :>> phase = "PH-6"; }
        occurrence <'IFA-015'> ifa_015 : InFlightAnomaly { doc /* STS-47-V-15 客室湿度センサの読みが一定値で止まる */ attribute :>> reportNumber = "STS-47-V-15"; attribute :>> flight = "STS-47"; attribute :>> subsystem = "ECLSS"; attribute :>> causeState = "特定"; attribute :>> actionClass = "再点検・再試験"; attribute :>> phase = "PH-3"; }
        occurrence <'IFA-016'> ifa_016 : InFlightAnomaly { doc /* STS-47-V-16 APU 1 のドレンライン温度 2 が 47°F で張りつく */ attribute :>> reportNumber = "STS-47-V-16"; attribute :>> flight = "STS-47"; attribute :>> subsystem = "APU"; attribute :>> causeState = "記載なし"; attribute :>> actionClass = "手順・規則の変更"; attribute :>> phase = "PH-2"; }
        occurrence <'IFA-017'> ifa_017 : InFlightAnomaly { doc /* STS-47-V-17 スタートラッカが電源投入後すぐに 2 回続けて自己試験に不合格 */ attribute :>> reportNumber = "STS-47-V-17"; attribute :>> flight = "STS-47"; attribute :>> subsystem = "GNC"; attribute :>> causeState = "調査中"; attribute :>> actionClass = "再点検・再試験"; attribute :>> phase = "PH-3"; }
        occurrence <'IFA-018'> ifa_018 : InFlightAnomaly { doc /* STS-47-V-18 CCTV カメラ D の映像に水平方向のジッタ */ attribute :>> reportNumber = "STS-47-V-18"; attribute :>> flight = "STS-47"; attribute :>> subsystem = "CT"; attribute :>> causeState = "記載なし"; attribute :>> actionClass = "許容・そのまま飛行"; attribute :>> phase = "PH-3"; }
        occurrence <'IFA-019'> ifa_019 : InFlightAnomaly { doc /* STS-47-V-19 再突入中に TACAN の方位指示が約 13 秒間 40 度ずれる */ attribute :>> reportNumber = "STS-47-V-19"; attribute :>> flight = "STS-47"; attribute :>> subsystem = "GNC"; attribute :>> causeState = "調査中"; attribute :>> actionClass = "再点検・再試験"; attribute :>> phase = "PH-6"; }
        occurrence <'IFA-020'> ifa_020 : InFlightAnomaly { doc /* STS-47-V-20 WSB 1 のレギュレータ出口圧が飛行中に上昇し続ける */ attribute :>> reportNumber = "STS-47-V-20"; attribute :>> flight = "STS-47"; attribute :>> subsystem = "APU"; attribute :>> causeState = "推定"; attribute :>> actionClass = "記載なし"; attribute :>> phase = "PH-3"; }
        occurrence <'IFA-021'> ifa_021 : InFlightAnomaly { doc /* STS-47-V-21 FES の起動時に出口温度が振動する */ attribute :>> reportNumber = "STS-47-V-21"; attribute :>> flight = "STS-47"; attribute :>> subsystem = "ECLSS"; attribute :>> causeState = "調査中"; attribute :>> actionClass = "記載なし"; attribute :>> phase = "PH-3"; }
        occurrence <'IFA-022'> ifa_022 : InFlightAnomaly { doc /* STS-47-V-22 ドラッグシュートの展開後、着陸滑走中に左へ逸れる */ attribute :>> reportNumber = "STS-47-V-22"; attribute :>> flight = "STS-47"; attribute :>> subsystem = "MECH"; attribute :>> causeState = "記載なし"; attribute :>> actionClass = "記載なし"; attribute :>> phase = "PH-6"; }
        occurrence <'IFA-023'> ifa_023 : InFlightAnomaly { doc /* STS-47-V-23 空地 1 と空地 2 の通信リンクにクロストーク */ attribute :>> reportNumber = "STS-47-V-23"; attribute :>> flight = "STS-47"; attribute :>> subsystem = "CT"; attribute :>> causeState = "記載なし"; attribute :>> actionClass = "記載なし"; attribute :>> phase = "PH-3"; }
        occurrence <'IFA-024'> ifa_024 : InFlightAnomaly { doc /* STS-47-V-24 ギャレーの package in-place マイクロスイッチの動きが粘る */ attribute :>> reportNumber = "STS-47-V-24"; attribute :>> flight = "STS-47"; attribute :>> subsystem = "OTHER"; attribute :>> causeState = "特定"; attribute :>> actionClass = "再点検・再試験"; attribute :>> phase = "PH-3"; }
        occurrence <'IFA-025'> ifa_025 : InFlightAnomaly { doc /* STS-47-V-25 打上げ前に MS3 の LES の酸素ホースがスーツから外れる */ attribute :>> reportNumber = "STS-47-V-25"; attribute :>> flight = "STS-47"; attribute :>> subsystem = "OTHER"; attribute :>> causeState = "記載なし"; attribute :>> actionClass = "許容・そのまま飛行"; attribute :>> phase = "PH-1"; }
        occurrence <'IFA-026'> ifa_026 : InFlightAnomaly { doc /* STS-47-V-26 RCC チンパネルと機首キャップの角シールのギャップフィラの間に大きな隙間 */ attribute :>> reportNumber = "STS-47-V-26"; attribute :>> flight = "STS-47"; attribute :>> subsystem = "TPS"; attribute :>> causeState = "記載なし"; attribute :>> actionClass = "設計変更"; attribute :>> phase = "PH-7"; }
        occurrence <'IFA-027'> ifa_027 : InFlightAnomaly { doc /* STS-54-V-01 WSB 3 が冷却を始めない */ attribute :>> reportNumber = "STS-54-V-01"; attribute :>> flight = "STS-54"; attribute :>> subsystem = "APU"; attribute :>> causeState = "推定"; attribute :>> actionClass = "手順・規則の変更"; attribute :>> phase = "PH-2"; }
        occurrence <'IFA-028'> ifa_028 : InFlightAnomaly { doc /* STS-54-V-02 CCTV カメラ A〜D の不具合（4件） */ attribute :>> reportNumber = "STS-54-V-02"; attribute :>> flight = "STS-54"; attribute :>> subsystem = "CT"; attribute :>> causeState = "推定"; attribute :>> actionClass = "再点検・再試験"; attribute :>> phase = "PH-5"; }
        occurrence <'IFA-029'> ifa_029 : InFlightAnomaly { doc /* STS-54-V-03 EDO の WCS の便器故障灯が点灯 */ attribute :>> reportNumber = "STS-54-V-03"; attribute :>> flight = "STS-54"; attribute :>> subsystem = "ECLSS"; attribute :>> causeState = "推定"; attribute :>> actionClass = "部品交換"; attribute :>> phase = "PH-3"; }
        occurrence <'IFA-030'> ifa_030 : InFlightAnomaly { doc /* STS-54-V-04 ラダー・スピードブレーキ切替弁の表示が油圧系3を示さない */ attribute :>> reportNumber = "STS-54-V-04"; attribute :>> flight = "STS-54"; attribute :>> subsystem = "APU"; attribute :>> causeState = "推定"; attribute :>> actionClass = "再点検・再試験"; attribute :>> phase = "PH-3"; }
        occurrence <'IFA-031'> ifa_031 : InFlightAnomaly { doc /* STS-54-V-05 RCS スラスタ R1R が作動せず */ attribute :>> reportNumber = "STS-54-V-05"; attribute :>> flight = "STS-54"; attribute :>> subsystem = "RCS"; attribute :>> causeState = "推定"; attribute :>> actionClass = "部品交換"; attribute :>> phase = "PH-3"; }
        occurrence <'IFA-032'> ifa_032 : InFlightAnomaly { doc /* STS-54-V-06 窒素漏れ率が低く、湿ったごみから臭気 */ attribute :>> reportNumber = "STS-54-V-06"; attribute :>> flight = "STS-54"; attribute :>> subsystem = "ECLSS"; attribute :>> causeState = "特定"; attribute :>> actionClass = "手順・規則の変更"; attribute :>> phase = "PH-3"; }
        occurrence <'IFA-033'> ifa_033 : InFlightAnomaly { doc /* STS-54-V-07 燃料電池2・3の代替水ラインの温度上昇 */ attribute :>> reportNumber = "STS-54-V-07"; attribute :>> flight = "STS-54"; attribute :>> subsystem = "EPS"; attribute :>> causeState = "記載なし"; attribute :>> actionClass = "再点検・再試験"; attribute :>> phase = "PH-3"; }
        occurrence <'IFA-034'> ifa_034 : InFlightAnomaly { doc /* STS-54-V-08 油圧系3の圧力が APU 停止後も下がらず */ attribute :>> reportNumber = "STS-54-V-08"; attribute :>> flight = "STS-54"; attribute :>> subsystem = "APU"; attribute :>> causeState = "不明"; attribute :>> actionClass = "再点検・再試験"; attribute :>> phase = "PH-2"; }
        occurrence <'IFA-035'> ifa_035 : InFlightAnomaly { doc /* STS-54-V-09 ペイロードベイ投光灯の不点 */ attribute :>> reportNumber = "STS-54-V-09"; attribute :>> flight = "STS-54"; attribute :>> subsystem = "CREW"; attribute :>> causeState = "記載なし"; attribute :>> actionClass = "部品交換"; attribute :>> phase = "PH-3"; }
        occurrence <'IFA-036'> ifa_036 : InFlightAnomaly { doc /* STS-54-V-10 APU 3 の軸受温度が不規則 */ attribute :>> reportNumber = "STS-54-V-10"; attribute :>> flight = "STS-54"; attribute :>> subsystem = "APU"; attribute :>> causeState = "不明"; attribute :>> actionClass = "再点検・再試験"; attribute :>> phase = "PH-6"; }
        occurrence <'IFA-037'> ifa_037 : InFlightAnomaly { doc /* STS-54-V-11 EMU 電源・電池充電器の騒音 */ attribute :>> reportNumber = "STS-54-V-11"; attribute :>> flight = "STS-54"; attribute :>> subsystem = "EVA"; attribute :>> causeState = "記載なし"; attribute :>> actionClass = "次便で対処"; attribute :>> phase = "PH-7"; }
        occurrence <'IFA-038'> ifa_038 : InFlightAnomaly { doc /* STS-100-V-01 FES の右舷フィードライン・ゾーン3のヒータ（系統1）の故障 */ attribute :>> reportNumber = "STS-100-V-01"; attribute :>> flight = "STS-100"; attribute :>> subsystem = "ECLSS"; attribute :>> causeState = "特定"; attribute :>> actionClass = "許容・そのまま飛行"; attribute :>> phase = "PH-3"; }
        occurrence <'IFA-039'> ifa_039 : InFlightAnomaly { doc /* STS-100-V-02 SSME 1B の 750 psia 調圧器の出口圧の低下 */ attribute :>> reportNumber = "STS-100-V-02"; attribute :>> flight = "STS-100"; attribute :>> subsystem = "MPS"; attribute :>> causeState = "特定"; attribute :>> actionClass = "部品交換"; attribute :>> phase = "PH-2"; }
        occurrence <'IFA-040'> ifa_040 : InFlightAnomaly { doc /* STS-100-V-03 WSB 3 のコア・水タンク・GN2 タンクの温度の急上昇（制御器 B） */ attribute :>> reportNumber = "STS-100-V-03"; attribute :>> flight = "STS-100"; attribute :>> subsystem = "APU"; attribute :>> causeState = "推定"; attribute :>> actionClass = "部品交換"; attribute :>> phase = "PH-3"; }
        occurrence <'IFA-041'> ifa_041 : InFlightAnomaly { doc /* STS-100-V-04 バーニア R5D の燃焼室圧（Pc）が低い */ attribute :>> reportNumber = "STS-100-V-04"; attribute :>> flight = "STS-100"; attribute :>> subsystem = "RCS"; attribute :>> causeState = "推定"; attribute :>> actionClass = "許容・そのまま飛行"; attribute :>> phase = "PH-4"; }
        occurrence <'IFA-042'> ifa_042 : InFlightAnomaly { doc /* STS-101-V-01 左 OMS エンジンの二液弁 2 が「開」のまま表示 */ attribute :>> reportNumber = "STS-101-V-01"; attribute :>> flight = "STS-101"; attribute :>> subsystem = "OMS"; attribute :>> causeState = "記載なし"; attribute :>> actionClass = "許容・そのまま飛行"; attribute :>> phase = "PH-3"; }
        occurrence <'IFA-043'> ifa_043 : InFlightAnomaly { doc /* STS-101-V-02 左 OMS エンジンの GN2 調圧器の圧力が FDA 限界を下回る */ attribute :>> reportNumber = "STS-101-V-02"; attribute :>> flight = "STS-101"; attribute :>> subsystem = "OMS"; attribute :>> causeState = "記載なし"; attribute :>> actionClass = "部品交換"; attribute :>> phase = "PH-2"; }
        occurrence <'IFA-044'> ifa_044 : InFlightAnomaly { doc /* STS-101-V-03 Ku 帯 TWT 送信機が RF 保護箱へ放射 */ attribute :>> reportNumber = "STS-101-V-03"; attribute :>> flight = "STS-101"; attribute :>> subsystem = "CT"; attribute :>> causeState = "調査中"; attribute :>> actionClass = "手順・規則の変更"; attribute :>> phase = "PH-3"; }
        occurrence <'IFA-045'> ifa_045 : InFlightAnomaly { doc /* STS-101-V-04 O2 タンク 4 のヒータ A が自動モードで作動しない */ attribute :>> reportNumber = "STS-101-V-04"; attribute :>> flight = "STS-101"; attribute :>> subsystem = "EPS"; attribute :>> causeState = "調査中"; attribute :>> actionClass = "再点検・再試験"; attribute :>> phase = "PH-3"; }
        occurrence <'IFA-046'> ifa_046 : InFlightAnomaly { doc /* STS-101-V-05 TACAN 3 が着陸中に BITE の故障を 2 回出す */ attribute :>> reportNumber = "STS-101-V-05"; attribute :>> flight = "STS-101"; attribute :>> subsystem = "GNC"; attribute :>> causeState = "調査中"; attribute :>> actionClass = "部品交換"; attribute :>> phase = "PH-6"; }
        occurrence <'IFA-047'> ifa_047 : InFlightAnomaly { doc /* STS-103-V-01 RMS エンドエフェクタのスナールが予備解放試験で十分に開かない */ attribute :>> reportNumber = "STS-103-V-01"; attribute :>> flight = "STS-103"; attribute :>> subsystem = "PLS"; attribute :>> causeState = "記載なし"; attribute :>> actionClass = "許容・そのまま飛行"; attribute :>> phase = "PH-3"; }
        occurrence <'IFA-048'> ifa_048 : InFlightAnomaly { doc /* STS-103-V-02 右内側エレボンの黒色タイルが着陸後に欠落 */ attribute :>> reportNumber = "STS-103-V-02"; attribute :>> flight = "STS-103"; attribute :>> subsystem = "TPS"; attribute :>> causeState = "記載なし"; attribute :>> actionClass = "再点検・再試験"; attribute :>> phase = "PH-7"; }
        occurrence <'IFA-049'> ifa_049 : InFlightAnomaly { doc /* STS-103-V-03 左の RCC 前縁パネルの損傷 */ attribute :>> reportNumber = "STS-103-V-03"; attribute :>> flight = "STS-103"; attribute :>> subsystem = "TPS"; attribute :>> causeState = "記載なし"; attribute :>> actionClass = "再点検・再試験"; attribute :>> phase = "PH-7"; }
        occurrence <'IFA-050'> ifa_050 : InFlightAnomaly { doc /* STS-105-V-01 左 OMS 低点酸化剤ドレン配管の温度がヒータ作動温度を下回る */ attribute :>> reportNumber = "STS-105-V-01"; attribute :>> flight = "STS-105"; attribute :>> subsystem = "OMS"; attribute :>> causeState = "記載なし"; attribute :>> actionClass = "許容・そのまま飛行"; attribute :>> phase = "PH-3"; }
        occurrence <'IFA-051'> ifa_051 : InFlightAnomaly { doc /* STS-106-V-01 ET 分離の約 4 秒後の後部主母線 B の電流スパイク */ attribute :>> reportNumber = "STS-106-V-01"; attribute :>> flight = "STS-106"; attribute :>> subsystem = "EPS"; attribute :>> causeState = "推定"; attribute :>> actionClass = "記載なし"; attribute :>> phase = "PH-2"; }
        occurrence <'IFA-052'> ifa_052 : InFlightAnomaly { doc /* STS-106-V-02 -Z スタートラッカが電源・追尾・大きさの BITE を出し、自己試験に失敗 */ attribute :>> reportNumber = "STS-106-V-02"; attribute :>> flight = "STS-106"; attribute :>> subsystem = "GNC"; attribute :>> causeState = "記載なし"; attribute :>> actionClass = "部品交換"; attribute :>> phase = "PH-3"; }
        occurrence <'IFA-053'> ifa_053 : InFlightAnomaly { doc /* STS-106-V-03 MSBLS 2 が着陸の終盤で追尾を失う */ attribute :>> reportNumber = "STS-106-V-03"; attribute :>> flight = "STS-106"; attribute :>> subsystem = "GNC"; attribute :>> causeState = "記載なし"; attribute :>> actionClass = "許容・そのまま飛行"; attribute :>> phase = "PH-6"; }
        occurrence <'IFA-054'> ifa_054 : InFlightAnomaly { doc /* STS-106-V-04 左ベントドア 8・9 の閉マイクロスイッチ 2 が表示されない */ attribute :>> reportNumber = "STS-106-V-04"; attribute :>> flight = "STS-106"; attribute :>> subsystem = "MECH"; attribute :>> causeState = "記載なし"; attribute :>> actionClass = "許容・そのまま飛行"; attribute :>> phase = "PH-6"; }
        occurrence <'IFA-055'> ifa_055 : InFlightAnomaly { doc /* STS-106-V-05 ODS の中心線カメラが初めての通電で起動しない */ attribute :>> reportNumber = "STS-106-V-05"; attribute :>> flight = "STS-106"; attribute :>> subsystem = "PLS"; attribute :>> causeState = "記載なし"; attribute :>> actionClass = "再点検・再試験"; attribute :>> phase = "PH-3"; }
        occurrence <'IFA-056'> ifa_056 : InFlightAnomaly { doc /* STS-107-V-01 AC 2 の B 相の電流の立上がりが鈍い */ attribute :>> reportNumber = "STS-107-V-01"; attribute :>> flight = "STS-107"; attribute :>> subsystem = "EPS"; attribute :>> causeState = "推定"; attribute :>> actionClass = "記載なし"; attribute :>> phase = "PH-1"; }
        occurrence <'IFA-057'> ifa_057 : InFlightAnomaly { doc /* STS-107-V-02 O2 タンク 7 のヒータ A が手動で作動しない */ attribute :>> reportNumber = "STS-107-V-02"; attribute :>> flight = "STS-107"; attribute :>> subsystem = "EPS"; attribute :>> causeState = "記載なし"; attribute :>> actionClass = "許容・そのまま飛行"; attribute :>> phase = "PH-3"; }
        occurrence <'IFA-058'> ifa_058 : InFlightAnomaly { doc /* STS-107-V-03 再突入中の機体の喪失 */ attribute :>> reportNumber = "STS-107-V-03"; attribute :>> flight = "STS-107"; attribute :>> subsystem = "OTHER"; attribute :>> causeState = "調査中"; attribute :>> actionClass = "記載なし"; attribute :>> phase = "PH-6"; }
        occurrence <'IFA-059'> ifa_059 : InFlightAnomaly { doc /* STS-108-V-01 主 RCS スラスタ R4U が「切」で故障し自動で選択解除 */ attribute :>> reportNumber = "STS-108-V-01"; attribute :>> flight = "STS-108"; attribute :>> subsystem = "RCS"; attribute :>> causeState = "推定"; attribute :>> actionClass = "部品交換"; attribute :>> phase = "PH-2"; }
        occurrence <'IFA-060'> ifa_060 : InFlightAnomaly { doc /* STS-108-V-02 主 RCS スラスタ F3F が「切」で故障し選択解除 */ attribute :>> reportNumber = "STS-108-V-02"; attribute :>> flight = "STS-108"; attribute :>> subsystem = "RCS"; attribute :>> causeState = "推定"; attribute :>> actionClass = "部品交換"; attribute :>> phase = "PH-3"; }
        occurrence <'IFA-061'> ifa_061 : InFlightAnomaly { doc /* STS-108-V-03 IMU 2 のプラットフォーム故障・冗長レート故障の BITE */ attribute :>> reportNumber = "STS-108-V-03"; attribute :>> flight = "STS-108"; attribute :>> subsystem = "GNC"; attribute :>> causeState = "特定"; attribute :>> actionClass = "許容・そのまま飛行"; attribute :>> phase = "PH-3"; }
        occurrence <'IFA-062'> ifa_062 : InFlightAnomaly { doc /* STS-108-V-04 FES の副制御器が出口温度を制御できない */ attribute :>> reportNumber = "STS-108-V-04"; attribute :>> flight = "STS-108"; attribute :>> subsystem = "ECLSS"; attribute :>> causeState = "特定"; attribute :>> actionClass = "記載なし"; attribute :>> phase = "PH-4"; }
        occurrence <'IFA-063'> ifa_063 : InFlightAnomaly { doc /* STS-109-V-01 フレオンループ 1 の後部コールドプレートの流量が低下 */ attribute :>> reportNumber = "STS-109-V-01"; attribute :>> flight = "STS-109"; attribute :>> subsystem = "ECLSS"; attribute :>> causeState = "推定"; attribute :>> actionClass = "許容・そのまま飛行"; attribute :>> phase = "PH-2"; }
        occurrence <'IFA-064'> ifa_064 : InFlightAnomaly { doc /* STS-109-V-02 エアロックの内側ハッチ（A ハッチ）のアクチュエータのロックが外れにくい */ attribute :>> reportNumber = "STS-109-V-02"; attribute :>> flight = "STS-109"; attribute :>> subsystem = "EVA"; attribute :>> causeState = "記載なし"; attribute :>> actionClass = "許容・そのまま飛行"; attribute :>> phase = "PH-3"; }
        occurrence <'IFA-065'> ifa_065 : InFlightAnomaly { doc /* STS-109-V-03 LH2 の 4 インチ再循環ラインの切離し部の閉じが遅い */ attribute :>> reportNumber = "STS-109-V-03"; attribute :>> flight = "STS-109"; attribute :>> subsystem = "MPS"; attribute :>> causeState = "記載なし"; attribute :>> actionClass = "許容・そのまま飛行"; attribute :>> phase = "PH-2"; }
        occurrence <'IFA-066'> ifa_066 : InFlightAnomaly { doc /* STS-109-V-04 前方並進ハンドコントローラの C チャネルが早く切れる */ attribute :>> reportNumber = "STS-109-V-04"; attribute :>> flight = "STS-109"; attribute :>> subsystem = "GNC"; attribute :>> causeState = "不明"; attribute :>> actionClass = "許容・そのまま飛行"; attribute :>> phase = "PH-3"; }
        occurrence <'IFA-067'> ifa_067 : InFlightAnomaly { doc /* STS-109-V-05 FES アキュムレータ・高負荷フィードライン B のヒータ系統 2 の故障 */ attribute :>> reportNumber = "STS-109-V-05"; attribute :>> flight = "STS-109"; attribute :>> subsystem = "ECLSS"; attribute :>> causeState = "記載なし"; attribute :>> actionClass = "再点検・再試験"; attribute :>> phase = "PH-3"; }
        occurrence <'IFA-068'> ifa_068 : InFlightAnomaly { doc /* STS-109-V-06 主 RCS スラスタ R3R が「切」で故障し選択解除 */ attribute :>> reportNumber = "STS-109-V-06"; attribute :>> flight = "STS-109"; attribute :>> subsystem = "RCS"; attribute :>> causeState = "推定"; attribute :>> actionClass = "再点検・再試験"; attribute :>> phase = "PH-4"; }
        occurrence <'IFA-069'> ifa_069 : InFlightAnomaly { doc /* STS-109-V-07 EMU 1 の PLSS へ水が漏れる（フィードウォータ遮断弁が開いた） */ attribute :>> reportNumber = "STS-109-V-07"; attribute :>> flight = "STS-109"; attribute :>> subsystem = "EVA"; attribute :>> causeState = "推定"; attribute :>> actionClass = "設計変更"; attribute :>> phase = "PH-5"; }
        occurrence <'IFA-070'> ifa_070 : InFlightAnomaly { doc /* STS-110-V-01 主 RCS スラスタ L1A が「切」で故障し選択解除 */ attribute :>> reportNumber = "STS-110-V-01"; attribute :>> flight = "STS-110"; attribute :>> subsystem = "RCS"; attribute :>> causeState = "推定"; attribute :>> actionClass = "部品交換"; attribute :>> phase = "PH-3"; }
        occurrence <'IFA-071'> ifa_071 : InFlightAnomaly { doc /* STS-110-V-02 主 RCS スラスタ F1D の低いチャンバ圧 */ attribute :>> reportNumber = "STS-110-V-02"; attribute :>> flight = "STS-110"; attribute :>> subsystem = "RCS"; attribute :>> causeState = "不明"; attribute :>> actionClass = "部品交換"; attribute :>> phase = "PH-3"; }
        occurrence <'IFA-072'> ifa_072 : InFlightAnomaly { doc /* STS-110-V-03 主 RCS スラスタ F3L の低いチャンバ圧 */ attribute :>> reportNumber = "STS-110-V-03"; attribute :>> flight = "STS-110"; attribute :>> subsystem = "RCS"; attribute :>> causeState = "記載なし"; attribute :>> actionClass = "部品交換"; attribute :>> phase = "PH-3"; }
        occurrence <'IFA-073'> ifa_073 : InFlightAnomaly { doc /* STS-110-V-04 IDP 2 がバッファ・オーバーフローの誤りと MSU アクセスの BITE を出す */ attribute :>> reportNumber = "STS-110-V-04"; attribute :>> flight = "STS-110"; attribute :>> subsystem = "DPS"; attribute :>> causeState = "推定"; attribute :>> actionClass = "許容・そのまま飛行"; attribute :>> phase = "PH-3"; }
        occurrence <'IFA-074'> ifa_074 : InFlightAnomaly { doc /* STS-111-V-01 OMS 左エンジンの GN2 調圧器の漏れ */ attribute :>> reportNumber = "STS-111-V-01"; attribute :>> flight = "STS-111"; attribute :>> subsystem = "OMS"; attribute :>> causeState = "推定"; attribute :>> actionClass = "部品交換"; attribute :>> phase = "PH-1"; }
        occurrence <'IFA-075'> ifa_075 : InFlightAnomaly { doc /* STS-111-V-02 FES がプライマリ B 制御器のトッピングでスタンバイから復帰しない */ attribute :>> reportNumber = "STS-111-V-02"; attribute :>> flight = "STS-111"; attribute :>> subsystem = "ECLSS"; attribute :>> causeState = "特定"; attribute :>> actionClass = "許容・そのまま飛行"; attribute :>> phase = "PH-3"; }
        occurrence <'IFA-076'> ifa_076 : InFlightAnomaly { doc /* STS-111-V-03 左舷ペイロードベイドア後部の ready-to-latch（R-T-L）表示3つが消えない */ attribute :>> reportNumber = "STS-111-V-03"; attribute :>> flight = "STS-111"; attribute :>> subsystem = "MECH"; attribute :>> causeState = "推定"; attribute :>> actionClass = "部品交換"; attribute :>> phase = "PH-4"; }
        occurrence <'IFA-077'> ifa_077 : InFlightAnomaly { doc /* STS-112-V-01 一次スラスタ L4D の fail-off（燃焼室圧の不足） */ attribute :>> reportNumber = "STS-112-V-01"; attribute :>> flight = "STS-112"; attribute :>> subsystem = "RCS"; attribute :>> causeState = "推定"; attribute :>> actionClass = "部品交換"; attribute :>> phase = "PH-2"; }
        occurrence <'IFA-078'> ifa_078 : InFlightAnomaly { doc /* STS-113-V-01 ペイロードベイの酸素濃度の上昇による打上げの延期 */ attribute :>> reportNumber = "STS-113-V-01"; attribute :>> flight = "STS-113"; attribute :>> subsystem = "ECLSS"; attribute :>> causeState = "推定"; attribute :>> actionClass = "部品交換"; attribute :>> phase = "PH-1"; }
        occurrence <'IFA-079'> ifa_079 : InFlightAnomaly { doc /* STS-113-V-02 OMS 右エンジンのボール弁 2 が開の表示のまま */ attribute :>> reportNumber = "STS-113-V-02"; attribute :>> flight = "STS-113"; attribute :>> subsystem = "OMS"; attribute :>> causeState = "特定"; attribute :>> actionClass = "許容・そのまま飛行"; attribute :>> phase = "PH-2"; }
        occurrence <'IFA-080'> ifa_080 : InFlightAnomaly { doc /* STS-113-V-03 RMS 手首ロール関節の直接駆動試験での角速度スパイク */ attribute :>> reportNumber = "STS-113-V-03"; attribute :>> flight = "STS-113"; attribute :>> subsystem = "PLS"; attribute :>> causeState = "推定"; attribute :>> actionClass = "再点検・再試験"; attribute :>> phase = "PH-3"; }
        occurrence <'IFA-081'> ifa_081 : InFlightAnomaly { doc /* STS-113-V-04 S バンド電力増幅器 PA 2 の出力低下 */ attribute :>> reportNumber = "STS-113-V-04"; attribute :>> flight = "STS-113"; attribute :>> subsystem = "CT"; attribute :>> causeState = "記載なし"; attribute :>> actionClass = "許容・そのまま飛行"; attribute :>> phase = "PH-3"; }
        occurrence <'IFA-082'> ifa_082 : InFlightAnomaly { doc /* STS-113-V-05 FES の水ダンプ中の停止（プライマリ B 制御器） */ attribute :>> reportNumber = "STS-113-V-05"; attribute :>> flight = "STS-113"; attribute :>> subsystem = "ECLSS"; attribute :>> causeState = "推定"; attribute :>> actionClass = "許容・そのまま飛行"; attribute :>> phase = "PH-3"; }
        occurrence <'IFA-083'> ifa_083 : InFlightAnomaly { doc /* STS-114-V-01 LH2 ECO センサ 2 が乾き指令に対して「湿」のまま */ attribute :>> reportNumber = "STS-114-V-01"; attribute :>> flight = "STS-114"; attribute :>> subsystem = "MPS"; attribute :>> causeState = "不明"; attribute :>> actionClass = "再点検・再試験"; attribute :>> phase = "PH-1"; }
        occurrence <'IFA-084'> ifa_084 : InFlightAnomaly { doc /* STS-114-V-02 前部 RCS のタイベック製カバー（スラスタ F3D・F4D）の遅い離脱 */ attribute :>> reportNumber = "STS-114-V-02"; attribute :>> flight = "STS-114"; attribute :>> subsystem = "RCS"; attribute :>> causeState = "推定"; attribute :>> actionClass = "記載なし"; attribute :>> phase = "PH-2"; }
        occurrence <'IFA-085'> ifa_085 : InFlightAnomaly { doc /* STS-114-V-03 左 OMS 上部 Y ウェブ内側の温度が不規則 */ attribute :>> reportNumber = "STS-114-V-03"; attribute :>> flight = "STS-114"; attribute :>> subsystem = "OMS"; attribute :>> causeState = "特定"; attribute :>> actionClass = "部品交換"; attribute :>> phase = "PH-1"; }
        occurrence <'IFA-086'> ifa_086 : InFlightAnomaly { doc /* STS-114-V-04 右舷ペイロードベイドアの閉表示が扉の動きの後も21秒点いたまま */ attribute :>> reportNumber = "STS-114-V-04"; attribute :>> flight = "STS-114"; attribute :>> subsystem = "MECH"; attribute :>> causeState = "記載なし"; attribute :>> actionClass = "再点検・再試験"; attribute :>> phase = "PH-3"; }
        occurrence <'IFA-087'> ifa_087 : InFlightAnomaly { doc /* STS-114-V-05 RMS サイドビューカメラ（RSC）のレンズの汚れ */ attribute :>> reportNumber = "STS-114-V-05"; attribute :>> flight = "STS-114"; attribute :>> subsystem = "CT"; attribute :>> causeState = "推定"; attribute :>> actionClass = "再点検・再試験"; attribute :>> phase = "PH-3"; }
        occurrence <'IFA-088'> ifa_088 : InFlightAnomaly { doc /* STS-114-V-06 APU 1 のドレン系の圧力低下 */ attribute :>> reportNumber = "STS-114-V-06"; attribute :>> flight = "STS-114"; attribute :>> subsystem = "APU"; attribute :>> causeState = "推定"; attribute :>> actionClass = "部品交換"; attribute :>> phase = "PH-3"; }
        occurrence <'IFA-089'> ifa_089 : InFlightAnomaly { doc /* STS-114-V-07 DTV の DSR-20 ビデオテープ装填の故障 */ attribute :>> reportNumber = "STS-114-V-07"; attribute :>> flight = "STS-114"; attribute :>> subsystem = "CT"; attribute :>> causeState = "推定"; attribute :>> actionClass = "部品交換"; attribute :>> phase = "PH-3"; }
        occurrence <'IFA-090'> ifa_090 : InFlightAnomaly { doc /* STS-114-V-08 窓1の下の TPS ブランケットの損傷 */ attribute :>> reportNumber = "STS-114-V-08"; attribute :>> flight = "STS-114"; attribute :>> subsystem = "TPS"; attribute :>> causeState = "記載なし"; attribute :>> actionClass = "許容・そのまま飛行"; attribute :>> phase = "PH-3"; }
        occurrence <'IFA-091'> ifa_091 : InFlightAnomaly { doc /* STS-114-V-09 APU 2 の圧力・温度指示の一時的な喪失 */ attribute :>> reportNumber = "STS-114-V-09"; attribute :>> flight = "STS-114"; attribute :>> subsystem = "APU"; attribute :>> causeState = "調査中"; attribute :>> actionClass = "部品交換"; attribute :>> phase = "PH-3"; }
        occurrence <'IFA-092'> ifa_092 : InFlightAnomaly { doc /* STS-114-V-10 MEDS の MDU CDR2 の 1553B エラー */ attribute :>> reportNumber = "STS-114-V-10"; attribute :>> flight = "STS-114"; attribute :>> subsystem = "DPS"; attribute :>> causeState = "不明"; attribute :>> actionClass = "部品交換"; attribute :>> phase = "PH-3"; }
        occurrence <'IFA-093'> ifa_093 : InFlightAnomaly { doc /* STS-114-V-11 TPS タイルの損傷（デブリによるもの） */ attribute :>> reportNumber = "STS-114-V-11"; attribute :>> flight = "STS-114"; attribute :>> subsystem = "TPS"; attribute :>> causeState = "推定"; attribute :>> actionClass = "許容・そのまま飛行"; attribute :>> phase = "PH-3"; }
        occurrence <'IFA-094'> ifa_094 : InFlightAnomaly { doc /* STS-114-V-12 TPS ギャップフィラの突出 */ attribute :>> reportNumber = "STS-114-V-12"; attribute :>> flight = "STS-114"; attribute :>> subsystem = "TPS"; attribute :>> causeState = "特定"; attribute :>> actionClass = "再点検・再試験"; attribute :>> phase = "PH-3"; }
        occurrence <'IFA-095'> ifa_095 : InFlightAnomaly { doc /* STS-114-V-13 AVIU が機能しなかった */ attribute :>> reportNumber = "STS-114-V-13"; attribute :>> flight = "STS-114"; attribute :>> subsystem = "CT"; attribute :>> causeState = "推定"; attribute :>> actionClass = "部品交換"; attribute :>> phase = "PH-3"; }
        occurrence <'IFA-096'> ifa_096 : InFlightAnomaly { doc /* STS-114-V-14 Viper PCMCIA カード挿入時の PGSC STS3 のロックアップ */ attribute :>> reportNumber = "STS-114-V-14"; attribute :>> flight = "STS-114"; attribute :>> subsystem = "OTHER"; attribute :>> causeState = "推定"; attribute :>> actionClass = "許容・そのまま飛行"; attribute :>> phase = "PH-3"; }
        occurrence <'IFA-097'> ifa_097 : InFlightAnomaly { doc /* STS-114-V-15 エアロックの減圧が通常と異なった */ attribute :>> reportNumber = "STS-114-V-15"; attribute :>> flight = "STS-114"; attribute :>> subsystem = "ECLSS"; attribute :>> causeState = "不明"; attribute :>> actionClass = "再点検・再試験"; attribute :>> phase = "PH-5"; }
        occurrence <'IFA-098'> ifa_098 : InFlightAnomaly { doc /* STS-114-V-16 ODS のキャプチャラッチの手動解除のタルクバックが「開」を示した */ attribute :>> reportNumber = "STS-114-V-16"; attribute :>> flight = "STS-114"; attribute :>> subsystem = "PLS"; attribute :>> causeState = "特定"; attribute :>> actionClass = "再点検・再試験"; attribute :>> phase = "PH-3"; }
        occurrence <'IFA-099'> ifa_099 : InFlightAnomaly { doc /* STS-114-V-17 WLE IDS のセンサユニット4台が処理データを生成しなかった */ attribute :>> reportNumber = "STS-114-V-17"; attribute :>> flight = "STS-114"; attribute :>> subsystem = "TPS"; attribute :>> causeState = "特定"; attribute :>> actionClass = "設計変更"; attribute :>> phase = "PH-2"; }
        occurrence <'IFA-100'> ifa_100 : InFlightAnomaly { doc /* STS-114-V-18 左舷の軽量工具収納組立のラッチが開かなかった */ attribute :>> reportNumber = "STS-114-V-18"; attribute :>> flight = "STS-114"; attribute :>> subsystem = "EVA"; attribute :>> causeState = "推定"; attribute :>> actionClass = "手順・規則の変更"; attribute :>> phase = "PH-5"; }
        occurrence <'IFA-101'> ifa_101 : InFlightAnomaly { doc /* STS-114-V-19 コンティンジェンシー水容器（CWC）の漏れ */ attribute :>> reportNumber = "STS-114-V-19"; attribute :>> flight = "STS-114"; attribute :>> subsystem = "ECLSS"; attribute :>> causeState = "記載なし"; attribute :>> actionClass = "設計変更"; attribute :>> phase = "PH-3"; }
        occurrence <'IFA-102'> ifa_102 : InFlightAnomaly { doc /* STS-114-V-20 OBSS の ITVC の映像喪失 */ attribute :>> reportNumber = "STS-114-V-20"; attribute :>> flight = "STS-114"; attribute :>> subsystem = "CT"; attribute :>> causeState = "推定"; attribute :>> actionClass = "再点検・再試験"; attribute :>> phase = "PH-3"; }
        occurrence <'IFA-103'> ifa_103 : InFlightAnomaly { doc /* STS-114-V-21 OBSS の指向の不正確さ */ attribute :>> reportNumber = "STS-114-V-21"; attribute :>> flight = "STS-114"; attribute :>> subsystem = "PLS"; attribute :>> causeState = "推定"; attribute :>> actionClass = "再点検・再試験"; attribute :>> phase = "PH-3"; }
        occurrence <'IFA-104'> ifa_104 : InFlightAnomaly { doc /* STS-114-V-22 右舷 MPM の中央の系2の格納表示が遅い */ attribute :>> reportNumber = "STS-114-V-22"; attribute :>> flight = "STS-114"; attribute :>> subsystem = "PLS"; attribute :>> causeState = "記載なし"; attribute :>> actionClass = "再点検・再試験"; attribute :>> phase = "PH-3"; }
        occurrence <'IFA-105'> ifa_105 : InFlightAnomaly { doc /* STS-114-V-23 TCS の追尾の喪失の繰り返し */ attribute :>> reportNumber = "STS-114-V-23"; attribute :>> flight = "STS-114"; attribute :>> subsystem = "GNC"; attribute :>> causeState = "推定"; attribute :>> actionClass = "部品交換"; attribute :>> phase = "PH-3"; }
        occurrence <'IFA-106'> ifa_106 : InFlightAnomaly { doc /* STS-114-V-24 バーニア・スラスタ R5R のチャンバ圧（Pc）が低い */ attribute :>> reportNumber = "STS-114-V-24"; attribute :>> flight = "STS-114"; attribute :>> subsystem = "RCS"; attribute :>> causeState = "推定"; attribute :>> actionClass = "部品交換"; attribute :>> phase = "PH-4"; }
        occurrence <'IFA-107'> ifa_107 : InFlightAnomaly { doc /* STS-114-V-25 再突入中の APU 3 の排気ガス温度（EGT）が不規則 */ attribute :>> reportNumber = "STS-114-V-25"; attribute :>> flight = "STS-114"; attribute :>> subsystem = "APU"; attribute :>> causeState = "特定"; attribute :>> actionClass = "部品交換"; attribute :>> phase = "PH-6"; }
        occurrence <'IFA-108'> ifa_108 : InFlightAnomaly { doc /* STS-114-V-26 TPS タイルの損傷（前脚ドア） */ attribute :>> reportNumber = "STS-114-V-26"; attribute :>> flight = "STS-114"; attribute :>> subsystem = "TPS"; attribute :>> causeState = "記載なし"; attribute :>> actionClass = "再点検・再試験"; attribute :>> phase = "PH-7"; }
        occurrence <'IFA-109'> ifa_109 : InFlightAnomaly { doc /* STS-114-V-27 上・下のノーズキャップの膨張シールの左舷側の損傷 */ attribute :>> reportNumber = "STS-114-V-27"; attribute :>> flight = "STS-114"; attribute :>> subsystem = "TPS"; attribute :>> causeState = "調査中"; attribute :>> actionClass = "記載なし"; attribute :>> phase = "PH-7"; }
        occurrence <'IFA-110'> ifa_110 : InFlightAnomaly { doc /* STS-114-V-28 窓5・6の近くの LRSI タイルの部分的なはがれ */ attribute :>> reportNumber = "STS-114-V-28"; attribute :>> flight = "STS-114"; attribute :>> subsystem = "TPS"; attribute :>> causeState = "調査中"; attribute :>> actionClass = "再点検・再試験"; attribute :>> phase = "PH-7"; }
        occurrence <'IFA-111'> ifa_111 : InFlightAnomaly { doc /* STS-114-V-29 前部 ET 結合のせん断ボルトの NSI の解放 */ attribute :>> reportNumber = "STS-114-V-29"; attribute :>> flight = "STS-114"; attribute :>> subsystem = "STR"; attribute :>> causeState = "調査中"; attribute :>> actionClass = "部品交換"; attribute :>> phase = "PH-7"; }
        occurrence <'IFA-112'> ifa_112 : InFlightAnomaly { doc /* STS-114-V-30 ODS のリング整列表示の遅い喪失 */ attribute :>> reportNumber = "STS-114-V-30"; attribute :>> flight = "STS-114"; attribute :>> subsystem = "PLS"; attribute :>> causeState = "推定"; attribute :>> actionClass = "再点検・再試験"; attribute :>> phase = "PH-3"; }
        occurrence <'IFA-113'> ifa_113 : InFlightAnomaly { doc /* STS-114-V-31 TPS のパテ補修の欠落 */ attribute :>> reportNumber = "STS-114-V-31"; attribute :>> flight = "STS-114"; attribute :>> subsystem = "TPS"; attribute :>> causeState = "調査中"; attribute :>> actionClass = "再点検・再試験"; attribute :>> phase = "PH-7"; }
        occurrence <'IFA-114'> ifa_114 : InFlightAnomaly { doc /* STS-114-V-32 GH2 圧力系の漏れ */ attribute :>> reportNumber = "STS-114-V-32"; attribute :>> flight = "STS-114"; attribute :>> subsystem = "MPS"; attribute :>> causeState = "記載なし"; attribute :>> actionClass = "再点検・再試験"; attribute :>> phase = "PH-3"; }
        occurrence <'IFA-115'> ifa_115 : InFlightAnomaly { doc /* STS-114-V-33 MPS/SSME の低圧ヘリウムの減衰率の超過 */ attribute :>> reportNumber = "STS-114-V-33"; attribute :>> flight = "STS-114"; attribute :>> subsystem = "MPS"; attribute :>> causeState = "記載なし"; attribute :>> actionClass = "再点検・再試験"; attribute :>> phase = "PH-3"; }
        occurrence <'IFA-116'> ifa_116 : InFlightAnomaly { doc /* STS-114-V-34 WSB の GN2 レギュレータ出口圧が低い */ attribute :>> reportNumber = "STS-114-V-34"; attribute :>> flight = "STS-114"; attribute :>> subsystem = "APU"; attribute :>> causeState = "推定"; attribute :>> actionClass = "再点検・再試験"; attribute :>> phase = "PH-7"; }
        occurrence <'IFA-117'> ifa_117 : InFlightAnomaly { doc /* STS-114-V-35 機体の荷降ろし中に LiOH カートリッジの割れが見つかった */ attribute :>> reportNumber = "STS-114-V-35"; attribute :>> flight = "STS-114"; attribute :>> subsystem = "ECLSS"; attribute :>> causeState = "推定"; attribute :>> actionClass = "許容・そのまま飛行"; attribute :>> phase = "PH-7"; }
        occurrence <'IFA-118'> ifa_118 : InFlightAnomaly { doc /* STS-114-V-36 後部胴体のサンプルボトル R3 と L3 が高い酸素濃度を示した */ attribute :>> reportNumber = "STS-114-V-36"; attribute :>> flight = "STS-114"; attribute :>> subsystem = "OTHER"; attribute :>> causeState = "記載なし"; attribute :>> actionClass = "記載なし"; attribute :>> phase = "PH-7"; }
        occurrence <'IFA-119'> ifa_119 : InFlightAnomaly { doc /* STS-114-V-37 後部胴体のサンプルボトル L1 が試料を保持できなかった */ attribute :>> reportNumber = "STS-114-V-37"; attribute :>> flight = "STS-114"; attribute :>> subsystem = "OTHER"; attribute :>> causeState = "記載なし"; attribute :>> actionClass = "記載なし"; attribute :>> phase = "PH-7"; }
        occurrence <'IFA-120'> ifa_120 : InFlightAnomaly { doc /* STS-115-V-01 燃料電池1の冷却材ポンプの AC1 相A の短絡 */ attribute :>> reportNumber = "STS-115-V-01"; attribute :>> flight = "STS-115"; attribute :>> subsystem = "EPS"; attribute :>> causeState = "記載なし"; attribute :>> actionClass = "許容・そのまま飛行"; attribute :>> phase = "PH-1"; }
        occurrence <'IFA-121'> ifa_121 : InFlightAnomaly { doc /* STS-115-V-02 ASA 3 のスピードブレーキ・ドライバのチャネル3が不規則 */ attribute :>> reportNumber = "STS-115-V-02"; attribute :>> flight = "STS-115"; attribute :>> subsystem = "GNC"; attribute :>> causeState = "特定"; attribute :>> actionClass = "再点検・再試験"; attribute :>> phase = "PH-2"; }
        occurrence <'IFA-122'> ifa_122 : InFlightAnomaly { doc /* STS-115-V-03 右舷ペイロードベイドアの後方（B）閉リミットスイッチの表示が「閉」のまま */ attribute :>> reportNumber = "STS-115-V-03"; attribute :>> flight = "STS-115"; attribute :>> subsystem = "MECH"; attribute :>> causeState = "記載なし"; attribute :>> actionClass = "部品交換"; attribute :>> phase = "PH-3"; }
        occurrence <'IFA-123'> ifa_123 : InFlightAnomaly { doc /* STS-115-V-04 MADS の PCM データの欠落 */ attribute :>> reportNumber = "STS-115-V-04"; attribute :>> flight = "STS-115"; attribute :>> subsystem = "OTHER"; attribute :>> causeState = "推定"; attribute :>> actionClass = "部品交換"; attribute :>> phase = "PH-2"; }
        occurrence <'IFA-124'> ifa_124 : InFlightAnomaly { doc /* STS-115-V-05 前向き RCS スラスタ F4D の Tyvek カバーの遅い放出 */ attribute :>> reportNumber = "STS-115-V-05"; attribute :>> flight = "STS-115"; attribute :>> subsystem = "RCS"; attribute :>> causeState = "特定"; attribute :>> actionClass = "手順・規則の変更"; attribute :>> phase = "PH-2"; }
        occurrence <'IFA-125'> ifa_125 : InFlightAnomaly { doc /* STS-115-V-06 乗員搭乗時のヘッドセット・インタフェース・ユニット（HIU）の異常 */ attribute :>> reportNumber = "STS-115-V-06"; attribute :>> flight = "STS-115"; attribute :>> subsystem = "CT"; attribute :>> causeState = "記載なし"; attribute :>> actionClass = "部品交換"; attribute :>> phase = "PH-1"; }
        occurrence <'IFA-126'> ifa_126 : InFlightAnomaly { doc /* STS-115-V-07 WSB 3 の GN2 レギュレータ/リリーフ弁の再着座圧力の低下 */ attribute :>> reportNumber = "STS-115-V-07"; attribute :>> flight = "STS-115"; attribute :>> subsystem = "APU"; attribute :>> causeState = "記載なし"; attribute :>> actionClass = "部品交換"; attribute :>> phase = "PH-2"; }
        occurrence <'IFA-127'> ifa_127 : InFlightAnomaly { doc /* STS-115-V-08 TPS のタイル・ブランケットの異常と欠落したセラミック・インサート */ attribute :>> reportNumber = "STS-115-V-08"; attribute :>> flight = "STS-115"; attribute :>> subsystem = "TPS"; attribute :>> causeState = "記載なし"; attribute :>> actionClass = "再点検・再試験"; attribute :>> phase = "PH-3"; }
        occurrence <'IFA-128'> ifa_128 : InFlightAnomaly { doc /* STS-115-V-09 左舷ペイロードベイドアの前方（A）閉表示が早く失われた */ attribute :>> reportNumber = "STS-115-V-09"; attribute :>> flight = "STS-115"; attribute :>> subsystem = "MECH"; attribute :>> causeState = "記載なし"; attribute :>> actionClass = "許容・そのまま飛行"; attribute :>> phase = "PH-3"; }
        occurrence <'IFA-129'> ifa_129 : InFlightAnomaly { doc /* STS-115-V-10 上昇中の FES の停止 */ attribute :>> reportNumber = "STS-115-V-10"; attribute :>> flight = "STS-115"; attribute :>> subsystem = "ECLSS"; attribute :>> causeState = "特定"; attribute :>> actionClass = "記載なし"; attribute :>> phase = "PH-2"; }
        occurrence <'IFA-130'> ifa_130 : InFlightAnomaly { doc /* STS-115-V-11 給水ダンプ配管のヒータ A の異常な温度サイクル */ attribute :>> reportNumber = "STS-115-V-11"; attribute :>> flight = "STS-115"; attribute :>> subsystem = "ECLSS"; attribute :>> causeState = "特定"; attribute :>> actionClass = "部品交換"; attribute :>> phase = "PH-3"; }
        occurrence <'IFA-131'> ifa_131 : InFlightAnomaly { doc /* STS-115-V-12 油圧系3の TVC ピッチ作動器の切替弁の表示 */ attribute :>> reportNumber = "STS-115-V-12"; attribute :>> flight = "STS-115"; attribute :>> subsystem = "MPS"; attribute :>> causeState = "特定"; attribute :>> actionClass = "再点検・再試験"; attribute :>> phase = "PH-1"; }
        occurrence <'IFA-132'> ifa_132 : InFlightAnomaly { doc /* STS-115-V-13 給水ダンプ弁の漏れ */ attribute :>> reportNumber = "STS-115-V-13"; attribute :>> flight = "STS-115"; attribute :>> subsystem = "ECLSS"; attribute :>> causeState = "推定"; attribute :>> actionClass = "次便で対処"; attribute :>> phase = "PH-3"; }
        occurrence <'IFA-133'> ifa_133 : InFlightAnomaly { doc /* STS-115-V-14 SSV（逐次静止画ビデオ）ユニットの故障 */ attribute :>> reportNumber = "STS-115-V-14"; attribute :>> flight = "STS-115"; attribute :>> subsystem = "OTHER"; attribute :>> causeState = "推定"; attribute :>> actionClass = "部品交換"; attribute :>> phase = "PH-3"; }
        occurrence <'IFA-134'> ifa_134 : InFlightAnomaly { doc /* STS-115-V-15 APU 2 の X 軸加速度計のデータの不規則 */ attribute :>> reportNumber = "STS-115-V-15"; attribute :>> flight = "STS-115"; attribute :>> subsystem = "APU"; attribute :>> causeState = "記載なし"; attribute :>> actionClass = "部品交換"; attribute :>> phase = "PH-2"; }
        occurrence <'IFA-135'> ifa_135 : InFlightAnomaly { doc /* STS-115-V-16 再突入中の APU 2 の排気ガス温度（EGT）1 の不規則 */ attribute :>> reportNumber = "STS-115-V-16"; attribute :>> flight = "STS-115"; attribute :>> subsystem = "APU"; attribute :>> causeState = "記載なし"; attribute :>> actionClass = "部品交換"; attribute :>> phase = "PH-6"; }
        occurrence <'IFA-136'> ifa_136 : InFlightAnomaly { doc /* STS-115-V-17 ドッキング中のエア・トゥ・グラウンド（A/G）ループの失敗 */ attribute :>> reportNumber = "STS-115-V-17"; attribute :>> flight = "STS-115"; attribute :>> subsystem = "CT"; attribute :>> causeState = "不明"; attribute :>> actionClass = "再点検・再試験"; attribute :>> phase = "PH-3"; }
        occurrence <'IFA-137'> ifa_137 : InFlightAnomaly { doc /* STS-115-V-18 S 帯の右下アンテナの通信の問題 */ attribute :>> reportNumber = "STS-115-V-18"; attribute :>> flight = "STS-115"; attribute :>> subsystem = "CT"; attribute :>> causeState = "特定"; attribute :>> actionClass = "部品交換"; attribute :>> phase = "PH-3"; }
        occurrence <'IFA-138'> ifa_138 : InFlightAnomaly { doc /* STS-115-V-19 FES トッピングの左ダクト・センサの不規則・下限振り切れ */ attribute :>> reportNumber = "STS-115-V-19"; attribute :>> flight = "STS-115"; attribute :>> subsystem = "ECLSS"; attribute :>> causeState = "特定"; attribute :>> actionClass = "再点検・再試験"; attribute :>> phase = "PH-6"; }
        occurrence <'IFA-139'> ifa_139 : InFlightAnomaly { doc /* STS-115-V-20 MADS の FDM 2 マルチプレクサ D の BITE 表示 */ attribute :>> reportNumber = "STS-115-V-20"; attribute :>> flight = "STS-115"; attribute :>> subsystem = "OTHER"; attribute :>> causeState = "記載なし"; attribute :>> actionClass = "部品交換"; attribute :>> phase = "PH-4"; }
        occurrence <'IFA-140'> ifa_140 : InFlightAnomaly { doc /* STS-115-V-21 機首キャップの膨張シールの RCC の損傷 */ attribute :>> reportNumber = "STS-115-V-21"; attribute :>> flight = "STS-115"; attribute :>> subsystem = "TPS"; attribute :>> causeState = "推定"; attribute :>> actionClass = "設計変更"; attribute :>> phase = "PH-7"; }
        occurrence <'IFA-141'> ifa_141 : InFlightAnomaly { doc /* STS-115-V-22 MADS がテープを引かない */ attribute :>> reportNumber = "STS-115-V-22"; attribute :>> flight = "STS-115"; attribute :>> subsystem = "OTHER"; attribute :>> causeState = "特定"; attribute :>> actionClass = "再点検・再試験"; attribute :>> phase = "PH-4"; }
        occurrence <'IFA-142'> ifa_142 : InFlightAnomaly { doc /* STS-115-V-23 主エンジン2の LO2 入口圧力変換器が低く読む */ attribute :>> reportNumber = "STS-115-V-23"; attribute :>> flight = "STS-115"; attribute :>> subsystem = "MPS"; attribute :>> causeState = "特定"; attribute :>> actionClass = "部品交換"; attribute :>> phase = "PH-1"; }
        occurrence <'IFA-143'> ifa_143 : InFlightAnomaly { doc /* STS-115-V-24 RCS スラスタ R4R のヒータが ON のまま故障 */ attribute :>> reportNumber = "STS-115-V-24"; attribute :>> flight = "STS-115"; attribute :>> subsystem = "RCS"; attribute :>> causeState = "記載なし"; attribute :>> actionClass = "部品交換"; attribute :>> phase = "PH-6"; }
        occurrence <'IFA-144'> ifa_144 : InFlightAnomaly { doc /* STS-115-V-25 後部サンプルボトル L1 と R2 の漏れ */ attribute :>> reportNumber = "STS-115-V-25"; attribute :>> flight = "STS-115"; attribute :>> subsystem = "OTHER"; attribute :>> causeState = "推定"; attribute :>> actionClass = "再点検・再試験"; attribute :>> phase = "PH-7"; }
        occurrence <'IFA-145'> ifa_145 : InFlightAnomaly { doc /* STS-115-V-26 Ku 帯の角度追尾の問題 */ attribute :>> reportNumber = "STS-115-V-26"; attribute :>> flight = "STS-115"; attribute :>> subsystem = "CT"; attribute :>> causeState = "推定"; attribute :>> actionClass = "許容・そのまま飛行"; attribute :>> phase = "PH-3"; }
        occurrence <'IFA-146'> ifa_146 : InFlightAnomaly { doc /* STS-115-V-27 右舷ラジエータの微小隕石・軌道デブリ（MMOD）の衝突 */ attribute :>> reportNumber = "STS-115-V-27"; attribute :>> flight = "STS-115"; attribute :>> subsystem = "STR"; attribute :>> causeState = "特定"; attribute :>> actionClass = "再点検・再試験"; attribute :>> phase = "PH-7"; }
        occurrence <'IFA-147'> ifa_147 : InFlightAnomaly { doc /* STS-115-V-28 CCTV モニタ1のちらつき */ attribute :>> reportNumber = "STS-115-V-28"; attribute :>> flight = "STS-115"; attribute :>> subsystem = "CT"; attribute :>> causeState = "記載なし"; attribute :>> actionClass = "部品交換"; attribute :>> phase = "PH-3"; }
        occurrence <'IFA-148'> ifa_148 : InFlightAnomaly { doc /* STS-115-V-29 オービタ・アンビリカルの 16 mm ET 分離カメラの映像の欠落とピントの問題 */ attribute :>> reportNumber = "STS-115-V-29"; attribute :>> flight = "STS-115"; attribute :>> subsystem = "OTHER"; attribute :>> causeState = "特定"; attribute :>> actionClass = "再点検・再試験"; attribute :>> phase = "PH-2"; }
        occurrence <'IFA-149'> ifa_149 : InFlightAnomaly { doc /* STS-115-V-30 ドラッグシュート付近で見つかった TCS のグラウンドストラップ */ attribute :>> reportNumber = "STS-115-V-30"; attribute :>> flight = "STS-115"; attribute :>> subsystem = "MECH"; attribute :>> causeState = "特定"; attribute :>> actionClass = "再点検・再試験"; attribute :>> phase = "PH-7"; }
        occurrence <'IFA-150'> ifa_150 : InFlightAnomaly { doc /* STS-115-V-31 打上げ・再突入服（LES）の呼吸用レギュレータの取付けブロックの留め具の欠落 */ attribute :>> reportNumber = "STS-115-V-31"; attribute :>> flight = "STS-115"; attribute :>> subsystem = "CREW"; attribute :>> causeState = "不明"; attribute :>> actionClass = "手順・規則の変更"; attribute :>> phase = "PH-7"; }
        occurrence <'IFA-151'> ifa_151 : InFlightAnomaly { doc /* STS-115-V-32 MADS の左 OMS ポッド LRSI 表面温度が上限振り切れ */ attribute :>> reportNumber = "STS-115-V-32"; attribute :>> flight = "STS-115"; attribute :>> subsystem = "OTHER"; attribute :>> causeState = "記載なし"; attribute :>> actionClass = "次便で対処"; attribute :>> phase = "PH-1"; }
        occurrence <'IFA-152'> ifa_152 : InFlightAnomaly { doc /* STS-116-V-01 SRMS の点検中にエンドエフェクタの自動解放ができなくなる */ attribute :>> reportNumber = "STS-116-V-01"; attribute :>> flight = "STS-116"; attribute :>> subsystem = "PLS"; attribute :>> causeState = "不明"; attribute :>> actionClass = "部品交換"; attribute :>> phase = "PH-3"; }
        occurrence <'IFA-153'> ifa_153 : InFlightAnomaly { doc /* STS-116-V-02 燃料電池 3 の O2 流量計が最低値側に振り切れ */ attribute :>> reportNumber = "STS-116-V-02"; attribute :>> flight = "STS-116"; attribute :>> subsystem = "EPS"; attribute :>> causeState = "推定"; attribute :>> actionClass = "許容・そのまま飛行"; attribute :>> phase = "PH-3"; }
        occurrence <'IFA-154'> ifa_154 : InFlightAnomaly { doc /* STS-116-V-03 FES の一次 B 制御器がスタンバイから復帰せず */ attribute :>> reportNumber = "STS-116-V-03"; attribute :>> flight = "STS-116"; attribute :>> subsystem = "ECLSS"; attribute :>> causeState = "推定"; attribute :>> actionClass = "再点検・再試験"; attribute :>> phase = "PH-3"; }
        occurrence <'IFA-155'> ifa_155 : InFlightAnomaly { doc /* STS-116-V-04 ペイロードベイの左舷中央の投光器が点灯せず */ attribute :>> reportNumber = "STS-116-V-04"; attribute :>> flight = "STS-116"; attribute :>> subsystem = "CREW"; attribute :>> causeState = "特定"; attribute :>> actionClass = "部品交換"; attribute :>> phase = "PH-3"; }
        occurrence <'IFA-156'> ifa_156 : InFlightAnomaly { doc /* STS-116-V-05 A6U の後部イベントタイマのサムホイールが正しく更新されず */ attribute :>> reportNumber = "STS-116-V-05"; attribute :>> flight = "STS-116"; attribute :>> subsystem = "OTHER"; attribute :>> causeState = "推定"; attribute :>> actionClass = "許容・そのまま飛行"; attribute :>> phase = "PH-3"; }
        occurrence <'IFA-157'> ifa_157 : InFlightAnomaly { doc /* STS-116-V-06 TPS のタイルとブランケットの損傷（STS-116 の TPS 関連の損傷の集約） */ attribute :>> reportNumber = "STS-116-V-06"; attribute :>> flight = "STS-116"; attribute :>> subsystem = "TPS"; attribute :>> causeState = "推定"; attribute :>> actionClass = "部品交換"; attribute :>> phase = "PH-2"; }
        occurrence <'IFA-158'> ifa_158 : InFlightAnomaly { doc /* STS-116-V-07 ML94B のカメラのクイックシューが剥離 */ attribute :>> reportNumber = "STS-116-V-07"; attribute :>> flight = "STS-116"; attribute :>> subsystem = "OTHER"; attribute :>> causeState = "推定"; attribute :>> actionClass = "再点検・再試験"; attribute :>> phase = "PH-3"; }
        occurrence <'IFA-159'> ifa_159 : InFlightAnomaly { doc /* STS-116-V-08 EVA 3 で手持ちのデジタルカメラが失われる */ attribute :>> reportNumber = "STS-116-V-08"; attribute :>> flight = "STS-116"; attribute :>> subsystem = "EVA"; attribute :>> causeState = "推定"; attribute :>> actionClass = "手順・規則の変更"; attribute :>> phase = "PH-5"; }
        occurrence <'IFA-160'> ifa_160 : InFlightAnomaly { doc /* STS-116-V-09 廃水ダンプの流量低下 */ attribute :>> reportNumber = "STS-116-V-09"; attribute :>> flight = "STS-116"; attribute :>> subsystem = "ECLSS"; attribute :>> causeState = "推定"; attribute :>> actionClass = "部品交換"; attribute :>> phase = "PH-3"; }
        occurrence <'IFA-161'> ifa_161 : InFlightAnomaly { doc /* STS-116-V-10 -Z スタートラッカの圧力異常の BITE 表示 */ attribute :>> reportNumber = "STS-116-V-10"; attribute :>> flight = "STS-116"; attribute :>> subsystem = "GNC"; attribute :>> causeState = "記載なし"; attribute :>> actionClass = "再点検・再試験"; attribute :>> phase = "PH-3"; }
        occurrence <'IFA-162'> ifa_162 : InFlightAnomaly { doc /* STS-116-V-11 GPS 受信機が衛星の切替えをしない */ attribute :>> reportNumber = "STS-116-V-11"; attribute :>> flight = "STS-116"; attribute :>> subsystem = "GNC"; attribute :>> causeState = "推定"; attribute :>> actionClass = "手順・規則の変更"; attribute :>> phase = "PH-4"; }
        occurrence <'IFA-163'> ifa_163 : InFlightAnomaly { doc /* STS-116-V-12 MADS の信号が途切れる */ attribute :>> reportNumber = "STS-116-V-12"; attribute :>> flight = "STS-116"; attribute :>> subsystem = "CT"; attribute :>> causeState = "記載なし"; attribute :>> actionClass = "許容・そのまま飛行"; attribute :>> phase = "PH-2"; }
        occurrence <'IFA-164'> ifa_164 : InFlightAnomaly { doc /* STS-116-V-13 翼前縁の衝撃検知システムのセンサユニットが不意に停止 */ attribute :>> reportNumber = "STS-116-V-13"; attribute :>> flight = "STS-116"; attribute :>> subsystem = "STR"; attribute :>> causeState = "記載なし"; attribute :>> actionClass = "記載なし"; attribute :>> phase = "PH-3"; }
        occurrence <'IFA-165'> ifa_165 : InFlightAnomaly { doc /* STS-116-V-14 左エレボンのコーブの過熱 */ attribute :>> reportNumber = "STS-116-V-14"; attribute :>> flight = "STS-116"; attribute :>> subsystem = "TPS"; attribute :>> causeState = "記載なし"; attribute :>> actionClass = "部品交換"; attribute :>> phase = "PH-7"; }
        occurrence <'IFA-166'> ifa_166 : InFlightAnomaly { doc /* STS-117-V-01 SSME 3 の LH2 圧力変換器が最高値側に振り切れ、FA3 MDM のカード 14 が A/D BITE を報告 */ attribute :>> reportNumber = "STS-117-V-01"; attribute :>> flight = "STS-117"; attribute :>> subsystem = "MPS"; attribute :>> causeState = "推定"; attribute :>> actionClass = "部品交換"; attribute :>> phase = "PH-2"; }
        occurrence <'IFA-167'> ifa_167 : InFlightAnomaly { doc /* STS-117-V-02 TPS のタイルとブランケットの損傷（STS-117 の TPS 関連の損傷の集約） */ attribute :>> reportNumber = "STS-117-V-02"; attribute :>> flight = "STS-117"; attribute :>> subsystem = "TPS"; attribute :>> causeState = "不明"; attribute :>> actionClass = "再点検・再試験"; attribute :>> phase = "PH-3"; }
        occurrence <'IFA-168'> ifa_168 : InFlightAnomaly { doc /* STS-117-V-03 OA2 MDM のカード 5 の BITE 表示 */ attribute :>> reportNumber = "STS-117-V-03"; attribute :>> flight = "STS-117"; attribute :>> subsystem = "DPS"; attribute :>> causeState = "特定"; attribute :>> actionClass = "部品交換"; attribute :>> phase = "PH-3"; }
        occurrence <'IFA-169'> ifa_169 : InFlightAnomaly { doc /* STS-117-V-04 カメラ A がニアフォーカスで固着 */ attribute :>> reportNumber = "STS-117-V-04"; attribute :>> flight = "STS-117"; attribute :>> subsystem = "CT"; attribute :>> causeState = "調査中"; attribute :>> actionClass = "再点検・再試験"; attribute :>> phase = "PH-3"; }
        occurrence <'IFA-170'> ifa_170 : InFlightAnomaly { doc /* STS-117-V-05 CWC の注入ポートから漏れ */ attribute :>> reportNumber = "STS-117-V-05"; attribute :>> flight = "STS-117"; attribute :>> subsystem = "ECLSS"; attribute :>> causeState = "推定"; attribute :>> actionClass = "再点検・再試験"; attribute :>> phase = "PH-3"; }
        occurrence <'IFA-171'> ifa_171 : InFlightAnomaly { doc /* STS-117-V-06 SSOR 1 の通信喪失 */ attribute :>> reportNumber = "STS-117-V-06"; attribute :>> flight = "STS-117"; attribute :>> subsystem = "CT"; attribute :>> causeState = "記載なし"; attribute :>> actionClass = "再点検・再試験"; attribute :>> phase = "PH-3"; }
        occurrence <'IFA-172'> ifa_172 : InFlightAnomaly { doc /* STS-117-V-07 デジタルアンビリカルカメラの画像の破損 */ attribute :>> reportNumber = "STS-117-V-07"; attribute :>> flight = "STS-117"; attribute :>> subsystem = "OTHER"; attribute :>> causeState = "推定"; attribute :>> actionClass = "許容・そのまま飛行"; attribute :>> phase = "PH-3"; }
        occurrence <'IFA-173'> ifa_173 : InFlightAnomaly { doc /* STS-117-V-08 モニタ 2 でカメラデータの表示が失われる */ attribute :>> reportNumber = "STS-117-V-08"; attribute :>> flight = "STS-117"; attribute :>> subsystem = "CT"; attribute :>> causeState = "推定"; attribute :>> actionClass = "再点検・再試験"; attribute :>> phase = "PH-3"; }
        occurrence <'IFA-174'> ifa_174 : InFlightAnomaly { doc /* STS-117-V-09 モニタ 1 のちらつきと唸り音 */ attribute :>> reportNumber = "STS-117-V-09"; attribute :>> flight = "STS-117"; attribute :>> subsystem = "CT"; attribute :>> causeState = "推定"; attribute :>> actionClass = "再点検・再試験"; attribute :>> phase = "PH-3"; }
        occurrence <'IFA-175'> ifa_175 : InFlightAnomaly { doc /* STS-117-V-10 パネル A6 のアナンシエータの干渉音 */ attribute :>> reportNumber = "STS-117-V-10"; attribute :>> flight = "STS-117"; attribute :>> subsystem = "CW"; attribute :>> causeState = "推定"; attribute :>> actionClass = "許容・そのまま飛行"; attribute :>> phase = "PH-3"; }
        occurrence <'IFA-176'> ifa_176 : InFlightAnomaly { doc /* STS-117-V-11 MADS の記録器のテープ速度が指令なしに増える */ attribute :>> reportNumber = "STS-117-V-11"; attribute :>> flight = "STS-117"; attribute :>> subsystem = "CT"; attribute :>> causeState = "推定"; attribute :>> actionClass = "再点検・再試験"; attribute :>> phase = "PH-7"; }
        occurrence <'IFA-177'> ifa_177 : InFlightAnomaly { doc /* STS-117-V-12 サラダボウルの Kahr-Lon ライナのコーティングのはがれ */ attribute :>> reportNumber = "STS-117-V-12"; attribute :>> flight = "STS-117"; attribute :>> subsystem = "STR"; attribute :>> causeState = "調査中"; attribute :>> actionClass = "再点検・再試験"; attribute :>> phase = "PH-7"; }
        occurrence <'IFA-178'> ifa_178 : InFlightAnomaly { doc /* STS-117-V-13 MSGU のユニットがデータを取らない */ attribute :>> reportNumber = "STS-117-V-13"; attribute :>> flight = "STS-117"; attribute :>> subsystem = "OTHER"; attribute :>> causeState = "調査中"; attribute :>> actionClass = "記載なし"; attribute :>> phase = "PH-2"; }
        occurrence <'IFA-179'> ifa_179 : InFlightAnomaly { doc /* STS-117-V-14 左舷前方の MPM の台座の収納表示が点かない */ attribute :>> reportNumber = "STS-117-V-14"; attribute :>> flight = "STS-117"; attribute :>> subsystem = "PLS"; attribute :>> causeState = "不明"; attribute :>> actionClass = "手順・規則の変更"; attribute :>> phase = "PH-4"; }
        occurrence <'IFA-180'> ifa_180 : InFlightAnomaly { doc /* STS-118-V-01 PRSD の極低温 O2 タンク2の制御圧力が下限外れ */ attribute :>> reportNumber = "STS-118-V-01"; attribute :>> flight = "STS-118"; attribute :>> subsystem = "EPS"; attribute :>> causeState = "特定"; attribute :>> actionClass = "部品交換"; attribute :>> phase = "PH-3"; }
        occurrence <'IFA-181'> ifa_181 : InFlightAnomaly { doc /* STS-118-V-02 パネル O8 の表示灯試験スイッチの左位置が故障 */ attribute :>> reportNumber = "STS-118-V-02"; attribute :>> flight = "STS-118"; attribute :>> subsystem = "CW"; attribute :>> causeState = "推定"; attribute :>> actionClass = "再点検・再試験"; attribute :>> phase = "PH-3"; }
        occurrence <'IFA-182'> ifa_182 : InFlightAnomaly { doc /* STS-118-V-03 タイルの損傷・ブランケットの引込み・ギャップフィラの突出 */ attribute :>> reportNumber = "STS-118-V-03"; attribute :>> flight = "STS-118"; attribute :>> subsystem = "TPS"; attribute :>> causeState = "記載なし"; attribute :>> actionClass = "記載なし"; attribute :>> phase = "PH-3"; }
        occurrence <'IFA-183'> ifa_183 : InFlightAnomaly { doc /* STS-118-V-04 APU 3 のシール空洞ドレン配管の圧力低下 */ attribute :>> reportNumber = "STS-118-V-04"; attribute :>> flight = "STS-118"; attribute :>> subsystem = "APU"; attribute :>> causeState = "特定"; attribute :>> actionClass = "部品交換"; attribute :>> phase = "PH-3"; }
        occurrence <'IFA-184'> ifa_184 : InFlightAnomaly { doc /* STS-118-V-05 FRCS スラスタ F3D の Tyvek カバーが一部残った */ attribute :>> reportNumber = "STS-118-V-05"; attribute :>> flight = "STS-118"; attribute :>> subsystem = "RCS"; attribute :>> causeState = "推定"; attribute :>> actionClass = "許容・そのまま飛行"; attribute :>> phase = "PH-2"; }
        occurrence <'IFA-185'> ifa_185 : InFlightAnomaly { doc /* STS-118-V-06 MADS の左 OMS ポッド LRSI 表面前方の熱電対が上限外れ */ attribute :>> reportNumber = "STS-118-V-06"; attribute :>> flight = "STS-118"; attribute :>> subsystem = "OTHER"; attribute :>> causeState = "特定"; attribute :>> actionClass = "次便で対処"; attribute :>> phase = "PH-2"; }
        occurrence <'IFA-186'> ifa_186 : InFlightAnomaly { doc /* STS-118-V-07 MADS の左 OMS ポッドの熱電対 BP049T が上限外れ */ attribute :>> reportNumber = "STS-118-V-07"; attribute :>> flight = "STS-118"; attribute :>> subsystem = "OTHER"; attribute :>> causeState = "特定"; attribute :>> actionClass = "次便で対処"; attribute :>> phase = "PH-2"; }
        occurrence <'IFA-187'> ifa_187 : InFlightAnomaly { doc /* STS-118-V-08 左舷前方の MRL のラッチの系統1の表示の遅れ */ attribute :>> reportNumber = "STS-118-V-08"; attribute :>> flight = "STS-118"; attribute :>> subsystem = "PLS"; attribute :>> causeState = "不明"; attribute :>> actionClass = "許容・そのまま飛行"; attribute :>> phase = "PH-3"; }
        occurrence <'IFA-188'> ifa_188 : InFlightAnomaly { doc /* STS-118-V-09 カメラ A の画像が赤紫色になる */ attribute :>> reportNumber = "STS-118-V-09"; attribute :>> flight = "STS-118"; attribute :>> subsystem = "CT"; attribute :>> causeState = "記載なし"; attribute :>> actionClass = "記載なし"; attribute :>> phase = "PH-3"; }
        occurrence <'IFA-189'> ifa_189 : InFlightAnomaly { doc /* STS-118-V-10 FCS 点検中の ADTA 3 の通信の故障 */ attribute :>> reportNumber = "STS-118-V-10"; attribute :>> flight = "STS-118"; attribute :>> subsystem = "GNC"; attribute :>> causeState = "推定"; attribute :>> actionClass = "部品交換"; attribute :>> phase = "PH-4"; }
        occurrence <'IFA-190'> ifa_190 : InFlightAnomaly { doc /* STS-118-V-11 LiOH キャニスタの粉じん */ attribute :>> reportNumber = "STS-118-V-11"; attribute :>> flight = "STS-118"; attribute :>> subsystem = "ECLSS"; attribute :>> causeState = "推定"; attribute :>> actionClass = "手順・規則の変更"; attribute :>> phase = "PH-3"; }
        occurrence <'IFA-191'> ifa_191 : InFlightAnomaly { doc /* STS-118-V-12 ドラッグシュートの火工品式リーフィング・ライン・カッタがラインを切り離さなかった */ attribute :>> reportNumber = "STS-118-V-12"; attribute :>> flight = "STS-118"; attribute :>> subsystem = "MECH"; attribute :>> causeState = "特定"; attribute :>> actionClass = "記載なし"; attribute :>> phase = "PH-7"; }
        occurrence <'IFA-192'> ifa_192 : InFlightAnomaly { doc /* STS-118-V-13 側面ハッチのリミットスイッチの抵抗の故障 */ attribute :>> reportNumber = "STS-118-V-13"; attribute :>> flight = "STS-118"; attribute :>> subsystem = "STR"; attribute :>> causeState = "特定"; attribute :>> actionClass = "再点検・再試験"; attribute :>> phase = "PH-1"; }
        occurrence <'IFA-193'> ifa_193 : InFlightAnomaly { doc /* STS-119-V-01 燃料電池3の O2 流量計が下限外れ */ attribute :>> reportNumber = "STS-119-V-01"; attribute :>> flight = "STS-119"; attribute :>> subsystem = "EPS"; attribute :>> causeState = "推定"; attribute :>> actionClass = "部品交換"; attribute :>> phase = "PH-3"; }
        occurrence <'IFA-194'> ifa_194 : InFlightAnomaly { doc /* STS-119-V-02 AVIU S/N 1031 の故障 */ attribute :>> reportNumber = "STS-119-V-02"; attribute :>> flight = "STS-119"; attribute :>> subsystem = "CT"; attribute :>> causeState = "特定"; attribute :>> actionClass = "部品交換"; attribute :>> phase = "PH-3"; }
        occurrence <'IFA-195'> ifa_195 : InFlightAnomaly { doc /* STS-119-V-03 エルゴメータのペダルの動きの制限 */ attribute :>> reportNumber = "STS-119-V-03"; attribute :>> flight = "STS-119"; attribute :>> subsystem = "CREW"; attribute :>> causeState = "特定"; attribute :>> actionClass = "再点検・再試験"; attribute :>> phase = "PH-3"; }
        occurrence <'IFA-196'> ifa_196 : InFlightAnomaly { doc /* STS-119-V-04 ET アンビリカル・ウェル・カメラのフラッシュとダウンロードの不具合 */ attribute :>> reportNumber = "STS-119-V-04"; attribute :>> flight = "STS-119"; attribute :>> subsystem = "OTHER"; attribute :>> causeState = "特定"; attribute :>> actionClass = "記載なし"; attribute :>> phase = "PH-2"; }
        occurrence <'IFA-197'> ifa_197 : InFlightAnomaly { doc /* STS-119-V-05 MADS の底面熱シールド外部圧力センサが下限外れ */ attribute :>> reportNumber = "STS-119-V-05"; attribute :>> flight = "STS-119"; attribute :>> subsystem = "OTHER"; attribute :>> causeState = "特定"; attribute :>> actionClass = "再点検・再試験"; attribute :>> phase = "PH-2"; }
        occurrence <'IFA-198'> ifa_198 : InFlightAnomaly { doc /* STS-119-V-06 TPS のタイルとブランケットの異常 */ attribute :>> reportNumber = "STS-119-V-06"; attribute :>> flight = "STS-119"; attribute :>> subsystem = "TPS"; attribute :>> causeState = "記載なし"; attribute :>> actionClass = "許容・そのまま飛行"; attribute :>> phase = "PH-3"; }
        occurrence <'IFA-199'> ifa_199 : InFlightAnomaly { doc /* STS-119-V-07 WLES センサ 1033 の時計の誤差 */ attribute :>> reportNumber = "STS-119-V-07"; attribute :>> flight = "STS-119"; attribute :>> subsystem = "STR"; attribute :>> causeState = "調査中"; attribute :>> actionClass = "部品交換"; attribute :>> phase = "PH-3"; }
        occurrence <'IFA-200'> ifa_200 : InFlightAnomaly { doc /* STS-119-V-08 スラスタ F4D の Tyvek 雨よけカバーの一部が残った */ attribute :>> reportNumber = "STS-119-V-08"; attribute :>> flight = "STS-119"; attribute :>> subsystem = "RCS"; attribute :>> causeState = "記載なし"; attribute :>> actionClass = "設計変更"; attribute :>> phase = "PH-2"; }
        occurrence <'IFA-201'> ifa_201 : InFlightAnomaly { doc /* STS-119-V-09 WLES センサ S/N 1024 の不意のモード変化 */ attribute :>> reportNumber = "STS-119-V-09"; attribute :>> flight = "STS-119"; attribute :>> subsystem = "STR"; attribute :>> causeState = "調査中"; attribute :>> actionClass = "部品交換"; attribute :>> phase = "PH-3"; }
        occurrence <'IFA-202'> ifa_202 : InFlightAnomaly { doc /* STS-119-V-10 APU 2 の燃料ポンプ B のヒータのサーモスタットが小刻みに入切 */ attribute :>> reportNumber = "STS-119-V-10"; attribute :>> flight = "STS-119"; attribute :>> subsystem = "APU"; attribute :>> causeState = "推定"; attribute :>> actionClass = "部品交換"; attribute :>> phase = "PH-3"; }
        occurrence <'IFA-203'> ifa_203 : InFlightAnomaly { doc /* STS-119-V-11 APU 2 の EGT 1 のトランスデューサが不規則 */ attribute :>> reportNumber = "STS-119-V-11"; attribute :>> flight = "STS-119"; attribute :>> subsystem = "APU"; attribute :>> causeState = "推定"; attribute :>> actionClass = "部品交換"; attribute :>> phase = "PH-6"; }
        occurrence <'IFA-204'> ifa_204 : InFlightAnomaly { doc /* STS-119-V-12 APU 3 の Z 軸加速度計の読みが高い傾向 */ attribute :>> reportNumber = "STS-119-V-12"; attribute :>> flight = "STS-119"; attribute :>> subsystem = "APU"; attribute :>> causeState = "不明"; attribute :>> actionClass = "部品交換"; attribute :>> phase = "PH-6"; }
        occurrence <'IFA-205'> ifa_205 : InFlightAnomaly { doc /* STS-119-V-13 ET・オービタ・アンビリカルの LH2 前方外側のアクチュエータが機械ロックまで引き込まれなかった */ attribute :>> reportNumber = "STS-119-V-13"; attribute :>> flight = "STS-119"; attribute :>> subsystem = "MECH"; attribute :>> causeState = "特定"; attribute :>> actionClass = "部品交換"; attribute :>> phase = "PH-2"; }
        occurrence <'IFA-206'> ifa_206 : InFlightAnomaly { doc /* STS-119-V-14 MADS のメインエンジン3のジンバル軸受の加速度計のデータが不規則 */ attribute :>> reportNumber = "STS-119-V-14"; attribute :>> flight = "STS-119"; attribute :>> subsystem = "OTHER"; attribute :>> causeState = "特定"; attribute :>> actionClass = "部品交換"; attribute :>> phase = "PH-2"; }
        occurrence <'IFA-207'> ifa_207 : InFlightAnomaly { doc /* STS-119-V-15 SORG の注水時の漏れ */ attribute :>> reportNumber = "STS-119-V-15"; attribute :>> flight = "STS-119"; attribute :>> subsystem = "ECLSS"; attribute :>> causeState = "推定"; attribute :>> actionClass = "部品交換"; attribute :>> phase = "PH-3"; }
        occurrence <'IFA-208'> ifa_208 : InFlightAnomaly { doc /* STS-119-V-16 HUD ミニカムの映像が再突入中に地上へ下りなかった */ attribute :>> reportNumber = "STS-119-V-16"; attribute :>> flight = "STS-119"; attribute :>> subsystem = "CT"; attribute :>> causeState = "不明"; attribute :>> actionClass = "再点検・再試験"; attribute :>> phase = "PH-6"; }
        occurrence <'IFA-209'> ifa_209 : InFlightAnomaly { doc /* STS-120-V-01 MPS エンジン 1 の LO2 入口温度が不安定 */ attribute :>> reportNumber = "STS-120-V-01"; attribute :>> flight = "STS-120"; attribute :>> subsystem = "MPS"; attribute :>> causeState = "特定"; attribute :>> actionClass = "部品交換"; attribute :>> phase = "PH-2"; }
        occurrence <'IFA-210'> ifa_210 : InFlightAnomaly { doc /* STS-120-V-02 PRLA 4 のラッチ表示が遅れた（ON から OFF） */ attribute :>> reportNumber = "STS-120-V-02"; attribute :>> flight = "STS-120"; attribute :>> subsystem = "PLS"; attribute :>> causeState = "調査中"; attribute :>> actionClass = "部品交換"; attribute :>> phase = "PH-3"; }
        occurrence <'IFA-211'> ifa_211 : InFlightAnomaly { doc /* STS-120-V-03 RMS による OBSS の把持位置が期待からずれた */ attribute :>> reportNumber = "STS-120-V-03"; attribute :>> flight = "STS-120"; attribute :>> subsystem = "PLS"; attribute :>> causeState = "特定"; attribute :>> actionClass = "再点検・再試験"; attribute :>> phase = "PH-3"; }
        occurrence <'IFA-212'> ifa_212 : InFlightAnomaly { doc /* STS-120-V-04 主系 WLES の PGSC モニタが表示されない */ attribute :>> reportNumber = "STS-120-V-04"; attribute :>> flight = "STS-120"; attribute :>> subsystem = "OTHER"; attribute :>> causeState = "記載なし"; attribute :>> actionClass = "記載なし"; attribute :>> phase = "PH-3"; }
        occurrence <'IFA-213'> ifa_213 : InFlightAnomaly { doc /* STS-120-V-05 TPS のタイル・ブランケットの異常 */ attribute :>> reportNumber = "STS-120-V-05"; attribute :>> flight = "STS-120"; attribute :>> subsystem = "TPS"; attribute :>> causeState = "記載なし"; attribute :>> actionClass = "許容・そのまま飛行"; attribute :>> phase = "PH-3"; }
        occurrence <'IFA-214'> ifa_214 : InFlightAnomaly { doc /* STS-120-V-06 非常用水容器（CWC）の漏れ */ attribute :>> reportNumber = "STS-120-V-06"; attribute :>> flight = "STS-120"; attribute :>> subsystem = "ECLSS"; attribute :>> causeState = "記載なし"; attribute :>> actionClass = "記載なし"; attribute :>> phase = "PH-3"; }
        occurrence <'IFA-215'> ifa_215 : InFlightAnomaly { doc /* STS-120-V-07 ペイロードベイの投光器 3 番の故障 */ attribute :>> reportNumber = "STS-120-V-07"; attribute :>> flight = "STS-120"; attribute :>> subsystem = "CREW"; attribute :>> causeState = "特定"; attribute :>> actionClass = "部品交換"; attribute :>> phase = "PH-5"; }
        occurrence <'IFA-216'> ifa_216 : InFlightAnomaly { doc /* STS-120-V-08 廃水ノズルの温度センサ B が不安定 */ attribute :>> reportNumber = "STS-120-V-08"; attribute :>> flight = "STS-120"; attribute :>> subsystem = "ECLSS"; attribute :>> causeState = "特定"; attribute :>> actionClass = "部品交換"; attribute :>> phase = "PH-3"; }
        occurrence <'IFA-217'> ifa_217 : InFlightAnomaly { doc /* STS-120-V-09 左側のオービタ後部胴体のガスサンプラーが大気を採取しなかった */ attribute :>> reportNumber = "STS-120-V-09"; attribute :>> flight = "STS-120"; attribute :>> subsystem = "OTHER"; attribute :>> causeState = "特定"; attribute :>> actionClass = "部品交換"; attribute :>> phase = "PH-7"; }
        occurrence <'IFA-218'> ifa_218 : InFlightAnomaly { doc /* STS-120-V-10 デジタルカメラ（S/N 1013・1014）の故障 */ attribute :>> reportNumber = "STS-120-V-10"; attribute :>> flight = "STS-120"; attribute :>> subsystem = "OTHER"; attribute :>> causeState = "推定"; attribute :>> actionClass = "手順・規則の変更"; attribute :>> phase = "PH-5"; }
        occurrence <'IFA-219'> ifa_219 : InFlightAnomaly { doc /* STS-120-V-11 足部拘束具（FRED）の組立てが分解 */ attribute :>> reportNumber = "STS-120-V-11"; attribute :>> flight = "STS-120"; attribute :>> subsystem = "EVA"; attribute :>> causeState = "特定"; attribute :>> actionClass = "設計変更"; attribute :>> phase = "PH-7"; }
        occurrence <'IFA-220'> ifa_220 : InFlightAnomaly { doc /* STS-121-V-01 バーニア・スラスタ L5L のヒータが「切」のまま故障 */ attribute :>> reportNumber = "STS-121-V-01"; attribute :>> flight = "STS-121"; attribute :>> subsystem = "RCS"; attribute :>> causeState = "特定"; attribute :>> actionClass = "部品交換"; attribute :>> phase = "PH-1"; }
        occurrence <'IFA-221'> ifa_221 : InFlightAnomaly { doc /* STS-121-V-02 個人衛生ホース（PHH）の漏れ */ attribute :>> reportNumber = "STS-121-V-02"; attribute :>> flight = "STS-121"; attribute :>> subsystem = "CREW"; attribute :>> causeState = "推定"; attribute :>> actionClass = "部品交換"; attribute :>> phase = "PH-3"; }
        occurrence <'IFA-222'> ifa_222 : InFlightAnomaly { doc /* STS-121-V-03 手持ち LIDAR（HHL）のケーブルの故障 */ attribute :>> reportNumber = "STS-121-V-03"; attribute :>> flight = "STS-121"; attribute :>> subsystem = "OTHER"; attribute :>> causeState = "不明"; attribute :>> actionClass = "部品交換"; attribute :>> phase = "PH-3"; }
        occurrence <'IFA-223'> ifa_223 : InFlightAnomaly { doc /* STS-121-V-04 下面の突出したギャップフィラ3か所 */ attribute :>> reportNumber = "STS-121-V-04"; attribute :>> flight = "STS-121"; attribute :>> subsystem = "TPS"; attribute :>> causeState = "記載なし"; attribute :>> actionClass = "許容・そのまま飛行"; attribute :>> phase = "PH-3"; }
        occurrence <'IFA-224'> ifa_224 : InFlightAnomaly { doc /* STS-121-V-05 TPS ブランケットの浮き・損傷 */ attribute :>> reportNumber = "STS-121-V-05"; attribute :>> flight = "STS-121"; attribute :>> subsystem = "TPS"; attribute :>> causeState = "記載なし"; attribute :>> actionClass = "設計変更"; attribute :>> phase = "PH-3"; }
        occurrence <'IFA-225'> ifa_225 : InFlightAnomaly { doc /* STS-121-V-06 翼前縁衝撃検知システム（WLE IDS）のセンサ 1009 の通信不能 */ attribute :>> reportNumber = "STS-121-V-06"; attribute :>> flight = "STS-121"; attribute :>> subsystem = "STR"; attribute :>> causeState = "推定"; attribute :>> actionClass = "部品交換"; attribute :>> phase = "PH-3"; }
        occurrence <'IFA-226'> ifa_226 : InFlightAnomaly { doc /* STS-121-V-07 CCTV カメラ D の赤紫色の色かぶり */ attribute :>> reportNumber = "STS-121-V-07"; attribute :>> flight = "STS-121"; attribute :>> subsystem = "CT"; attribute :>> causeState = "記載なし"; attribute :>> actionClass = "再点検・再試験"; attribute :>> phase = "PH-3"; }
        occurrence <'IFA-227'> ifa_227 : InFlightAnomaly { doc /* STS-121-V-08 APU 1 の燃料タンク圧の原因不明の低下 */ attribute :>> reportNumber = "STS-121-V-08"; attribute :>> flight = "STS-121"; attribute :>> subsystem = "APU"; attribute :>> causeState = "推定"; attribute :>> actionClass = "再点検・再試験"; attribute :>> phase = "PH-3"; }
        occurrence <'IFA-228'> ifa_228 : InFlightAnomaly { doc /* STS-121-V-09 APU 3 の GG 燃料ライン・ポンプ・弁の温度が一次サーモスタットで制御されない */ attribute :>> reportNumber = "STS-121-V-09"; attribute :>> flight = "STS-121"; attribute :>> subsystem = "APU"; attribute :>> causeState = "特定"; attribute :>> actionClass = "再点検・再試験"; attribute :>> phase = "PH-3"; }
        occurrence <'IFA-229'> ifa_229 : InFlightAnomaly { doc /* STS-121-V-10 MADS 前部胴体ベント扉の圧力がスケールオーバー（高） */ attribute :>> reportNumber = "STS-121-V-10"; attribute :>> flight = "STS-121"; attribute :>> subsystem = "OTHER"; attribute :>> causeState = "記載なし"; attribute :>> actionClass = "次便で対処"; attribute :>> phase = "PH-2"; }
        occurrence <'IFA-230'> ifa_230 : InFlightAnomaly { doc /* STS-121-V-11 MADS の Xo376 隔壁の差圧の過大 */ attribute :>> reportNumber = "STS-121-V-11"; attribute :>> flight = "STS-121"; attribute :>> subsystem = "STR"; attribute :>> causeState = "特定"; attribute :>> actionClass = "部品交換"; attribute :>> phase = "PH-2"; }
        occurrence <'IFA-231'> ifa_231 : InFlightAnomaly { doc /* STS-121-V-12 エンジン3の LH2 入口圧トランスデューサの異常 */ attribute :>> reportNumber = "STS-121-V-12"; attribute :>> flight = "STS-121"; attribute :>> subsystem = "MPS"; attribute :>> causeState = "推定"; attribute :>> actionClass = "部品交換"; attribute :>> phase = "PH-2"; }
        occurrence <'IFA-232'> ifa_232 : InFlightAnomaly { doc /* STS-121-V-13 エアロック／ヴェスティビュールの差圧トランスデューサが低く漂う */ attribute :>> reportNumber = "STS-121-V-13"; attribute :>> flight = "STS-121"; attribute :>> subsystem = "EVA"; attribute :>> causeState = "不明"; attribute :>> actionClass = "部品交換"; attribute :>> phase = "PH-3"; }
        occurrence <'IFA-233'> ifa_233 : InFlightAnomaly { doc /* STS-121-V-14 FES の Primary B フルアップでの停止 */ attribute :>> reportNumber = "STS-121-V-14"; attribute :>> flight = "STS-121"; attribute :>> subsystem = "ECLSS"; attribute :>> causeState = "不明"; attribute :>> actionClass = "再点検・再試験"; attribute :>> phase = "PH-3"; }
        occurrence <'IFA-234'> ifa_234 : InFlightAnomaly { doc /* STS-121-V-15 右エアデータプローブの初回展開の失敗 */ attribute :>> reportNumber = "STS-121-V-15"; attribute :>> flight = "STS-121"; attribute :>> subsystem = "GNC"; attribute :>> causeState = "特定"; attribute :>> actionClass = "記載なし"; attribute :>> phase = "PH-6"; }
        occurrence <'IFA-235'> ifa_235 : InFlightAnomaly { doc /* STS-121-V-16 WLE IDS のソフトウェアの不用意な停止 */ attribute :>> reportNumber = "STS-121-V-16"; attribute :>> flight = "STS-121"; attribute :>> subsystem = "STR"; attribute :>> causeState = "推定"; attribute :>> actionClass = "記載なし"; attribute :>> phase = "PH-3"; }
        occurrence <'IFA-236'> ifa_236 : InFlightAnomaly { doc /* STS-121-V-17 WSB 3 排気ダクトのブランケットの汚れ */ attribute :>> reportNumber = "STS-121-V-17"; attribute :>> flight = "STS-121"; attribute :>> subsystem = "APU"; attribute :>> causeState = "調査中"; attribute :>> actionClass = "再点検・再試験"; attribute :>> phase = "PH-7"; }
        occurrence <'IFA-237'> ifa_237 : InFlightAnomaly { doc /* STS-121-V-18 MADS 胴体左側の表面圧がスケールオーバー（低） */ attribute :>> reportNumber = "STS-121-V-18"; attribute :>> flight = "STS-121"; attribute :>> subsystem = "OTHER"; attribute :>> causeState = "記載なし"; attribute :>> actionClass = "許容・そのまま飛行"; attribute :>> phase = "PH-6"; }
        occurrence <'IFA-238'> ifa_238 : InFlightAnomaly { doc /* STS-121-V-19 TPS のパテ補修の欠落 */ attribute :>> reportNumber = "STS-121-V-19"; attribute :>> flight = "STS-121"; attribute :>> subsystem = "TPS"; attribute :>> causeState = "特定"; attribute :>> actionClass = "記載なし"; attribute :>> phase = "PH-7"; }
        occurrence <'IFA-239'> ifa_239 : InFlightAnomaly { doc /* STS-121-V-20 左外側キャリアパネルのコロポンの変色 */ attribute :>> reportNumber = "STS-121-V-20"; attribute :>> flight = "STS-121"; attribute :>> subsystem = "TPS"; attribute :>> causeState = "特定"; attribute :>> actionClass = "部品交換"; attribute :>> phase = "PH-7"; }
        occurrence <'IFA-240'> ifa_240 : InFlightAnomaly { doc /* STS-122-V-01 TPS のタイル・ブランケットの異常 */ attribute :>> reportNumber = "STS-122-V-01"; attribute :>> flight = "STS-122"; attribute :>> subsystem = "TPS"; attribute :>> causeState = "記載なし"; attribute :>> actionClass = "許容・そのまま飛行"; attribute :>> phase = "PH-3"; }
        occurrence <'IFA-241'> ifa_241 : InFlightAnomaly { doc /* STS-122-V-02 APU 3 のドレン配管ヒータのサイクルが異常 */ attribute :>> reportNumber = "STS-122-V-02"; attribute :>> flight = "STS-122"; attribute :>> subsystem = "APU"; attribute :>> causeState = "推定"; attribute :>> actionClass = "部品交換"; attribute :>> phase = "PH-3"; }
        occurrence <'IFA-242'> ifa_242 : InFlightAnomaly { doc /* STS-122-V-03 AVIU のビデオが露出過多 */ attribute :>> reportNumber = "STS-122-V-03"; attribute :>> flight = "STS-122"; attribute :>> subsystem = "CT"; attribute :>> causeState = "不明"; attribute :>> actionClass = "部品交換"; attribute :>> phase = "PH-3"; }
        occurrence <'IFA-243'> ifa_243 : InFlightAnomaly { doc /* STS-122-V-04 燃料電池 3 の O2 流量計が不安定 */ attribute :>> reportNumber = "STS-122-V-04"; attribute :>> flight = "STS-122"; attribute :>> subsystem = "EPS"; attribute :>> causeState = "記載なし"; attribute :>> actionClass = "許容・そのまま飛行"; attribute :>> phase = "PH-3"; }
        occurrence <'IFA-244'> ifa_244 : InFlightAnomaly { doc /* STS-122-V-05 CCTV の白黒映像に色が出る */ attribute :>> reportNumber = "STS-122-V-05"; attribute :>> flight = "STS-122"; attribute :>> subsystem = "CT"; attribute :>> causeState = "特定"; attribute :>> actionClass = "許容・そのまま飛行"; attribute :>> phase = "PH-3"; }
        occurrence <'IFA-245'> ifa_245 : InFlightAnomaly { doc /* STS-122-V-06 後部バーニアのヒータが故障 */ attribute :>> reportNumber = "STS-122-V-06"; attribute :>> flight = "STS-122"; attribute :>> subsystem = "RCS"; attribute :>> causeState = "特定"; attribute :>> actionClass = "部品交換"; attribute :>> phase = "PH-3"; }
        occurrence <'IFA-246'> ifa_246 : InFlightAnomaly { doc /* STS-122-V-07 左舷後部 MPM の収納表示が遅れた */ attribute :>> reportNumber = "STS-122-V-07"; attribute :>> flight = "STS-122"; attribute :>> subsystem = "PLS"; attribute :>> causeState = "記載なし"; attribute :>> actionClass = "許容・そのまま飛行"; attribute :>> phase = "PH-4"; }
        occurrence <'IFA-247'> ifa_247 : InFlightAnomaly { doc /* STS-122-V-08 ミッドポートのペイロードベイ投光器が点かない */ attribute :>> reportNumber = "STS-122-V-08"; attribute :>> flight = "STS-122"; attribute :>> subsystem = "CREW"; attribute :>> causeState = "特定"; attribute :>> actionClass = "部品交換"; attribute :>> phase = "PH-3"; }
        occurrence <'IFA-248'> ifa_248 : InFlightAnomaly { doc /* STS-122-V-09 SSOR 1 の通信が断続的に切れた */ attribute :>> reportNumber = "STS-122-V-09"; attribute :>> flight = "STS-122"; attribute :>> subsystem = "CT"; attribute :>> causeState = "不明"; attribute :>> actionClass = "許容・そのまま飛行"; attribute :>> phase = "PH-3"; }
        occurrence <'IFA-249'> ifa_249 : InFlightAnomaly { doc /* STS-123-V-01 DSC-OL1 のカード1の故障で RCS 噴射器の温度計測4点が最低値側に振り切れ */ attribute :>> reportNumber = "STS-123-V-01"; attribute :>> flight = "STS-123"; attribute :>> subsystem = "CT"; attribute :>> causeState = "推定"; attribute :>> actionClass = "部品交換"; attribute :>> phase = "PH-2"; }
        occurrence <'IFA-250'> ifa_250 : InFlightAnomaly { doc /* STS-123-V-02 FES が主制御器 A で停止 */ attribute :>> reportNumber = "STS-123-V-02"; attribute :>> flight = "STS-123"; attribute :>> subsystem = "ECLSS"; attribute :>> causeState = "特定"; attribute :>> actionClass = "部品交換"; attribute :>> phase = "PH-2"; }
        occurrence <'IFA-251'> ifa_251 : InFlightAnomaly { doc /* STS-123-V-03 APU 1 のガス発生器チャンバ圧の変換器の値が上方へずれる */ attribute :>> reportNumber = "STS-123-V-03"; attribute :>> flight = "STS-123"; attribute :>> subsystem = "APU"; attribute :>> causeState = "推定"; attribute :>> actionClass = "許容・そのまま飛行"; attribute :>> phase = "PH-2"; }
        occurrence <'IFA-252'> ifa_252 : InFlightAnomaly { doc /* STS-123-V-04 APU 3 のシールキャビティ・ドレンラインの圧力の低下 */ attribute :>> reportNumber = "STS-123-V-04"; attribute :>> flight = "STS-123"; attribute :>> subsystem = "APU"; attribute :>> causeState = "推定"; attribute :>> actionClass = "再点検・再試験"; attribute :>> phase = "PH-3"; }
        occurrence <'IFA-253'> ifa_253 : InFlightAnomaly { doc /* STS-123-V-05 APU 1 の燃料タンク圧の低下 */ attribute :>> reportNumber = "STS-123-V-05"; attribute :>> flight = "STS-123"; attribute :>> subsystem = "APU"; attribute :>> causeState = "不明"; attribute :>> actionClass = "再点検・再試験"; attribute :>> phase = "PH-3"; }
        occurrence <'IFA-254'> ifa_254 : InFlightAnomaly { doc /* STS-123-V-06 SSME 3 の LO2 入口圧の計測値のずれ */ attribute :>> reportNumber = "STS-123-V-06"; attribute :>> flight = "STS-123"; attribute :>> subsystem = "MPS"; attribute :>> causeState = "不明"; attribute :>> actionClass = "部品交換"; attribute :>> phase = "PH-2"; }
        occurrence <'IFA-255'> ifa_255 : InFlightAnomaly { doc /* STS-123-V-07 TPS の損傷20件の評価（OMS ポッドのスティンガ上のタイル欠けほか） */ attribute :>> reportNumber = "STS-123-V-07"; attribute :>> flight = "STS-123"; attribute :>> subsystem = "TPS"; attribute :>> causeState = "記載なし"; attribute :>> actionClass = "許容・そのまま飛行"; attribute :>> phase = "PH-3"; }
        occurrence <'IFA-256'> ifa_256 : InFlightAnomaly { doc /* STS-123-V-08 MADS の PCM 計測3件（OMS ポッドの熱電対）の故障 */ attribute :>> reportNumber = "STS-123-V-08"; attribute :>> flight = "STS-123"; attribute :>> subsystem = "OTHER"; attribute :>> causeState = "記載なし"; attribute :>> actionClass = "部品交換"; attribute :>> phase = "PH-2"; }
        occurrence <'IFA-257'> ifa_257 : InFlightAnomaly { doc /* STS-123-V-09 OBSS の PTU のパンが +10 度ずれ（ハードストップの誤り） */ attribute :>> reportNumber = "STS-123-V-09"; attribute :>> flight = "STS-123"; attribute :>> subsystem = "OTHER"; attribute :>> causeState = "推定"; attribute :>> actionClass = "手順・規則の変更"; attribute :>> phase = "PH-3"; }
        occurrence <'IFA-258'> ifa_258 : InFlightAnomaly { doc /* STS-123-V-10 WLE 衝撃検知システムのセンサ S/N 1150 の異常データ（メモリの飽和） */ attribute :>> reportNumber = "STS-123-V-10"; attribute :>> flight = "STS-123"; attribute :>> subsystem = "STR"; attribute :>> causeState = "推定"; attribute :>> actionClass = "手順・規則の変更"; attribute :>> phase = "PH-3"; }
        occurrence <'IFA-259'> ifa_259 : InFlightAnomaly { doc /* STS-123-V-11 後部パネル A4 の MET・GMT ミッションタイマの故障 */ attribute :>> reportNumber = "STS-123-V-11"; attribute :>> flight = "STS-123"; attribute :>> subsystem = "DPS"; attribute :>> causeState = "特定"; attribute :>> actionClass = "部品交換"; attribute :>> phase = "PH-3"; }
        occurrence <'IFA-260'> ifa_260 : InFlightAnomaly { doc /* STS-123-V-12 パネル O6 の GPC 3 OUTPUT トークバックの固着 */ attribute :>> reportNumber = "STS-123-V-12"; attribute :>> flight = "STS-123"; attribute :>> subsystem = "DPS"; attribute :>> causeState = "不明"; attribute :>> actionClass = "手順・規則の変更"; attribute :>> phase = "PH-3"; }
        occurrence <'IFA-261'> ifa_261 : InFlightAnomaly { doc /* STS-123-V-13 燃料電池共通の水ラインの pH センサの断続的な指示 */ attribute :>> reportNumber = "STS-123-V-13"; attribute :>> flight = "STS-123"; attribute :>> subsystem = "ECLSS"; attribute :>> causeState = "調査中"; attribute :>> actionClass = "部品交換"; attribute :>> phase = "PH-3"; }
        occurrence <'IFA-262'> ifa_262 : InFlightAnomaly { doc /* STS-123-V-14 キャビン温度コントローラ 1 の作動音 */ attribute :>> reportNumber = "STS-123-V-14"; attribute :>> flight = "STS-123"; attribute :>> subsystem = "ECLSS"; attribute :>> causeState = "不明"; attribute :>> actionClass = "再点検・再試験"; attribute :>> phase = "PH-3"; }
        occurrence <'IFA-263'> ifa_263 : InFlightAnomaly { doc /* STS-123-V-15 放熱器の格納側フレキシブルホースの異常な曲がり */ attribute :>> reportNumber = "STS-123-V-15"; attribute :>> flight = "STS-123"; attribute :>> subsystem = "ECLSS"; attribute :>> causeState = "推定"; attribute :>> actionClass = "再点検・再試験"; attribute :>> phase = "PH-7"; }
        occurrence <'IFA-264'> ifa_264 : InFlightAnomaly { doc /* STS-123-V-16 ACES の手袋の内袋の裂け */ attribute :>> reportNumber = "STS-123-V-16"; attribute :>> flight = "STS-123"; attribute :>> subsystem = "CREW"; attribute :>> causeState = "調査中"; attribute :>> actionClass = "手順・規則の変更"; attribute :>> phase = "PH-7"; }
        occurrence <'IFA-265'> ifa_265 : InFlightAnomaly { doc /* STS-124-V-01 左 OMS の二次のピッチ・ヨー位置指示の故障 */ attribute :>> reportNumber = "STS-124-V-01"; attribute :>> flight = "STS-124"; attribute :>> subsystem = "OMS"; attribute :>> causeState = "不明"; attribute :>> actionClass = "部品交換"; attribute :>> phase = "PH-2"; }
        occurrence <'IFA-266'> ifa_266 : InFlightAnomaly { doc /* STS-124-V-02 TPS の損傷13件の評価（追加の解析が必要だった4件） */ attribute :>> reportNumber = "STS-124-V-02"; attribute :>> flight = "STS-124"; attribute :>> subsystem = "TPS"; attribute :>> causeState = "記載なし"; attribute :>> actionClass = "許容・そのまま飛行"; attribute :>> phase = "PH-3"; }
        occurrence <'IFA-267'> ifa_267 : InFlightAnomaly { doc /* STS-124-V-03 レーザカメラシステム（LCS）のスキャン中止 */ attribute :>> reportNumber = "STS-124-V-03"; attribute :>> flight = "STS-124"; attribute :>> subsystem = "OTHER"; attribute :>> causeState = "特定"; attribute :>> actionClass = "部品交換"; attribute :>> phase = "PH-3"; }
        occurrence <'IFA-268'> ifa_268 : InFlightAnomaly { doc /* STS-124-V-04 EV2 の通信キャップ（CCA）の音声劣化 */ attribute :>> reportNumber = "STS-124-V-04"; attribute :>> flight = "STS-124"; attribute :>> subsystem = "EVA"; attribute :>> causeState = "記載なし"; attribute :>> actionClass = "部品交換"; attribute :>> phase = "PH-5"; }
        occurrence <'IFA-269'> ifa_269 : InFlightAnomaly { doc /* STS-124-V-05 RCS の Tyvek カバーの一部が遅れて離脱 */ attribute :>> reportNumber = "STS-124-V-05"; attribute :>> flight = "STS-124"; attribute :>> subsystem = "RCS"; attribute :>> causeState = "記載なし"; attribute :>> actionClass = "許容・そのまま飛行"; attribute :>> phase = "PH-2"; }
        occurrence <'IFA-270'> ifa_270 : InFlightAnomaly { doc /* STS-124-V-06 燃料電池 3 の CPM と水素流量計の計測の喪失 */ attribute :>> reportNumber = "STS-124-V-06"; attribute :>> flight = "STS-124"; attribute :>> subsystem = "EPS"; attribute :>> causeState = "特定"; attribute :>> actionClass = "再点検・再試験"; attribute :>> phase = "PH-3"; }
        occurrence <'IFA-271'> ifa_271 : InFlightAnomaly { doc /* STS-124-V-07 ハンドヘルドマイクの断続的な送信不良 */ attribute :>> reportNumber = "STS-124-V-07"; attribute :>> flight = "STS-124"; attribute :>> subsystem = "CT"; attribute :>> causeState = "特定"; attribute :>> actionClass = "部品交換"; attribute :>> phase = "PH-3"; }
        occurrence <'IFA-272'> ifa_272 : InFlightAnomaly { doc /* STS-124-V-08 打上げ前の通信キャリア組立（CCA）の音量低下 */ attribute :>> reportNumber = "STS-124-V-08"; attribute :>> flight = "STS-124"; attribute :>> subsystem = "CT"; attribute :>> causeState = "不明"; attribute :>> actionClass = "許容・そのまま飛行"; attribute :>> phase = "PH-1"; }
        occurrence <'IFA-273'> ifa_273 : InFlightAnomaly { doc /* STS-124-V-09 IMU 1 の Z ジャイロの過大なドリフト */ attribute :>> reportNumber = "STS-124-V-09"; attribute :>> flight = "STS-124"; attribute :>> subsystem = "GNC"; attribute :>> causeState = "記載なし"; attribute :>> actionClass = "部品交換"; attribute :>> phase = "PH-3"; }
        occurrence <'IFA-274'> ifa_274 : InFlightAnomaly { doc /* STS-124-V-10 ランデブ中の TCS の追尾喪失 */ attribute :>> reportNumber = "STS-124-V-10"; attribute :>> flight = "STS-124"; attribute :>> subsystem = "GNC"; attribute :>> causeState = "推定"; attribute :>> actionClass = "再点検・再試験"; attribute :>> phase = "PH-3"; }
        occurrence <'IFA-275'> ifa_275 : InFlightAnomaly { doc /* STS-124-V-11 ラダー・スピードブレーキの熱クリップの破片の離脱 */ attribute :>> reportNumber = "STS-124-V-11"; attribute :>> flight = "STS-124"; attribute :>> subsystem = "STR"; attribute :>> causeState = "特定"; attribute :>> actionClass = "部品交換"; attribute :>> phase = "PH-4"; }
        occurrence <'IFA-276'> ifa_276 : InFlightAnomaly { doc /* STS-124-V-12 Y スタートラッカのドア SYS 2 の CLOSED 表示が出ない */ attribute :>> reportNumber = "STS-124-V-12"; attribute :>> flight = "STS-124"; attribute :>> subsystem = "GNC"; attribute :>> causeState = "特定"; attribute :>> actionClass = "部品交換"; attribute :>> phase = "PH-3"; }
        occurrence <'IFA-277'> ifa_277 : InFlightAnomaly { doc /* STS-124-V-13 APU 3 の水ラインのサーモスタットの細かい振動（ディザ） */ attribute :>> reportNumber = "STS-124-V-13"; attribute :>> flight = "STS-124"; attribute :>> subsystem = "APU"; attribute :>> causeState = "記載なし"; attribute :>> actionClass = "部品交換"; attribute :>> phase = "PH-3"; }
        occurrence <'IFA-278'> ifa_278 : InFlightAnomaly { doc /* STS-124-V-14 外部エアロックの上部ハッチのラッチ操作の困難 */ attribute :>> reportNumber = "STS-124-V-14"; attribute :>> flight = "STS-124"; attribute :>> subsystem = "PLS"; attribute :>> causeState = "特定"; attribute :>> actionClass = "記載なし"; attribute :>> phase = "PH-3"; }
        occurrence <'IFA-279'> ifa_279 : InFlightAnomaly { doc /* STS-124-V-15 右翼前縁の T シール（リブ継手 10）の過大な Type A フロー */ attribute :>> reportNumber = "STS-124-V-15"; attribute :>> flight = "STS-124"; attribute :>> subsystem = "TPS"; attribute :>> causeState = "推定"; attribute :>> actionClass = "設計変更"; attribute :>> phase = "PH-6"; }
        occurrence <'IFA-280'> ifa_280 : InFlightAnomaly { doc /* STS-125-V-01 SSME 2 の GH2 出口圧力トランスデューサの値が不安定 */ attribute :>> reportNumber = "STS-125-V-01"; attribute :>> flight = "STS-125"; attribute :>> subsystem = "MPS"; attribute :>> causeState = "特定"; attribute :>> actionClass = "部品交換"; attribute :>> phase = "PH-2"; }
        occurrence <'IFA-281'> ifa_281 : InFlightAnomaly { doc /* STS-125-V-02 エアロサーフェス・アクチュエータ組立（ASA）1 の電源の故障 */ attribute :>> reportNumber = "STS-125-V-02"; attribute :>> flight = "STS-125"; attribute :>> subsystem = "GNC"; attribute :>> causeState = "特定"; attribute :>> actionClass = "再点検・再試験"; attribute :>> phase = "PH-2"; }
        occurrence <'IFA-282'> ifa_282 : InFlightAnomaly { doc /* STS-125-V-03 前方右舷のペイロードベイ投光灯の故障 */ attribute :>> reportNumber = "STS-125-V-03"; attribute :>> flight = "STS-125"; attribute :>> subsystem = "CREW"; attribute :>> causeState = "特定"; attribute :>> actionClass = "部品交換"; attribute :>> phase = "PH-3"; }
        occurrence <'IFA-283'> ifa_283 : InFlightAnomaly { doc /* STS-125-V-04 前方左舷のペイロードベイ投光灯の故障 */ attribute :>> reportNumber = "STS-125-V-04"; attribute :>> flight = "STS-125"; attribute :>> subsystem = "CREW"; attribute :>> causeState = "特定"; attribute :>> actionClass = "部品交換"; attribute :>> phase = "PH-3"; }
        occurrence <'IFA-284'> ifa_284 : InFlightAnomaly { doc /* STS-125-V-05 翼前縁衝撃検知システム（WLEIDS）のセンサ S/N 1092 の通信タイムアウト */ attribute :>> reportNumber = "STS-125-V-05"; attribute :>> flight = "STS-125"; attribute :>> subsystem = "STR"; attribute :>> causeState = "不明"; attribute :>> actionClass = "再点検・再試験"; attribute :>> phase = "PH-3"; }
        occurrence <'IFA-285'> ifa_285 : InFlightAnomaly { doc /* STS-125-V-06 給水ダンプ配管のパージ装置の故障 */ attribute :>> reportNumber = "STS-125-V-06"; attribute :>> flight = "STS-125"; attribute :>> subsystem = "ECLSS"; attribute :>> causeState = "推定"; attribute :>> actionClass = "手順・規則の変更"; attribute :>> phase = "PH-3"; }
        occurrence <'IFA-286'> ifa_286 : InFlightAnomaly { doc /* STS-125-V-07 バーニア・スラスタ R5R の燃焼室圧力の指示が低い */ attribute :>> reportNumber = "STS-125-V-07"; attribute :>> flight = "STS-125"; attribute :>> subsystem = "RCS"; attribute :>> causeState = "推定"; attribute :>> actionClass = "許容・そのまま飛行"; attribute :>> phase = "PH-3"; }
        occurrence <'IFA-287'> ifa_287 : InFlightAnomaly { doc /* STS-125-V-08 上昇中の室内ミニカメラの映像の断続・録画なし */ attribute :>> reportNumber = "STS-125-V-08"; attribute :>> flight = "STS-125"; attribute :>> subsystem = "CT"; attribute :>> causeState = "特定"; attribute :>> actionClass = "部品交換"; attribute :>> phase = "PH-2"; }
        occurrence <'IFA-288'> ifa_288 : InFlightAnomaly { doc /* STS-125-V-09 湿度分離器の水の持ち越し */ attribute :>> reportNumber = "STS-125-V-09"; attribute :>> flight = "STS-125"; attribute :>> subsystem = "ECLSS"; attribute :>> causeState = "推定"; attribute :>> actionClass = "手順・規則の変更"; attribute :>> phase = "PH-3"; }
        occurrence <'IFA-289'> ifa_289 : InFlightAnomaly { doc /* STS-125-V-10 MEDS の IDP 4 の MSU の BITE 故障 */ attribute :>> reportNumber = "STS-125-V-10"; attribute :>> flight = "STS-125"; attribute :>> subsystem = "DPS"; attribute :>> causeState = "推定"; attribute :>> actionClass = "部品交換"; attribute :>> phase = "PH-3"; }
        occurrence <'IFA-290'> ifa_290 : InFlightAnomaly { doc /* STS-125-V-11 S 帯の右下クワッドアンテナのフォワードリンクの断続的な途切れ */ attribute :>> reportNumber = "STS-125-V-11"; attribute :>> flight = "STS-125"; attribute :>> subsystem = "CT"; attribute :>> causeState = "特定"; attribute :>> actionClass = "部品交換"; attribute :>> phase = "PH-3"; }
        occurrence <'IFA-291'> ifa_291 : InFlightAnomaly { doc /* STS-125-V-12 フレオン冷却ループ 1 の放熱器が Auto A でバイパスにトリップ */ attribute :>> reportNumber = "STS-125-V-12"; attribute :>> flight = "STS-125"; attribute :>> subsystem = "ECLSS"; attribute :>> causeState = "推定"; attribute :>> actionClass = "部品交換"; attribute :>> phase = "PH-4"; }
        occurrence <'IFA-292'> ifa_292 : InFlightAnomaly { doc /* STS-125-V-13 IMU ファンの差圧の原因不明の上昇 */ attribute :>> reportNumber = "STS-125-V-13"; attribute :>> flight = "STS-125"; attribute :>> subsystem = "ECLSS"; attribute :>> causeState = "特定"; attribute :>> actionClass = "許容・そのまま飛行"; attribute :>> phase = "PH-3"; }
        occurrence <'IFA-293'> ifa_293 : InFlightAnomaly { doc /* STS-125-V-14 TPS のタイルの異常（右舷チャインのタイル損傷と左 OMS ポッドのギャップフィラの脱落） */ attribute :>> reportNumber = "STS-125-V-14"; attribute :>> flight = "STS-125"; attribute :>> subsystem = "TPS"; attribute :>> causeState = "特定"; attribute :>> actionClass = "許容・そのまま飛行"; attribute :>> phase = "PH-2"; }
        occurrence <'IFA-294'> ifa_294 : InFlightAnomaly { doc /* STS-125-V-15 脱出用無線機の電池の電圧低下 */ attribute :>> reportNumber = "STS-125-V-15"; attribute :>> flight = "STS-125"; attribute :>> subsystem = "CREW"; attribute :>> causeState = "推定"; attribute :>> actionClass = "記載なし"; attribute :>> phase = "PH-7"; }
        occurrence <'IFA-295'> ifa_295 : InFlightAnomaly { doc /* STS-125-V-16 MEDS の MDU 4 の一過性の通信故障 */ attribute :>> reportNumber = "STS-125-V-16"; attribute :>> flight = "STS-125"; attribute :>> subsystem = "DPS"; attribute :>> causeState = "推定"; attribute :>> actionClass = "再点検・再試験"; attribute :>> phase = "PH-6"; }
        occurrence <'IFA-296'> ifa_296 : InFlightAnomaly { doc /* STS-125-V-17 窓 5 の異物（ワーク・ランプの取付けノブ） */ attribute :>> reportNumber = "STS-125-V-17"; attribute :>> flight = "STS-125"; attribute :>> subsystem = "STR"; attribute :>> causeState = "特定"; attribute :>> actionClass = "許容・そのまま飛行"; attribute :>> phase = "PH-7"; }
        occurrence <'IFA-297'> ifa_297 : InFlightAnomaly { doc /* STS-126-V-01 TPS のタイルとブランケットの異常（13件が基準を超えた） */ attribute :>> reportNumber = "STS-126-V-01"; attribute :>> flight = "STS-126"; attribute :>> subsystem = "TPS"; attribute :>> causeState = "記載なし"; attribute :>> actionClass = "部品交換"; attribute :>> phase = "PH-3"; }
        occurrence <'IFA-298'> ifa_298 : InFlightAnomaly { doc /* STS-126-V-02 APU 3 の Z 軸加速度計の出力が不安定 */ attribute :>> reportNumber = "STS-126-V-02"; attribute :>> flight = "STS-126"; attribute :>> subsystem = "APU"; attribute :>> causeState = "特定"; attribute :>> actionClass = "部品交換"; attribute :>> phase = "PH-2"; }
        occurrence <'IFA-299'> ifa_299 : InFlightAnomaly { doc /* STS-126-V-03 Ku 帯が COMM モードで追尾を維持できない */ attribute :>> reportNumber = "STS-126-V-03"; attribute :>> flight = "STS-126"; attribute :>> subsystem = "CT"; attribute :>> causeState = "調査中"; attribute :>> actionClass = "再点検・再試験"; attribute :>> phase = "PH-3"; }
        occurrence <'IFA-300'> ifa_300 : InFlightAnomaly { doc /* STS-126-V-04 WLE センサユニット 1163 の増幅 Grms の読みが他の約7倍 */ attribute :>> reportNumber = "STS-126-V-04"; attribute :>> flight = "STS-126"; attribute :>> subsystem = "TPS"; attribute :>> causeState = "特定"; attribute :>> actionClass = "手順・規則の変更"; attribute :>> phase = "PH-3"; }
        occurrence <'IFA-301'> ifa_301 : InFlightAnomaly { doc /* STS-126-V-05 OMS 右の酸化剤クロスフィード排出管ヒータ A が停止 */ attribute :>> reportNumber = "STS-126-V-05"; attribute :>> flight = "STS-126"; attribute :>> subsystem = "OMS"; attribute :>> causeState = "特定"; attribute :>> actionClass = "部品交換"; attribute :>> phase = "PH-3"; }
        occurrence <'IFA-302'> ifa_302 : InFlightAnomaly { doc /* STS-126-V-06 CCTV 肘カメラの映像が ALC モードで黒くなる */ attribute :>> reportNumber = "STS-126-V-06"; attribute :>> flight = "STS-126"; attribute :>> subsystem = "CT"; attribute :>> causeState = "不明"; attribute :>> actionClass = "再点検・再試験"; attribute :>> phase = "PH-3"; }
        occurrence <'IFA-303'> ifa_303 : InFlightAnomaly { doc /* STS-126-V-07 燃料電池1の水素流量計が上限外れ・不規則 */ attribute :>> reportNumber = "STS-126-V-07"; attribute :>> flight = "STS-126"; attribute :>> subsystem = "EPS"; attribute :>> causeState = "記載なし"; attribute :>> actionClass = "許容・そのまま飛行"; attribute :>> phase = "PH-3"; }
        occurrence <'IFA-304'> ifa_304 : InFlightAnomaly { doc /* STS-126-V-08 エンジン2の GH2 圧力流量制御弁2が指令なしに開いた */ attribute :>> reportNumber = "STS-126-V-08"; attribute :>> flight = "STS-126"; attribute :>> subsystem = "MPS"; attribute :>> causeState = "特定"; attribute :>> actionClass = "部品交換"; attribute :>> phase = "PH-2"; }
        occurrence <'IFA-305'> ifa_305 : InFlightAnomaly { doc /* STS-126-V-09 MPS 空圧ヘリウムの圧力低下が上昇中に想定を超えた */ attribute :>> reportNumber = "STS-126-V-09"; attribute :>> flight = "STS-126"; attribute :>> subsystem = "MPS"; attribute :>> causeState = "特定"; attribute :>> actionClass = "部品交換"; attribute :>> phase = "PH-2"; }
        occurrence <'IFA-306'> ifa_306 : InFlightAnomaly { doc /* STS-126-V-10 CCTV 肘カメラの色が公称と異なる */ attribute :>> reportNumber = "STS-126-V-10"; attribute :>> flight = "STS-126"; attribute :>> subsystem = "CT"; attribute :>> causeState = "調査中"; attribute :>> actionClass = "再点検・再試験"; attribute :>> phase = "PH-3"; }
        occurrence <'IFA-307'> ifa_307 : InFlightAnomaly { doc /* STS-126-V-11 CCTV カメラ A の映像が黄色味を帯びた */ attribute :>> reportNumber = "STS-126-V-11"; attribute :>> flight = "STS-126"; attribute :>> subsystem = "CT"; attribute :>> causeState = "記載なし"; attribute :>> actionClass = "許容・そのまま飛行"; attribute :>> phase = "PH-3"; }
        occurrence <'IFA-308'> ifa_308 : InFlightAnomaly { doc /* STS-126-V-12 Ku 帯レーダデータの GNC 側 bypass */ attribute :>> reportNumber = "STS-126-V-12"; attribute :>> flight = "STS-126"; attribute :>> subsystem = "CT"; attribute :>> causeState = "推定"; attribute :>> actionClass = "部品交換"; attribute :>> phase = "PH-3"; }
        occurrence <'IFA-309'> ifa_309 : InFlightAnomaly { doc /* STS-126-V-13 DTV マルチプレクサのチャネル2でバッファエラー */ attribute :>> reportNumber = "STS-126-V-13"; attribute :>> flight = "STS-126"; attribute :>> subsystem = "CT"; attribute :>> causeState = "特定"; attribute :>> actionClass = "許容・そのまま飛行"; attribute :>> phase = "PH-3"; }
        occurrence <'IFA-310'> ifa_310 : InFlightAnomaly { doc /* STS-126-V-14 LDRI の映像が後期点検で途切れた */ attribute :>> reportNumber = "STS-126-V-14"; attribute :>> flight = "STS-126"; attribute :>> subsystem = "OTHER"; attribute :>> causeState = "調査中"; attribute :>> actionClass = "再点検・再試験"; attribute :>> phase = "PH-4"; }
        occurrence <'IFA-311'> ifa_311 : InFlightAnomaly { doc /* STS-126-V-15 CDR キーボード3の特定のキーで二重入力 */ attribute :>> reportNumber = "STS-126-V-15"; attribute :>> flight = "STS-126"; attribute :>> subsystem = "DPS"; attribute :>> causeState = "調査中"; attribute :>> actionClass = "部品交換"; attribute :>> phase = "PH-3"; }
        occurrence <'IFA-312'> ifa_312 : InFlightAnomaly { doc /* STS-126-V-16 ペイロード信号処理器（PSP）1 の bypass */ attribute :>> reportNumber = "STS-126-V-16"; attribute :>> flight = "STS-126"; attribute :>> subsystem = "CT"; attribute :>> causeState = "調査中"; attribute :>> actionClass = "部品交換"; attribute :>> phase = "PH-3"; }
        occurrence <'IFA-313'> ifa_313 : InFlightAnomaly { doc /* STS-126-V-17 APU 1 の燃料タンク出口圧力トランスデューサが温度に追従しない */ attribute :>> reportNumber = "STS-126-V-17"; attribute :>> flight = "STS-126"; attribute :>> subsystem = "APU"; attribute :>> causeState = "特定"; attribute :>> actionClass = "部品交換"; attribute :>> phase = "PH-3"; }
        occurrence <'IFA-314'> ifa_314 : InFlightAnomaly { doc /* STS-126-V-18 CDR の音声が断続的に消える */ attribute :>> reportNumber = "STS-126-V-18"; attribute :>> flight = "STS-126"; attribute :>> subsystem = "CT"; attribute :>> causeState = "推定"; attribute :>> actionClass = "許容・そのまま飛行"; attribute :>> phase = "PH-6"; }
        occurrence <'IFA-315'> ifa_315 : InFlightAnomaly { doc /* STS-126-V-19 Ku 帯 216 kbps フォワードリンクのフレーム同期テレメトリが途切れる */ attribute :>> reportNumber = "STS-126-V-19"; attribute :>> flight = "STS-126"; attribute :>> subsystem = "CT"; attribute :>> causeState = "推定"; attribute :>> actionClass = "部品交換"; attribute :>> phase = "PH-3"; }
        occurrence <'IFA-316'> ifa_316 : InFlightAnomaly { doc /* STS-126-V-20 Ku 帯レーダの距離データが誤り */ attribute :>> reportNumber = "STS-126-V-20"; attribute :>> flight = "STS-126"; attribute :>> subsystem = "CT"; attribute :>> causeState = "不明"; attribute :>> actionClass = "許容・そのまま飛行"; attribute :>> phase = "PH-3"; }
        occurrence <'IFA-317'> ifa_317 : InFlightAnomaly { doc /* STS-127-V-01 微生物除去装置（MRA）の漏れ */ attribute :>> reportNumber = "STS-127-V-01"; attribute :>> flight = "STS-127"; attribute :>> subsystem = "ECLSS"; attribute :>> causeState = "推定"; attribute :>> actionClass = "部品交換"; attribute :>> phase = "PH-3"; }
        occurrence <'IFA-318'> ifa_318 : InFlightAnomaly { doc /* STS-127-V-02 RMS の肘カメラの映像の明るい部分に出るピンクと青の色かぶり */ attribute :>> reportNumber = "STS-127-V-02"; attribute :>> flight = "STS-127"; attribute :>> subsystem = "CT"; attribute :>> causeState = "特定"; attribute :>> actionClass = "再点検・再試験"; attribute :>> phase = "PH-3"; }
        occurrence <'IFA-319'> ifa_319 : InFlightAnomaly { doc /* STS-127-V-03 TPS の異常（下部機首・前部胴体のタイルの損傷7件） */ attribute :>> reportNumber = "STS-127-V-03"; attribute :>> flight = "STS-127"; attribute :>> subsystem = "TPS"; attribute :>> causeState = "記載なし"; attribute :>> actionClass = "再点検・再試験"; attribute :>> phase = "PH-3"; }
        occurrence <'IFA-320'> ifa_320 : InFlightAnomaly { doc /* STS-127-V-04 MADS の公称でない計測の波形 */ attribute :>> reportNumber = "STS-127-V-04"; attribute :>> flight = "STS-127"; attribute :>> subsystem = "STR"; attribute :>> causeState = "特定"; attribute :>> actionClass = "部品交換"; attribute :>> phase = "PH-2"; }
        occurrence <'IFA-321'> ifa_321 : InFlightAnomaly { doc /* STS-127-V-05 燃料電池 3 の維持ヒータの長いサイクル */ attribute :>> reportNumber = "STS-127-V-05"; attribute :>> flight = "STS-127"; attribute :>> subsystem = "EPS"; attribute :>> causeState = "調査中"; attribute :>> actionClass = "手順・規則の変更"; attribute :>> phase = "PH-3"; }
        occurrence <'IFA-322'> ifa_322 : InFlightAnomaly { doc /* STS-127-V-06 EV-3 のコミュニケーション・キャップの左耳の音声の喪失 */ attribute :>> reportNumber = "STS-127-V-06"; attribute :>> flight = "STS-127"; attribute :>> subsystem = "EVA"; attribute :>> causeState = "不明"; attribute :>> actionClass = "再点検・再試験"; attribute :>> phase = "PH-5"; }
        occurrence <'IFA-323'> ifa_323 : InFlightAnomaly { doc /* STS-127-V-07 RCS のホットファイア中に前部 RCS スラスタ F2F が故障オフ */ attribute :>> reportNumber = "STS-127-V-07"; attribute :>> flight = "STS-127"; attribute :>> subsystem = "RCS"; attribute :>> causeState = "特定"; attribute :>> actionClass = "部品交換"; attribute :>> phase = "PH-3"; }
        occurrence <'IFA-324'> ifa_324 : InFlightAnomaly { doc /* STS-127-V-08 LH2 内側の ET パイロ・キャニスタの発泡 TPS のひび */ attribute :>> reportNumber = "STS-127-V-08"; attribute :>> flight = "STS-127"; attribute :>> subsystem = "ET"; attribute :>> causeState = "特定"; attribute :>> actionClass = "手順・規則の変更"; attribute :>> phase = "PH-1"; }
        occurrence <'IFA-325'> ifa_325 : InFlightAnomaly { doc /* STS-127-V-09 パイロットのヘッドセット・インタフェース・ユニット（HIU）の故障 */ attribute :>> reportNumber = "STS-127-V-09"; attribute :>> flight = "STS-127"; attribute :>> subsystem = "CT"; attribute :>> causeState = "特定"; attribute :>> actionClass = "部品交換"; attribute :>> phase = "PH-4"; }
        occurrence <'IFA-326'> ifa_326 : InFlightAnomaly { doc /* STS-127-V-10 LO2 の飛行ストラットが誤った位置に取り付けられていた */ attribute :>> reportNumber = "STS-127-V-10"; attribute :>> flight = "STS-127"; attribute :>> subsystem = "MPS"; attribute :>> causeState = "調査中"; attribute :>> actionClass = "再点検・再試験"; attribute :>> phase = "PH-7"; }
        occurrence <'IFA-327'> ifa_327 : InFlightAnomaly { doc /* STS-128-V-01 LH2 内側の充填排出弁（PV12）の閉位置表示が「入」にならない */ attribute :>> reportNumber = "STS-128-V-01"; attribute :>> flight = "STS-128"; attribute :>> subsystem = "MPS"; attribute :>> causeState = "調査中"; attribute :>> actionClass = "再点検・再試験"; attribute :>> phase = "PH-1"; }
        occurrence <'IFA-328'> ifa_328 : InFlightAnomaly { doc /* STS-128-V-02 前部 RCS バーニア F5R の噴射器温度の低下 */ attribute :>> reportNumber = "STS-128-V-02"; attribute :>> flight = "STS-128"; attribute :>> subsystem = "RCS"; attribute :>> causeState = "記載なし"; attribute :>> actionClass = "部品交換"; attribute :>> phase = "PH-3"; }
        occurrence <'IFA-329'> ifa_329 : InFlightAnomaly { doc /* STS-128-V-03 RMS エンドエフェクタ点検中の予期しない捕獲のマイクロスイッチ作動 */ attribute :>> reportNumber = "STS-128-V-03"; attribute :>> flight = "STS-128"; attribute :>> subsystem = "PLS"; attribute :>> causeState = "特定"; attribute :>> actionClass = "部品交換"; attribute :>> phase = "PH-3"; }
        occurrence <'IFA-330'> ifa_330 : InFlightAnomaly { doc /* STS-128-V-04 TPS の13件が選別基準を超過（うち4件は追加の解析） */ attribute :>> reportNumber = "STS-128-V-04"; attribute :>> flight = "STS-128"; attribute :>> subsystem = "TPS"; attribute :>> causeState = "記載なし"; attribute :>> actionClass = "再点検・再試験"; attribute :>> phase = "PH-3"; }
        occurrence <'IFA-331'> ifa_331 : InFlightAnomaly { doc /* STS-128-V-05 MADS の左 OMS ポッド温度がオフスケール高 */ attribute :>> reportNumber = "STS-128-V-05"; attribute :>> flight = "STS-128"; attribute :>> subsystem = "OTHER"; attribute :>> causeState = "特定"; attribute :>> actionClass = "次便で対処"; attribute :>> phase = "PH-2"; }
        occurrence <'IFA-332'> ifa_332 : InFlightAnomaly { doc /* STS-128-V-06 APU 3 の EGT 変換器 2 が周囲温度を下回る値を示す */ attribute :>> reportNumber = "STS-128-V-06"; attribute :>> flight = "STS-128"; attribute :>> subsystem = "APU"; attribute :>> causeState = "推定"; attribute :>> actionClass = "部品交換"; attribute :>> phase = "PH-7"; }
        occurrence <'IFA-333'> ifa_333 : InFlightAnomaly { doc /* STS-128-V-07 EVA 2 の EV2 のバックアップ CCA の通信が不良 */ attribute :>> reportNumber = "STS-128-V-07"; attribute :>> flight = "STS-128"; attribute :>> subsystem = "EVA"; attribute :>> causeState = "不明"; attribute :>> actionClass = "部品交換"; attribute :>> phase = "PH-5"; }
        occurrence <'IFA-334'> ifa_334 : InFlightAnomaly { doc /* STS-128-V-08 後部 DAP パネルの「A」押しボタンの接点 C が冗長管理で故障 */ attribute :>> reportNumber = "STS-128-V-08"; attribute :>> flight = "STS-128"; attribute :>> subsystem = "GNC"; attribute :>> causeState = "推定"; attribute :>> actionClass = "部品交換"; attribute :>> phase = "PH-3"; }
        occurrence <'IFA-335'> ifa_335 : InFlightAnomaly { doc /* STS-129-V-02 EV1 の CCA のヘッドセットの音声喪失 */ attribute :>> reportNumber = "STS-129-V-02"; attribute :>> flight = "STS-129"; attribute :>> subsystem = "EVA"; attribute :>> causeState = "特定"; attribute :>> actionClass = "部品交換"; attribute :>> phase = "PH-5"; }
        occurrence <'IFA-336'> ifa_336 : InFlightAnomaly { doc /* STS-129-V-03 中部右舷のペイロードベイの投光灯 4 の故障 */ attribute :>> reportNumber = "STS-129-V-03"; attribute :>> flight = "STS-129"; attribute :>> subsystem = "CREW"; attribute :>> causeState = "特定"; attribute :>> actionClass = "部品交換"; attribute :>> phase = "PH-3"; }
        occurrence <'IFA-337'> ifa_337 : InFlightAnomaly { doc /* STS-129-V-04 WVS 1 の V10 レコーダがテープを噛む */ attribute :>> reportNumber = "STS-129-V-04"; attribute :>> flight = "STS-129"; attribute :>> subsystem = "CT"; attribute :>> causeState = "特定"; attribute :>> actionClass = "部品交換"; attribute :>> phase = "PH-3"; }
        occurrence <'IFA-338'> ifa_338 : InFlightAnomaly { doc /* STS-129-V-05 廃水ダンプが途中で止まる */ attribute :>> reportNumber = "STS-129-V-05"; attribute :>> flight = "STS-129"; attribute :>> subsystem = "ECLSS"; attribute :>> causeState = "特定"; attribute :>> actionClass = "部品交換"; attribute :>> phase = "PH-3"; }
        occurrence <'IFA-339'> ifa_339 : InFlightAnomaly { doc /* STS-129-V-06 ET アンビリカルカメラのフラッシュモジュールのサーモスタットの短絡 */ attribute :>> reportNumber = "STS-129-V-06"; attribute :>> flight = "STS-129"; attribute :>> subsystem = "OTHER"; attribute :>> causeState = "特定"; attribute :>> actionClass = "記載なし"; attribute :>> phase = "PH-7"; }
        occurrence <'IFA-340'> ifa_340 : InFlightAnomaly { doc /* STS-129-V-07 PLT 1 の MDU の画面ガラスの損傷 */ attribute :>> reportNumber = "STS-129-V-07"; attribute :>> flight = "STS-129"; attribute :>> subsystem = "DPS"; attribute :>> causeState = "推定"; attribute :>> actionClass = "部品交換"; attribute :>> phase = "PH-3"; }
        occurrence <'IFA-341'> ifa_341 : InFlightAnomaly { doc /* STS-129-V-08 ケーブルの不良によるモニタ 2 の映像なし */ attribute :>> reportNumber = "STS-129-V-08"; attribute :>> flight = "STS-129"; attribute :>> subsystem = "CT"; attribute :>> causeState = "特定"; attribute :>> actionClass = "再点検・再試験"; attribute :>> phase = "PH-3"; }
        occurrence <'IFA-342'> ifa_342 : InFlightAnomaly { doc /* STS-129-V-09 消火器が壁の保持具から外れる */ attribute :>> reportNumber = "STS-129-V-09"; attribute :>> flight = "STS-129"; attribute :>> subsystem = "ECLSS"; attribute :>> causeState = "記載なし"; attribute :>> actionClass = "手順・規則の変更"; attribute :>> phase = "PH-6"; }
        occurrence <'IFA-343'> ifa_343 : InFlightAnomaly { doc /* STS-129-V-10 APU の噴射器冷却水タンクのヒータ A が期待の温度で作動しない */ attribute :>> reportNumber = "STS-129-V-10"; attribute :>> flight = "STS-129"; attribute :>> subsystem = "APU"; attribute :>> causeState = "特定"; attribute :>> actionClass = "部品交換"; attribute :>> phase = "PH-3"; }
        occurrence <'IFA-344'> ifa_344 : InFlightAnomaly { doc /* STS-129-V-11 HD 映像のダウンリンクが成功しない */ attribute :>> reportNumber = "STS-129-V-11"; attribute :>> flight = "STS-129"; attribute :>> subsystem = "OTHER"; attribute :>> causeState = "特定"; attribute :>> actionClass = "部品交換"; attribute :>> phase = "PH-3"; }
        occurrence <'IFA-345'> ifa_345 : InFlightAnomaly { doc /* STS-131-V-01 エンジン 3 の LH2 入口圧力 3 がオフスケール低 */ attribute :>> reportNumber = "STS-131-V-01"; attribute :>> flight = "STS-131"; attribute :>> subsystem = "MPS"; attribute :>> causeState = "特定"; attribute :>> actionClass = "部品交換"; attribute :>> phase = "PH-1"; }
        occurrence <'IFA-346'> ifa_346 : InFlightAnomaly { doc /* STS-131-V-02 Ku 帯のフォワード・リターンリンクの故障 */ attribute :>> reportNumber = "STS-131-V-02"; attribute :>> flight = "STS-131"; attribute :>> subsystem = "CT"; attribute :>> causeState = "特定"; attribute :>> actionClass = "部品交換"; attribute :>> phase = "PH-3"; }
        occurrence <'IFA-347'> ifa_347 : InFlightAnomaly { doc /* STS-131-V-03 ペイロードベイの後部から出た正体不明の明るい物体 */ attribute :>> reportNumber = "STS-131-V-03"; attribute :>> flight = "STS-131"; attribute :>> subsystem = "OTHER"; attribute :>> causeState = "不明"; attribute :>> actionClass = "再点検・再試験"; attribute :>> phase = "PH-5"; }
        occurrence <'IFA-348'> ifa_348 : InFlightAnomaly { doc /* STS-131-V-04 TPS の6件が選別基準を超過 */ attribute :>> reportNumber = "STS-131-V-04"; attribute :>> flight = "STS-131"; attribute :>> subsystem = "TPS"; attribute :>> causeState = "記載なし"; attribute :>> actionClass = "再点検・再試験"; attribute :>> phase = "PH-3"; }
        occurrence <'IFA-349'> ifa_349 : InFlightAnomaly { doc /* STS-131-V-05 WLE センサ No. 1041 が他の10個のセンサを強制トリガしない */ attribute :>> reportNumber = "STS-131-V-05"; attribute :>> flight = "STS-131"; attribute :>> subsystem = "STR"; attribute :>> causeState = "調査中"; attribute :>> actionClass = "部品交換"; attribute :>> phase = "PH-3"; }
        occurrence <'IFA-350'> ifa_350 : InFlightAnomaly { doc /* STS-131-V-06 SSR2 が予期せずスタンバイへ移行 */ attribute :>> reportNumber = "STS-131-V-06"; attribute :>> flight = "STS-131"; attribute :>> subsystem = "DPS"; attribute :>> causeState = "記載なし"; attribute :>> actionClass = "部品交換"; attribute :>> phase = "PH-3"; }
        occurrence <'IFA-351'> ifa_351 : InFlightAnomaly { doc /* STS-131-V-07 CCTV カメラ C のズームが働かない */ attribute :>> reportNumber = "STS-131-V-07"; attribute :>> flight = "STS-131"; attribute :>> subsystem = "CT"; attribute :>> causeState = "記載なし"; attribute :>> actionClass = "再点検・再試験"; attribute :>> phase = "PH-3"; }
        occurrence <'IFA-352'> ifa_352 : InFlightAnomaly { doc /* STS-131-V-08 左 RCS の燃料ヘリウム隔離弁 B の閉が遅い */ attribute :>> reportNumber = "STS-131-V-08"; attribute :>> flight = "STS-131"; attribute :>> subsystem = "RCS"; attribute :>> causeState = "推定"; attribute :>> actionClass = "再点検・再試験"; attribute :>> phase = "PH-4"; }
        occurrence <'IFA-353'> ifa_353 : InFlightAnomaly { doc /* STS-131-V-09 前部 RCS の燃料ヘリウム隔離弁 A の閉が遅い */ attribute :>> reportNumber = "STS-131-V-09"; attribute :>> flight = "STS-131"; attribute :>> subsystem = "RCS"; attribute :>> causeState = "推定"; attribute :>> actionClass = "再点検・再試験"; attribute :>> phase = "PH-4"; }
        occurrence <'IFA-354'> ifa_354 : InFlightAnomaly { doc /* STS-131-V-10 窓のセラミックプラグの突出・欠落 */ attribute :>> reportNumber = "STS-131-V-10"; attribute :>> flight = "STS-131"; attribute :>> subsystem = "TPS"; attribute :>> causeState = "特定"; attribute :>> actionClass = "部品交換"; attribute :>> phase = "PH-7"; }
        occurrence <'IFA-355'> ifa_355 : InFlightAnomaly { doc /* STS-131-V-11 左上の S 帯アンテナの AGC レベルの雑音 */ attribute :>> reportNumber = "STS-131-V-11"; attribute :>> flight = "STS-131"; attribute :>> subsystem = "CT"; attribute :>> causeState = "推定"; attribute :>> actionClass = "部品交換"; attribute :>> phase = "PH-3"; }
        occurrence <'IFA-356'> ifa_356 : InFlightAnomaly { doc /* STS-131-V-12 CCTV モニタ 2 が赤みを帯びる */ attribute :>> reportNumber = "STS-131-V-12"; attribute :>> flight = "STS-131"; attribute :>> subsystem = "CT"; attribute :>> causeState = "特定"; attribute :>> actionClass = "部品交換"; attribute :>> phase = "PH-3"; }
        occurrence <'IFA-357'> ifa_357 : InFlightAnomaly { doc /* STS-131-V-13 MPLM のキール・カメラの映像のちらつき */ attribute :>> reportNumber = "STS-131-V-13"; attribute :>> flight = "STS-131"; attribute :>> subsystem = "OTHER"; attribute :>> causeState = "調査中"; attribute :>> actionClass = "再点検・再試験"; attribute :>> phase = "PH-3"; }
        occurrence <'IFA-358'> ifa_358 : InFlightAnomaly { doc /* STS-131-V-14 流量制御弁（FCV）のポペットの亀裂 */ attribute :>> reportNumber = "STS-131-V-14"; attribute :>> flight = "STS-131"; attribute :>> subsystem = "MPS"; attribute :>> causeState = "記載なし"; attribute :>> actionClass = "許容・そのまま飛行"; attribute :>> phase = "PH-7"; }
        occurrence <'IFA-359'> ifa_359 : InFlightAnomaly { doc /* STS-132-V-01 OBSS の PTU のビデオケーブルの引っかかり */ attribute :>> reportNumber = "STS-132-V-01"; attribute :>> flight = "STS-132"; attribute :>> subsystem = "PLS"; attribute :>> causeState = "特定"; attribute :>> actionClass = "部品交換"; attribute :>> phase = "PH-3"; }
        occurrence <'IFA-360'> ifa_360 : InFlightAnomaly { doc /* STS-132-V-02 RCS 噴射器 L3D のヒータが OFF のまま故障 */ attribute :>> reportNumber = "STS-132-V-02"; attribute :>> flight = "STS-132"; attribute :>> subsystem = "RCS"; attribute :>> causeState = "記載なし"; attribute :>> actionClass = "部品交換"; attribute :>> phase = "PH-3"; }
        occurrence <'IFA-361'> ifa_361 : InFlightAnomaly { doc /* STS-132-V-03 TPS の異常（OBSS の PTU 故障で LDRI を取れなかった点検） */ attribute :>> reportNumber = "STS-132-V-03"; attribute :>> flight = "STS-132"; attribute :>> subsystem = "TPS"; attribute :>> causeState = "記載なし"; attribute :>> actionClass = "許容・そのまま飛行"; attribute :>> phase = "PH-3"; }
        occurrence <'IFA-362'> ifa_362 : InFlightAnomaly { doc /* STS-132-V-04 FES の一次 B 制御器での停止 */ attribute :>> reportNumber = "STS-132-V-04"; attribute :>> flight = "STS-132"; attribute :>> subsystem = "ECLSS"; attribute :>> causeState = "推定"; attribute :>> actionClass = "部品交換"; attribute :>> phase = "PH-4"; }
        occurrence <'IFA-363'> ifa_363 : InFlightAnomaly { doc /* STS-133-V-01 湿度分離器 B の水の持ち越し */ attribute :>> reportNumber = "STS-133-V-01"; attribute :>> flight = "STS-133"; attribute :>> subsystem = "ECLSS"; attribute :>> causeState = "記載なし"; attribute :>> actionClass = "手順・規則の変更"; attribute :>> phase = "PH-3"; }
        occurrence <'IFA-364'> ifa_364 : InFlightAnomaly { doc /* STS-133-V-02 MADS の左翼桁の差圧の測定値が不安定 */ attribute :>> reportNumber = "STS-133-V-02"; attribute :>> flight = "STS-133"; attribute :>> subsystem = "OTHER"; attribute :>> causeState = "記載なし"; attribute :>> actionClass = "許容・そのまま飛行"; attribute :>> phase = "PH-2"; }
        occurrence <'IFA-365'> ifa_365 : InFlightAnomaly { doc /* STS-133-V-03 TPS の異常（8件が飛行中の基準を超えた） */ attribute :>> reportNumber = "STS-133-V-03"; attribute :>> flight = "STS-133"; attribute :>> subsystem = "TPS"; attribute :>> causeState = "記載なし"; attribute :>> actionClass = "許容・そのまま飛行"; attribute :>> phase = "PH-3"; }
        occurrence <'IFA-366'> ifa_366 : InFlightAnomaly { doc /* STS-133-V-04 右 RCS の燃料ヘリウム一次調圧器のクリープ（内部漏れ） */ attribute :>> reportNumber = "STS-133-V-04"; attribute :>> flight = "STS-133"; attribute :>> subsystem = "RCS"; attribute :>> causeState = "記載なし"; attribute :>> actionClass = "許容・そのまま飛行"; attribute :>> phase = "PH-1"; }
        occurrence <'IFA-367'> ifa_367 : InFlightAnomaly { doc /* STS-133-V-05 S 帯の高周波（HF）モードで上りが途切れる */ attribute :>> reportNumber = "STS-133-V-05"; attribute :>> flight = "STS-133"; attribute :>> subsystem = "CT"; attribute :>> causeState = "推定"; attribute :>> actionClass = "許容・そのまま飛行"; attribute :>> phase = "PH-3"; }
        occurrence <'IFA-368'> ifa_368 : InFlightAnomaly { doc /* STS-133-V-06 EVA 用 RF カメラ ERCA 19 の映像が出ない */ attribute :>> reportNumber = "STS-133-V-06"; attribute :>> flight = "STS-133"; attribute :>> subsystem = "EVA"; attribute :>> causeState = "推定"; attribute :>> actionClass = "次便で対処"; attribute :>> phase = "PH-5"; }
        occurrence <'IFA-369'> ifa_369 : InFlightAnomaly { doc /* STS-133-V-07 ATVC チャネル 1 の電源が再起動しない */ attribute :>> reportNumber = "STS-133-V-07"; attribute :>> flight = "STS-133"; attribute :>> subsystem = "GNC"; attribute :>> causeState = "推定"; attribute :>> actionClass = "再点検・再試験"; attribute :>> phase = "PH-4"; }
        occurrence <'IFA-370'> ifa_370 : InFlightAnomaly { doc /* STS-133-V-08 アンモニア・スプレーボイラ系 B の予期しない切替え */ attribute :>> reportNumber = "STS-133-V-08"; attribute :>> flight = "STS-133"; attribute :>> subsystem = "ECLSS"; attribute :>> causeState = "推定"; attribute :>> actionClass = "許容・そのまま飛行"; attribute :>> phase = "PH-6"; }
        occurrence <'IFA-371'> ifa_371 : InFlightAnomaly { doc /* STS-133-V-09 OAFGSS の左2番ボトル 1120 の圧力が低い */ attribute :>> reportNumber = "STS-133-V-09"; attribute :>> flight = "STS-133"; attribute :>> subsystem = "OTHER"; attribute :>> causeState = "推定"; attribute :>> actionClass = "次便で対処"; attribute :>> phase = "PH-3"; }
        occurrence <'IFA-372'> ifa_372 : InFlightAnomaly { doc /* STS-133-V-10 WLEIDS の最後のトリガが報告されなかった */ attribute :>> reportNumber = "STS-133-V-10"; attribute :>> flight = "STS-133"; attribute :>> subsystem = "OTHER"; attribute :>> causeState = "特定"; attribute :>> actionClass = "手順・規則の変更"; attribute :>> phase = "PH-3"; }
        occurrence <'IFA-373'> ifa_373 : InFlightAnomaly { doc /* STS-134-V-01 APU 1 の燃料テストラインの温度が LCC の限界を下回る */ attribute :>> reportNumber = "STS-134-V-01"; attribute :>> flight = "STS-134"; attribute :>> subsystem = "APU"; attribute :>> causeState = "推定"; attribute :>> actionClass = "部品交換"; attribute :>> phase = "PH-1"; }
        occurrence <'IFA-374'> ifa_374 : InFlightAnomaly { doc /* STS-134-V-02 前方ミッションタイマの MET が4時間ずれる */ attribute :>> reportNumber = "STS-134-V-02"; attribute :>> flight = "STS-134"; attribute :>> subsystem = "DPS"; attribute :>> causeState = "記載なし"; attribute :>> actionClass = "許容・そのまま飛行"; attribute :>> phase = "PH-3"; }
        occurrence <'IFA-375'> ifa_375 : InFlightAnomaly { doc /* STS-134-V-03 右前脚のタイヤ圧 2 の変換器の出力が不安定 */ attribute :>> reportNumber = "STS-134-V-03"; attribute :>> flight = "STS-134"; attribute :>> subsystem = "MECH"; attribute :>> causeState = "記載なし"; attribute :>> actionClass = "手順・規則の変更"; attribute :>> phase = "PH-2"; }
        occurrence <'IFA-376'> ifa_376 : InFlightAnomaly { doc /* STS-134-V-04 複数ヘッドセット・アダプタのポート J1・J2 が送信しない */ attribute :>> reportNumber = "STS-134-V-04"; attribute :>> flight = "STS-134"; attribute :>> subsystem = "CT"; attribute :>> causeState = "記載なし"; attribute :>> actionClass = "再点検・再試験"; attribute :>> phase = "PH-3"; }
        occurrence <'IFA-377'> ifa_377 : InFlightAnomaly { doc /* STS-134-V-05 TCS がパルスから CW への移行に遅れる */ attribute :>> reportNumber = "STS-134-V-05"; attribute :>> flight = "STS-134"; attribute :>> subsystem = "GNC"; attribute :>> causeState = "記載なし"; attribute :>> actionClass = "許容・そのまま飛行"; attribute :>> phase = "PH-3"; }
        occurrence <'IFA-378'> ifa_378 : InFlightAnomaly { doc /* STS-134-V-06 APU の SM アラート */ attribute :>> reportNumber = "STS-134-V-06"; attribute :>> flight = "STS-134"; attribute :>> subsystem = "APU"; attribute :>> causeState = "記載なし"; attribute :>> actionClass = "手順・規則の変更"; attribute :>> phase = "PH-3"; }
        occurrence <'IFA-379'> ifa_379 : InFlightAnomaly { doc /* STS-134-V-07 燃料電池 2 サブスタック 1 の CPM の自己試験が断続的に失敗 */ attribute :>> reportNumber = "STS-134-V-07"; attribute :>> flight = "STS-134"; attribute :>> subsystem = "EPS"; attribute :>> causeState = "記載なし"; attribute :>> actionClass = "手順・規則の変更"; attribute :>> phase = "PH-3"; }
        occurrence <'IFA-380'> ifa_380 : InFlightAnomaly { doc /* STS-134-V-08 左主脚の短い火炎の観測 */ attribute :>> reportNumber = "STS-134-V-08"; attribute :>> flight = "STS-134"; attribute :>> subsystem = "MECH"; attribute :>> causeState = "不明"; attribute :>> actionClass = "再点検・再試験"; attribute :>> phase = "PH-7"; }
        occurrence <'IFA-381'> ifa_381 : InFlightAnomaly { doc /* STS-134-V-09 ET／オービタ・アンビリカルの LO2 前方外側アクチュエータが機械ロックに戻らない */ attribute :>> reportNumber = "STS-134-V-09"; attribute :>> flight = "STS-134"; attribute :>> subsystem = "MECH"; attribute :>> causeState = "記載なし"; attribute :>> actionClass = "記載なし"; attribute :>> phase = "PH-7"; }
        occurrence <'IFA-382'> ifa_382 : InFlightAnomaly { doc /* STS-135-V-01 WLES センサ 1080 の通信の不具合 */ attribute :>> reportNumber = "STS-135-V-01"; attribute :>> flight = "STS-135"; attribute :>> subsystem = "OTHER"; attribute :>> causeState = "記載なし"; attribute :>> actionClass = "再点検・再試験"; attribute :>> phase = "PH-3"; }
        occurrence <'IFA-383'> ifa_383 : InFlightAnomaly { doc /* STS-135-V-02 タイル・ブランケットの異常（5件が基準を超えた） */ attribute :>> reportNumber = "STS-135-V-02"; attribute :>> flight = "STS-135"; attribute :>> subsystem = "TPS"; attribute :>> causeState = "記載なし"; attribute :>> actionClass = "許容・そのまま飛行"; attribute :>> phase = "PH-3"; }
        occurrence <'IFA-384'> ifa_384 : InFlightAnomaly { doc /* STS-135-V-03 WLES センサ 1111 が予定より早く OOM を抜ける */ attribute :>> reportNumber = "STS-135-V-03"; attribute :>> flight = "STS-135"; attribute :>> subsystem = "OTHER"; attribute :>> causeState = "記載なし"; attribute :>> actionClass = "再点検・再試験"; attribute :>> phase = "PH-3"; }
        occurrence <'IFA-385'> ifa_385 : InFlightAnomaly { doc /* STS-135-V-04 PRLA 3 のシステム A のマイクロスイッチが開を表示しない */ attribute :>> reportNumber = "STS-135-V-04"; attribute :>> flight = "STS-135"; attribute :>> subsystem = "PLS"; attribute :>> causeState = "記載なし"; attribute :>> actionClass = "許容・そのまま飛行"; attribute :>> phase = "PH-3"; }
        occurrence <'IFA-386'> ifa_386 : InFlightAnomaly { doc /* STS-135-V-05 ARS LiOH サービスドアが開かない */ attribute :>> reportNumber = "STS-135-V-05"; attribute :>> flight = "STS-135"; attribute :>> subsystem = "ECLSS"; attribute :>> causeState = "特定"; attribute :>> actionClass = "許容・そのまま飛行"; attribute :>> phase = "PH-3"; }
        occurrence <'IFA-387'> ifa_387 : InFlightAnomaly { doc /* STS-135-V-06 OPP から LCS へのケーブルが正しく装着できない */ attribute :>> reportNumber = "STS-135-V-06"; attribute :>> flight = "STS-135"; attribute :>> subsystem = "OTHER"; attribute :>> causeState = "推定"; attribute :>> actionClass = "許容・そのまま飛行"; attribute :>> phase = "PH-3"; }
        occurrence <'IFA-388'> ifa_388 : InFlightAnomaly { doc /* STS-135-V-07 LRCS 酸化剤マニホールド 5 の弁の、飛行後の弁試験での故障 */ attribute :>> reportNumber = "STS-135-V-07"; attribute :>> flight = "STS-135"; attribute :>> subsystem = "RCS"; attribute :>> causeState = "推定"; attribute :>> actionClass = "許容・そのまま飛行"; attribute :>> phase = "PH-7"; }
        occurrence <'IFA-389'> ifa_389 : InFlightAnomaly { doc /* STS-135-V-08 GPC 4（PASS の SM）の故障 */ attribute :>> reportNumber = "STS-135-V-08"; attribute :>> flight = "STS-135"; attribute :>> subsystem = "DPS"; attribute :>> causeState = "推定"; attribute :>> actionClass = "再点検・再試験"; attribute :>> phase = "PH-3"; }
        occurrence <'IFA-390'> ifa_390 : InFlightAnomaly { doc /* STS-135-V-09 OV-104 の機首キャップの損傷 */ attribute :>> reportNumber = "STS-135-V-09"; attribute :>> flight = "STS-135"; attribute :>> subsystem = "TPS"; attribute :>> causeState = "特定"; attribute :>> actionClass = "許容・そのまま飛行"; attribute :>> phase = "PH-7"; }
    }
    // ---- 故障モードとのつなぎ（異常が観測された故障モード）
    #ObservedAs dependency <'IFA-003>FMX-RCS-08'> from Anomalies::ifa_003 to SSD_FMX_ORB_001::FunctionalFailureModes::fmx_rcs_08;
    #ObservedAs dependency <'IFA-005>FMX-APU-10'> from Anomalies::ifa_005 to SSD_FMX_ORB_001::FunctionalFailureModes::fmx_apu_10;
    #ObservedAs dependency <'IFA-007>FMX-APU-10'> from Anomalies::ifa_007 to SSD_FMX_ORB_001::FunctionalFailureModes::fmx_apu_10;
    #ObservedAs dependency <'IFA-019>FMX-GNC-12'> from Anomalies::ifa_019 to SSD_FMX_ORB_001::FunctionalFailureModes::fmx_gnc_12;
    #ObservedAs dependency <'IFA-027>FMX-APU-10'> from Anomalies::ifa_027 to SSD_FMX_ORB_001::FunctionalFailureModes::fmx_apu_10;
    #ObservedAs dependency <'IFA-030>FMX-APU-03'> from Anomalies::ifa_030 to SSD_FMX_ORB_001::FunctionalFailureModes::fmx_apu_03;
    #ObservedAs dependency <'IFA-031>FMX-RCS-08'> from Anomalies::ifa_031 to SSD_FMX_ORB_001::FunctionalFailureModes::fmx_rcs_08;
    #ObservedAs dependency <'IFA-034>FMX-MPS-07'> from Anomalies::ifa_034 to SSD_FMX_ORB_001::FunctionalFailureModes::fmx_mps_07;
    #ObservedAs dependency <'IFA-035>FMX-CREW-LTG-01'> from Anomalies::ifa_035 to SSD_FMX_ORB_001::FunctionalFailureModes::fmx_crew_ltg_01;
    #ObservedAs dependency <'IFA-038>FMX-TCS-07'> from Anomalies::ifa_038 to SSD_FMX_ECL_001::FunctionalFailureModes::fmx_tcs_07;
    #ObservedAs dependency <'IFA-039>CIL-MPS-158'> from Anomalies::ifa_039 to SSD_FMM_ORB_001::FailureModes::cil_mps_158;
    #ObservedAs dependency <'IFA-040>FMX-APU-12'> from Anomalies::ifa_040 to SSD_FMX_ORB_001::FunctionalFailureModes::fmx_apu_12;
    #ObservedAs dependency <'IFA-046>FMX-GNC-12'> from Anomalies::ifa_046 to SSD_FMX_ORB_001::FunctionalFailureModes::fmx_gnc_12;
    #ObservedAs dependency <'IFA-052>FMX-GNC-10'> from Anomalies::ifa_052 to SSD_FMX_ORB_001::FunctionalFailureModes::fmx_gnc_10;
    #ObservedAs dependency <'IFA-053>FMX-GNC-02'> from Anomalies::ifa_053 to SSD_FMX_ORB_001::FunctionalFailureModes::fmx_gnc_02;
    #ObservedAs dependency <'IFA-054>FMX-MECH-06'> from Anomalies::ifa_054 to SSD_FMX_ORB_001::FunctionalFailureModes::fmx_mech_06;
    #ObservedAs dependency <'IFA-059>FMX-RCS-08'> from Anomalies::ifa_059 to SSD_FMX_ORB_001::FunctionalFailureModes::fmx_rcs_08;
    #ObservedAs dependency <'IFA-060>FMX-RCS-08'> from Anomalies::ifa_060 to SSD_FMX_ORB_001::FunctionalFailureModes::fmx_rcs_08;
    #ObservedAs dependency <'IFA-061>FMX-GNC-11'> from Anomalies::ifa_061 to SSD_FMX_ORB_001::FunctionalFailureModes::fmx_gnc_11;
    #ObservedAs dependency <'IFA-062>FMX-TCS-08'> from Anomalies::ifa_062 to SSD_FMX_ECL_001::FunctionalFailureModes::fmx_tcs_08;
    #ObservedAs dependency <'IFA-067>FMX-TCS-07'> from Anomalies::ifa_067 to SSD_FMX_ECL_001::FunctionalFailureModes::fmx_tcs_07;
    #ObservedAs dependency <'IFA-068>FMX-RCS-08'> from Anomalies::ifa_068 to SSD_FMX_ORB_001::FunctionalFailureModes::fmx_rcs_08;
    #ObservedAs dependency <'IFA-070>FMX-RCS-08'> from Anomalies::ifa_070 to SSD_FMX_ORB_001::FunctionalFailureModes::fmx_rcs_08;
    #ObservedAs dependency <'IFA-076>FMX-MECH-06'> from Anomalies::ifa_076 to SSD_FMX_ORB_001::FunctionalFailureModes::fmx_mech_06;
    #ObservedAs dependency <'IFA-077>FMX-RCS-08'> from Anomalies::ifa_077 to SSD_FMX_ORB_001::FunctionalFailureModes::fmx_rcs_08;
    #ObservedAs dependency <'IFA-081>FMX-CT-17'> from Anomalies::ifa_081 to SSD_FMX_ORB_001::FunctionalFailureModes::fmx_ct_17;
    #ObservedAs dependency <'IFA-082>FMX-TCS-06'> from Anomalies::ifa_082 to SSD_FMX_ECL_001::FunctionalFailureModes::fmx_tcs_06;
    #ObservedAs dependency <'IFA-082>FMX-TCS-08'> from Anomalies::ifa_082 to SSD_FMX_ECL_001::FunctionalFailureModes::fmx_tcs_08;
    #ObservedAs dependency <'IFA-117>CIL-ECLSS-019'> from Anomalies::ifa_117 to SSD_FMM_ORB_001::FailureModes::cil_eclss_019;
    #ObservedAs dependency <'IFA-122>FMX-MECH-06'> from Anomalies::ifa_122 to SSD_FMX_ORB_001::FunctionalFailureModes::fmx_mech_06;
    #ObservedAs dependency <'IFA-126>FMX-APU-11'> from Anomalies::ifa_126 to SSD_FMX_ORB_001::FunctionalFailureModes::fmx_apu_11;
    #ObservedAs dependency <'IFA-128>FMX-MECH-06'> from Anomalies::ifa_128 to SSD_FMX_ORB_001::FunctionalFailureModes::fmx_mech_06;
    #ObservedAs dependency <'IFA-129>FMX-TCS-08'> from Anomalies::ifa_129 to SSD_FMX_ECL_001::FunctionalFailureModes::fmx_tcs_08;
    #ObservedAs dependency <'IFA-137>FMX-CT-16'> from Anomalies::ifa_137 to SSD_FMX_ORB_001::FunctionalFailureModes::fmx_ct_16;
    #ObservedAs dependency <'IFA-143>FMX-RCS-05'> from Anomalies::ifa_143 to SSD_FMX_ORB_001::FunctionalFailureModes::fmx_rcs_05;
    #ObservedAs dependency <'IFA-146>FMX-STR-02'> from Anomalies::ifa_146 to SSD_FMX_ORB_001::FunctionalFailureModes::fmx_str_02;
    #ObservedAs dependency <'IFA-155>FMX-CREW-LTG-01'> from Anomalies::ifa_155 to SSD_FMX_ORB_001::FunctionalFailureModes::fmx_crew_ltg_01;
    #ObservedAs dependency <'IFA-162>FMX-GNC-14'> from Anomalies::ifa_162 to SSD_FMX_ORB_001::FunctionalFailureModes::fmx_gnc_14;
    #ObservedAs dependency <'IFA-171>FMX-CT-20'> from Anomalies::ifa_171 to SSD_FMX_ORB_001::FunctionalFailureModes::fmx_ct_20;
    #ObservedAs dependency <'IFA-189>FMX-GNC-02'> from Anomalies::ifa_189 to SSD_FMX_ORB_001::FunctionalFailureModes::fmx_gnc_02;
    #ObservedAs dependency <'IFA-220>FMX-RCS-07'> from Anomalies::ifa_220 to SSD_FMX_ORB_001::FunctionalFailureModes::fmx_rcs_07;
    #ObservedAs dependency <'IFA-227>FMX-APU-02'> from Anomalies::ifa_227 to SSD_FMX_ORB_001::FunctionalFailureModes::fmx_apu_02;
    #ObservedAs dependency <'IFA-233>FMX-TCS-08'> from Anomalies::ifa_233 to SSD_FMX_ECL_001::FunctionalFailureModes::fmx_tcs_08;
    #ObservedAs dependency <'IFA-236>FMX-APU-12'> from Anomalies::ifa_236 to SSD_FMX_ORB_001::FunctionalFailureModes::fmx_apu_12;
    #ObservedAs dependency <'IFA-245>FMX-RCS-07'> from Anomalies::ifa_245 to SSD_FMX_ORB_001::FunctionalFailureModes::fmx_rcs_07;
    #ObservedAs dependency <'IFA-249>FMX-CT-07'> from Anomalies::ifa_249 to SSD_FMX_ORB_001::FunctionalFailureModes::fmx_ct_07;
    #ObservedAs dependency <'IFA-252>FMX-APU-02'> from Anomalies::ifa_252 to SSD_FMX_ORB_001::FunctionalFailureModes::fmx_apu_02;
    #ObservedAs dependency <'IFA-253>FMX-APU-02'> from Anomalies::ifa_253 to SSD_FMX_ORB_001::FunctionalFailureModes::fmx_apu_02;
    #ObservedAs dependency <'IFA-254>CIL-MPS-463'> from Anomalies::ifa_254 to SSD_FMM_ORB_001::FailureModes::cil_mps_463;
    #ObservedAs dependency <'IFA-273>FMX-GNC-13'> from Anomalies::ifa_273 to SSD_FMX_ORB_001::FunctionalFailureModes::fmx_gnc_13;
    #ObservedAs dependency <'IFA-280>CIL-MPS-084'> from Anomalies::ifa_280 to SSD_FMM_ORB_001::FailureModes::cil_mps_084;
    #ObservedAs dependency <'IFA-281>FMX-EPS-07'> from Anomalies::ifa_281 to SSD_FMX_ORB_001::FunctionalFailureModes::fmx_eps_07;
    #ObservedAs dependency <'IFA-282>FMX-CREW-LTG-01'> from Anomalies::ifa_282 to SSD_FMX_ORB_001::FunctionalFailureModes::fmx_crew_ltg_01;
    #ObservedAs dependency <'IFA-283>FMX-CREW-LTG-01'> from Anomalies::ifa_283 to SSD_FMX_ORB_001::FunctionalFailureModes::fmx_crew_ltg_01;
    #ObservedAs dependency <'IFA-288>FMX-THC-02'> from Anomalies::ifa_288 to SSD_FMX_ECL_001::FunctionalFailureModes::fmx_thc_02;
    #ObservedAs dependency <'IFA-290>FMX-CT-16'> from Anomalies::ifa_290 to SSD_FMX_ORB_001::FunctionalFailureModes::fmx_ct_16;
    #ObservedAs dependency <'IFA-291>FMX-TCS-18'> from Anomalies::ifa_291 to SSD_FMX_ECL_001::FunctionalFailureModes::fmx_tcs_18;
    #ObservedAs dependency <'IFA-292>FMX-IMU-03'> from Anomalies::ifa_292 to SSD_FMX_ECL_001::FunctionalFailureModes::fmx_imu_03;
    #ObservedAs dependency <'IFA-295>FMX-DPS-14'> from Anomalies::ifa_295 to SSD_FMX_ORB_001::FunctionalFailureModes::fmx_dps_14;
    #ObservedAs dependency <'IFA-311>FMX-DPS-15'> from Anomalies::ifa_311 to SSD_FMX_ORB_001::FunctionalFailureModes::fmx_dps_15;
    #ObservedAs dependency <'IFA-323>FMX-RCS-08'> from Anomalies::ifa_323 to SSD_FMX_ORB_001::FunctionalFailureModes::fmx_rcs_08;
    #ObservedAs dependency <'IFA-323>FMX-RCS-12'> from Anomalies::ifa_323 to SSD_FMX_ORB_001::FunctionalFailureModes::fmx_rcs_12;
    #ObservedAs dependency <'IFA-328>FMX-RCS-07'> from Anomalies::ifa_328 to SSD_FMX_ORB_001::FunctionalFailureModes::fmx_rcs_07;
    #ObservedAs dependency <'IFA-345>CIL-MPS-462'> from Anomalies::ifa_345 to SSD_FMM_ORB_001::FailureModes::cil_mps_462;
    #ObservedAs dependency <'IFA-360>FMX-RCS-04'> from Anomalies::ifa_360 to SSD_FMX_ORB_001::FunctionalFailureModes::fmx_rcs_04;
    #ObservedAs dependency <'IFA-363>FMX-THC-02'> from Anomalies::ifa_363 to SSD_FMX_ECL_001::FunctionalFailureModes::fmx_thc_02;
    #ObservedAs dependency <'IFA-366>FMX-RCS-02'> from Anomalies::ifa_366 to SSD_FMX_ORB_001::FunctionalFailureModes::fmx_rcs_02;
    #ObservedAs dependency <'IFA-367>FMX-CT-16'> from Anomalies::ifa_367 to SSD_FMX_ORB_001::FunctionalFailureModes::fmx_ct_16;
    #ObservedAs dependency <'IFA-380>FMX-MECH-10'> from Anomalies::ifa_380 to SSD_FMX_ORB_001::FunctionalFailureModes::fmx_mech_10;
    #ObservedAs dependency <'IFA-385>FMX-PLS-08'> from Anomalies::ifa_385 to SSD_FMX_ORB_001::FunctionalFailureModes::fmx_pls_08;
    #ObservedAs dependency <'IFA-386>FMX-CO2-03'> from Anomalies::ifa_386 to SSD_FMX_ECL_001::FunctionalFailureModes::fmx_co2_03;
    #ObservedAs dependency <'IFA-389>FMX-DPS-10'> from Anomalies::ifa_389 to SSD_FMX_ORB_001::FunctionalFailureModes::fmx_dps_10;
    #ObservedAs dependency <'IFA-389>FMX-DPS-12'> from Anomalies::ifa_389 to SSD_FMX_ORB_001::FunctionalFailureModes::fmx_dps_12;
}
