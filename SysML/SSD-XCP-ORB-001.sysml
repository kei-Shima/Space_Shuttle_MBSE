// SysML v2 テキスト：延長能力定義書（着陸時の反応剤の残りで延長できた時間と平均電力）
// SSD-XCP-ORB-001 延長能力定義書（着陸時の反応剤の残りで延長できた時間と平均電力） の表から生成（lib/build_docs_df.py・rev_df/xcpdata.py）。根拠の頁は SSD-XCP-ORB-001 にある。
package SSD_XCP_ORB_001 {
    doc /* SSD-XCP-ORB-001 延長能力定義書（着陸時の反応剤の残りで延長できた時間と平均電力）。飛行ごとの延長能力を part def ExtensionCapability の使用として持つ。時間・電力・電力の種類・延長日の値・エネルギー（計算）・数え方は属性。要求への関係（導出・充足・検証）は張らず、トレースの外に置く。 */
    private import ScalarValues::*;
    part def ExtensionCapability {
        doc /* 着陸時の反応剤の残りで延長できた時間（その飛行の着陸時点の能力。将来の飛行の予測ではない）。時間・電力は本文のとおり。エネルギーは時間×電力の本書の計算 */
        attribute flightName : String;
        attribute launchDate : String;
        attribute extensionHours : ScalarValues::Real [0..1];
        attribute powerKw : ScalarValues::Real [0..1];
        attribute powerBasis : String;
        attribute missionAvgKw : ScalarValues::Real [0..1];
        attribute extDayHours : ScalarValues::Real [0..1];
        attribute extDayKw : ScalarValues::Real [0..1];
        attribute energyKwh : ScalarValues::Real [0..1];
        attribute isCounted : ScalarValues::Boolean;
    }
    part <'XCP-001'> xcp_001 : ExtensionCapability { doc /* STS-27 */ :>> flightName = "STS-27"; :>> launchDate = "1988-12-02"; :>> extensionHours = 92.0; :>> powerBasis = "ミッション平均の電力"; :>> missionAvgKw = 14.6; :>> isCounted = true; }
    part <'XCP-002'> xcp_002 : ExtensionCapability { doc /* STS-28 */ :>> flightName = "STS-28"; :>> launchDate = "1989-08-08"; :>> extensionHours = 90.0; :>> powerBasis = "ミッション平均の電力"; :>> isCounted = true; }
    part <'XCP-003'> xcp_003 : ExtensionCapability { doc /* STS-31 */ :>> flightName = "STS-31"; :>> launchDate = "1990-04-24"; :>> extensionHours = 90.6; :>> powerBasis = "ミッション平均の電力"; :>> missionAvgKw = 14.4; :>> isCounted = true; }
    part <'XCP-004'> xcp_004 : ExtensionCapability { doc /* STS-32 */ :>> flightName = "STS-32"; :>> launchDate = "1990-01-09"; :>> extensionHours = 97.0; :>> powerKw = 13.7; :>> powerBasis = "ミッション平均の電力"; :>> missionAvgKw = 13.7; :>> energyKwh = 1328.9; :>> isCounted = true; }
    part <'XCP-005'> xcp_005 : ExtensionCapability { doc /* STS-33 */ :>> flightName = "STS-33"; :>> launchDate = ""; :>> extensionHours = 99.0; :>> powerBasis = "ミッション平均の電力"; :>> missionAvgKw = 13.6; :>> isCounted = true; }
    part <'XCP-006'> xcp_006 : ExtensionCapability { doc /* STS-34 */ :>> flightName = "STS-34"; :>> launchDate = "1989-10-18"; :>> extensionHours = 72.8; :>> powerKw = 13.6; :>> powerBasis = "電力の語なし"; :>> missionAvgKw = 13.6; :>> energyKwh = 990.1; :>> isCounted = true; }
    part <'XCP-007'> xcp_007 : ExtensionCapability { doc /* STS-35 */ :>> flightName = "STS-35"; :>> launchDate = "1990-12-02"; :>> extensionHours = 72.0; :>> powerBasis = "電力の語なし"; :>> missionAvgKw = 16.8; :>> isCounted = true; }
    part <'XCP-008'> xcp_008 : ExtensionCapability { doc /* STS-36 */ :>> flightName = "STS-36"; :>> launchDate = "1990-02-28"; :>> extensionHours = 70.0; :>> powerBasis = "ミッション平均の電力"; :>> missionAvgKw = 13.6; :>> isCounted = true; }
    part <'XCP-009'> xcp_009 : ExtensionCapability { doc /* STS-38 */ :>> flightName = "STS-38"; :>> launchDate = "1990-11-15"; :>> extensionHours = 79.0; :>> powerBasis = "ミッション平均の電力"; :>> missionAvgKw = 13.3; :>> isCounted = true; }
    part <'XCP-010'> xcp_010 : ExtensionCapability { doc /* STS-39 */ :>> flightName = "STS-39"; :>> launchDate = "1991-04-28"; :>> extensionHours = 63.0; :>> powerKw = 15.4; :>> powerBasis = "電力の語なし"; :>> energyKwh = 970.2; :>> isCounted = true; }
    part <'XCP-011'> xcp_011 : ExtensionCapability { doc /* STS-40 */ :>> flightName = "STS-40"; :>> launchDate = "1991-06-05"; :>> extensionHours = 73.0; :>> powerKw = 17.0; :>> powerBasis = "電力の語なし"; :>> energyKwh = 1241.0; :>> isCounted = true; }
    part <'XCP-012'> xcp_012 : ExtensionCapability { doc /* STS-41 */ :>> flightName = "STS-41"; :>> launchDate = ""; :>> extensionHours = 100.0; :>> powerBasis = "ミッション平均の電力"; :>> missionAvgKw = 15.3; :>> isCounted = true; }
    part <'XCP-013'> xcp_013 : ExtensionCapability { doc /* STS-42 */ :>> flightName = "STS-42"; :>> launchDate = "1992-01-22"; :>> extensionHours = 31.0; :>> powerKw = 17.2; :>> powerBasis = "ミッション平均の電力"; :>> missionAvgKw = 17.2; :>> energyKwh = 533.2; :>> isCounted = true; }
    part <'XCP-014'> xcp_014 : ExtensionCapability { doc /* STS-44 */ :>> flightName = "STS-44"; :>> launchDate = "1991-11-24"; :>> extensionHours = 154.0; :>> powerKw = 12.8; :>> powerBasis = "ミッション平均の電力"; :>> missionAvgKw = 12.8; :>> energyKwh = 1971.2; :>> isCounted = true; }
    part <'XCP-015'> xcp_015 : ExtensionCapability { doc /* STS-45 */ :>> flightName = "STS-45"; :>> launchDate = "1992-03-24"; :>> extensionHours = 31.0; :>> powerKw = 15.8; :>> powerBasis = "ミッション平均の電力"; :>> missionAvgKw = 15.8; :>> energyKwh = 489.8; :>> isCounted = true; }
    part <'XCP-016'> xcp_016 : ExtensionCapability { doc /* STS-48 */ :>> flightName = "STS-48"; :>> launchDate = "1991-09-12"; :>> extensionHours = 74.0; :>> powerKw = 14.7; :>> powerBasis = "電力の語なし"; :>> missionAvgKw = 14.7; :>> energyKwh = 1087.8; :>> isCounted = true; }
    part <'XCP-017'> xcp_017 : ExtensionCapability { doc /* STS-49 */ :>> flightName = "STS-49"; :>> launchDate = "1992-05-07"; :>> extensionHours = 87.6; :>> powerBasis = "ミッション平均の電力"; :>> missionAvgKw = 13.49; :>> isCounted = true; }
    part <'XCP-018'> xcp_018 : ExtensionCapability { doc /* STS-50 */ :>> flightName = "STS-50"; :>> launchDate = "1992-06-25"; :>> extensionHours = 56.0; :>> powerBasis = "電力の語なし"; :>> missionAvgKw = 18.7; :>> isCounted = true; }
    part <'XCP-019'> xcp_019 : ExtensionCapability { doc /* STS-51 */ :>> flightName = "STS-51"; :>> launchDate = "1993-09-12"; :>> extensionHours = 60.0; :>> powerKw = 13.8; :>> powerBasis = "ミッション平均の電力"; :>> missionAvgKw = 13.8; :>> energyKwh = 828.0; :>> isCounted = true; }
    part <'XCP-020'> xcp_020 : ExtensionCapability { doc /* STS-52 */ :>> flightName = "STS-52"; :>> launchDate = "1992-10-22"; :>> extensionHours = 107.9; :>> powerKw = 14.83; :>> powerBasis = "ミッション平均の電力"; :>> missionAvgKw = 14.83; :>> energyKwh = 1600.2; :>> isCounted = true; }
    part <'XCP-021'> xcp_021 : ExtensionCapability { doc /* STS-53 */ :>> flightName = "STS-53"; :>> launchDate = "1992-12-02"; :>> extensionHours = 83.1; :>> powerBasis = "ミッション平均の電力"; :>> missionAvgKw = 13.6; :>> isCounted = true; }
    part <'XCP-022'> xcp_022 : ExtensionCapability { doc /* STS-54 */ :>> flightName = "STS-54"; :>> launchDate = "1993-01-13"; :>> extensionHours = 111.5; :>> powerBasis = "ミッション平均の電力"; :>> isCounted = true; }
    part <'XCP-023'> xcp_023 : ExtensionCapability { doc /* STS-56 */ :>> flightName = "STS-56"; :>> launchDate = "1993-04-08"; :>> extensionHours = 29.1; :>> powerKw = 15.7; :>> powerBasis = "ミッション平均の電力"; :>> energyKwh = 456.9; :>> isCounted = true; }
    part <'XCP-024'> xcp_024 : ExtensionCapability { doc /* STS-57 */ :>> flightName = "STS-57"; :>> launchDate = "1993-06-21"; :>> extensionHours = 24.0; :>> powerKw = 14.7; :>> powerBasis = "電力の語なし"; :>> missionAvgKw = 14.7; :>> energyKwh = 352.8; :>> isCounted = true; }
    part <'XCP-025'> xcp_025 : ExtensionCapability { doc /* STS-60 */ :>> flightName = "STS-60"; :>> launchDate = "1994-02-03"; :>> extensionHours = 65.0; :>> powerKw = 15.2; :>> powerBasis = "ミッション平均の電力"; :>> missionAvgKw = 15.2; :>> energyKwh = 988.0; :>> isCounted = true; }
    part <'XCP-026'> xcp_026 : ExtensionCapability { doc /* STS-61 */ :>> flightName = "STS-61"; :>> launchDate = "1993-12-02"; :>> extensionHours = 94.0; :>> powerKw = 14.1; :>> powerBasis = "ミッション平均の電力"; :>> missionAvgKw = 14.1; :>> energyKwh = 1325.4; :>> isCounted = true; }
    part <'XCP-027'> xcp_027 : ExtensionCapability { doc /* STS-62 */ :>> flightName = "STS-62"; :>> launchDate = "1994-03-04"; :>> extensionHours = 155.0; :>> powerKw = 16.1; :>> powerBasis = "電力の語なし"; :>> extDayHours = 229.0; :>> extDayKw = 11.1; :>> energyKwh = 2495.5; :>> isCounted = true; }
    part <'XCP-028'> xcp_028 : ExtensionCapability { doc /* STS-63 */ :>> flightName = "STS-63"; :>> launchDate = "1995-02-03"; :>> extensionHours = 54.0; :>> powerKw = 15.8; :>> powerBasis = "ミッション平均の電力"; :>> missionAvgKw = 15.8; :>> extDayHours = 78.0; :>> extDayKw = 11.1; :>> energyKwh = 853.2; :>> isCounted = true; }
    part <'XCP-029'> xcp_029 : ExtensionCapability { doc /* STS-64 */ :>> flightName = "STS-64"; :>> launchDate = ""; :>> extensionHours = 33.0; :>> powerKw = 13.9; :>> powerBasis = "ミッション平均の電力"; :>> missionAvgKw = 13.9; :>> energyKwh = 458.7; :>> isCounted = true; }
    part <'XCP-030'> xcp_030 : ExtensionCapability { doc /* STS-65 */ :>> flightName = "STS-65"; :>> launchDate = "1994-07-08"; :>> extensionHours = 47.0; :>> powerKw = 18.8; :>> powerBasis = "ミッション平均の電力"; :>> missionAvgKw = 18.8; :>> energyKwh = 883.6; :>> isCounted = true; }
    part <'XCP-031'> xcp_031 : ExtensionCapability { doc /* STS-66 */ :>> flightName = "STS-66"; :>> launchDate = "1994-11-03"; :>> extensionHours = 61.0; :>> powerKw = 15.9; :>> powerBasis = "ミッション平均の電力"; :>> missionAvgKw = 15.9; :>> energyKwh = 969.9; :>> isCounted = true; }
    part <'XCP-032'> xcp_032 : ExtensionCapability { doc /* STS-67 */ :>> flightName = "STS-67"; :>> launchDate = "1995-03-02"; :>> extensionHours = 97.0; :>> powerKw = 18.1; :>> powerBasis = "ミッション平均の電力"; :>> missionAvgKw = 18.1; :>> energyKwh = 1755.7; :>> isCounted = true; }
    part <'XCP-033'> xcp_033 : ExtensionCapability { doc /* STS-68 */ :>> flightName = "STS-68"; :>> launchDate = "1994-09-30"; :>> extensionHours = 54.0; :>> powerKw = 15.8; :>> powerBasis = "ミッション平均の電力"; :>> missionAvgKw = 15.8; :>> energyKwh = 853.2; :>> isCounted = true; }
    part <'XCP-034'> xcp_034 : ExtensionCapability { doc /* STS-69 */ :>> flightName = "STS-69"; :>> launchDate = "1995-09-07"; :>> extensionHours = 81.0; :>> powerKw = 14.9; :>> powerBasis = "ミッション平均の電力"; :>> missionAvgKw = 14.9; :>> energyKwh = 1206.9; :>> isCounted = true; }
    part <'XCP-035'> xcp_035 : ExtensionCapability { doc /* STS-70 */ :>> flightName = "STS-70"; :>> launchDate = ""; :>> extensionHours = 55.0; :>> powerKw = 13.1; :>> powerBasis = "ミッション平均の電力"; :>> missionAvgKw = 13.1; :>> energyKwh = 720.5; :>> isCounted = true; }
    part <'XCP-036'> xcp_036 : ExtensionCapability { doc /* STS-71 */ :>> flightName = "STS-71"; :>> launchDate = "1995-06-27"; :>> extensionHours = 65.0; :>> powerKw = 16.7; :>> powerBasis = "ミッション平均の電力"; :>> missionAvgKw = 16.7; :>> energyKwh = 1085.5; :>> isCounted = true; }
    part <'XCP-037'> xcp_037 : ExtensionCapability { doc /* STS-72 */ :>> flightName = "STS-72"; :>> launchDate = "1996-01-11"; :>> extensionHours = 148.0; :>> powerKw = 13.8; :>> powerBasis = "ミッション平均の電力"; :>> missionAvgKw = 13.8; :>> energyKwh = 2042.4; :>> isCounted = true; }
    part <'XCP-038'> xcp_038 : ExtensionCapability { doc /* STS-73 */ :>> flightName = "STS-73"; :>> launchDate = "1995-10-20"; :>> extensionHours = 70.0; :>> powerKw = 19.5; :>> powerBasis = "ミッション平均の電力"; :>> missionAvgKw = 19.5; :>> energyKwh = 1365.0; :>> isCounted = true; }
    part <'XCP-039'> xcp_039 : ExtensionCapability { doc /* STS-74 */ :>> flightName = "STS-74"; :>> launchDate = "1995-11-12"; :>> extensionHours = 116.0; :>> powerKw = 15.9; :>> powerBasis = "ミッション平均の電力"; :>> energyKwh = 1844.4; :>> isCounted = true; }
    part <'XCP-040'> xcp_040 : ExtensionCapability { doc /* STS-75 */ :>> flightName = "STS-75"; :>> launchDate = "1996-02-22"; :>> extensionHours = 94.0; :>> powerBasis = "電力の語なし"; :>> missionAvgKw = 16.7; :>> isCounted = true; }
    part <'XCP-041'> xcp_041 : ExtensionCapability { doc /* STS-76 */ :>> flightName = "STS-76"; :>> launchDate = "1996-03-22"; :>> extensionHours = 89.0; :>> powerBasis = "ミッション平均の電力"; :>> missionAvgKw = 15.9; :>> extDayHours = 125.0; :>> extDayKw = 11.1; :>> isCounted = true; }
    part <'XCP-042'> xcp_042 : ExtensionCapability { doc /* STS-77 */ :>> flightName = "STS-77"; :>> launchDate = "1996-05-19"; :>> extensionHours = 67.0; :>> powerBasis = "ミッション平均の電力"; :>> missionAvgKw = 16.3; :>> extDayHours = 98.0; :>> extDayKw = 11.1; :>> isCounted = true; }
    part <'XCP-043'> xcp_043 : ExtensionCapability { doc /* STS-78 */ :>> flightName = "STS-78"; :>> launchDate = "1996-06-20"; :>> extensionHours = 68.0; :>> powerKw = 18.9; :>> powerBasis = "ミッション平均の電力"; :>> missionAvgKw = 18.9; :>> extDayHours = 97.0; :>> extDayKw = 13.5; :>> energyKwh = 1285.2; :>> isCounted = true; }
    part <'XCP-044'> xcp_044 : ExtensionCapability { doc /* STS-80 */ :>> flightName = "STS-80"; :>> launchDate = "1996-11-19"; :>> extensionHours = 155.0; :>> powerBasis = "ミッション平均の電力"; :>> missionAvgKw = 13.8; :>> extDayHours = 182.0; :>> extDayKw = 11.8; :>> isCounted = true; }
    part <'XCP-045'> xcp_045 : ExtensionCapability { doc /* STS-82 */ :>> flightName = "STS-82"; :>> launchDate = "1997-02-11"; :>> extensionHours = 51.0; :>> powerKw = 15.3; :>> powerBasis = "ミッション平均の電力"; :>> missionAvgKw = 15.3; :>> extDayHours = 66.0; :>> extDayKw = 11.8; :>> energyKwh = 780.3; :>> isCounted = true; }
    part <'XCP-046'> xcp_046 : ExtensionCapability { doc /* STS-83 */ :>> flightName = "STS-83"; :>> launchDate = "1997-04-04"; :>> powerBasis = "延長日の電力"; :>> missionAvgKw = 17.9; :>> extDayHours = 570.0; :>> extDayKw = 13.1; :>> isCounted = false; }
    part <'XCP-047'> xcp_047 : ExtensionCapability { doc /* STS-84 */ :>> flightName = "STS-84"; :>> launchDate = "1997-05-15"; :>> powerBasis = "延長日の電力"; :>> missionAvgKw = 16.0; :>> extDayHours = 114.0; :>> isCounted = false; }
    part <'XCP-048'> xcp_048 : ExtensionCapability { doc /* STS-85 */ :>> flightName = "STS-85"; :>> launchDate = "1997-08-07"; :>> extensionHours = 56.0; :>> powerKw = 15.1; :>> powerBasis = "ミッション平均の電力"; :>> missionAvgKw = 15.1; :>> extDayHours = 58.0; :>> energyKwh = 845.6; :>> isCounted = true; }
    part <'XCP-049'> xcp_049 : ExtensionCapability { doc /* STS-87 */ :>> flightName = "STS-87"; :>> launchDate = "1997-11-19"; :>> extensionHours = 174.0; :>> powerBasis = "ミッション平均の電力"; :>> missionAvgKw = 16.5; :>> extDayHours = 229.0; :>> extDayKw = 12.7; :>> isCounted = true; }
    part <'XCP-050'> xcp_050 : ExtensionCapability { doc /* STS-88 */ :>> flightName = "STS-88"; :>> launchDate = "1998-12-04"; :>> extensionHours = 51.0; :>> powerKw = 14.2; :>> powerBasis = "ミッション平均の電力"; :>> missionAvgKw = 14.2; :>> extDayHours = 62.0; :>> extDayKw = 11.7; :>> energyKwh = 724.2; :>> isCounted = true; }
    part <'XCP-051'> xcp_051 : ExtensionCapability { doc /* STS-89 */ :>> flightName = "STS-89"; :>> launchDate = "1998-01-22"; :>> extensionHours = 83.0; :>> powerBasis = "ミッション平均の電力"; :>> missionAvgKw = 15.7; :>> extDayHours = 98.0; :>> extDayKw = 13.2; :>> isCounted = true; }
    part <'XCP-052'> xcp_052 : ExtensionCapability { doc /* STS-90 */ :>> flightName = "STS-90"; :>> launchDate = ""; :>> extensionHours = 102.0; :>> powerBasis = "ミッション平均の電力"; :>> missionAvgKw = 18.0; :>> extDayHours = 143.0; :>> extDayKw = 13.2; :>> isCounted = true; }
    part <'XCP-053'> xcp_053 : ExtensionCapability { doc /* STS-91 */ :>> flightName = "STS-91"; :>> launchDate = ""; :>> extensionHours = 66.0; :>> powerBasis = "ミッション平均の電力"; :>> missionAvgKw = 16.7; :>> extDayHours = 83.0; :>> extDayKw = 13.2; :>> isCounted = true; }
    part <'XCP-054'> xcp_054 : ExtensionCapability { doc /* STS-92 */ :>> flightName = "STS-92"; :>> launchDate = "2000-10-11"; :>> extensionHours = 49.0; :>> powerKw = 13.9; :>> powerBasis = "ミッション平均の電力"; :>> missionAvgKw = 14.8; :>> extDayHours = 55.0; :>> extDayKw = 12.5; :>> isCounted = false; }
    part <'XCP-055'> xcp_055 : ExtensionCapability { doc /* STS-93 */ :>> flightName = "STS-93"; :>> launchDate = "1999-07-23"; :>> extensionHours = 76.0; :>> powerBasis = "ミッション平均の電力"; :>> missionAvgKw = 12.9; :>> isCounted = true; }
    part <'XCP-056'> xcp_056 : ExtensionCapability { doc /* STS-94 */ :>> flightName = "STS-94"; :>> launchDate = ""; :>> powerBasis = "延長日の電力"; :>> missionAvgKw = 20.2; :>> extDayHours = 111.0; :>> isCounted = false; }
    part <'XCP-057'> xcp_057 : ExtensionCapability { doc /* STS-95 */ :>> flightName = "STS-95"; :>> launchDate = "1998-10-29"; :>> extensionHours = 68.0; :>> powerKw = 17.9; :>> powerBasis = "ミッション平均の電力"; :>> missionAvgKw = 17.9; :>> extDayHours = 94.0; :>> extDayKw = 13.2; :>> energyKwh = 1217.2; :>> isCounted = true; }
    part <'XCP-058'> xcp_058 : ExtensionCapability { doc /* STS-96 */ :>> flightName = "STS-96"; :>> launchDate = "1999-05-27"; :>> extensionHours = 92.0; :>> powerKw = 15.5; :>> powerBasis = "ミッション平均の電力"; :>> missionAvgKw = 14.2; :>> extDayHours = 107.0; :>> extDayKw = 13.2; :>> isCounted = false; }
    part <'XCP-059'> xcp_059 : ExtensionCapability { doc /* STS-97 */ :>> flightName = "STS-97"; :>> launchDate = "2000-11-30"; :>> extensionHours = 113.0; :>> powerKw = 13.3; :>> powerBasis = "ミッション平均の電力"; :>> missionAvgKw = 13.3; :>> extDayHours = 123.0; :>> extDayKw = 12.5; :>> energyKwh = 1502.9; :>> isCounted = true; }
    part <'XCP-060'> xcp_060 : ExtensionCapability { doc /* STS-98 */ :>> flightName = "STS-98"; :>> launchDate = "2001-02-07"; :>> extensionHours = 47.0; :>> powerKw = 14.2; :>> powerBasis = "ミッション平均の電力"; :>> missionAvgKw = 14.1; :>> extDayHours = 55.0; :>> extDayKw = 12.1; :>> energyKwh = 667.4; :>> isCounted = true; }
    part <'XCP-061'> xcp_061 : ExtensionCapability { doc /* STS-99 */ :>> flightName = "STS-99"; :>> launchDate = "2000-02-11"; :>> extensionHours = 45.0; :>> powerKw = 16.2; :>> powerBasis = "ミッション平均の電力"; :>> missionAvgKw = 16.2; :>> extDayHours = 63.0; :>> extDayKw = 11.7; :>> energyKwh = 729.0; :>> isCounted = true; }
    part <'XCP-062'> xcp_062 : ExtensionCapability { doc /* STS-100 */ :>> flightName = "STS-100"; :>> launchDate = "2001-04-19"; :>> extensionHours = 88.0; :>> powerKw = 13.5; :>> powerBasis = "ミッション平均の電力"; :>> missionAvgKw = 13.5; :>> extDayHours = 92.0; :>> extDayKw = 12.9; :>> energyKwh = 1188.0; :>> isCounted = true; }
    part <'XCP-063'> xcp_063 : ExtensionCapability { doc /* STS-101 */ :>> flightName = "STS-101"; :>> launchDate = "2000-05-19"; :>> extensionHours = 79.0; :>> powerKw = 15.9; :>> powerBasis = "ミッション平均の電力"; :>> missionAvgKw = 15.9; :>> extDayHours = 97.0; :>> extDayKw = 12.9; :>> energyKwh = 1256.1; :>> isCounted = true; }
    part <'XCP-064'> xcp_064 : ExtensionCapability { doc /* STS-102 */ :>> flightName = "STS-102"; :>> launchDate = "2001-03-08"; :>> extensionHours = 54.0; :>> powerKw = 13.8; :>> powerBasis = "ミッション平均の電力"; :>> missionAvgKw = 13.8; :>> extDayHours = 60.0; :>> extDayKw = 12.1; :>> energyKwh = 745.2; :>> isCounted = true; }
    part <'XCP-065'> xcp_065 : ExtensionCapability { doc /* STS-103 */ :>> flightName = "STS-103"; :>> launchDate = "1999-12-19"; :>> extensionHours = 122.0; :>> powerKw = 15.6; :>> powerBasis = "ミッション平均の電力"; :>> missionAvgKw = 15.6; :>> extDayHours = 144.0; :>> extDayKw = 13.2; :>> energyKwh = 1903.2; :>> isCounted = true; }
    part <'XCP-066'> xcp_066 : ExtensionCapability { doc /* STS-104 */ :>> flightName = "STS-104"; :>> launchDate = "2001-07-12"; :>> extensionHours = 61.0; :>> powerKw = 13.9; :>> powerBasis = "ミッション平均の電力"; :>> missionAvgKw = 13.9; :>> extDayHours = 68.0; :>> extDayKw = 12.3; :>> energyKwh = 847.9; :>> isCounted = true; }
    part <'XCP-067'> xcp_067 : ExtensionCapability { doc /* STS-105 */ :>> flightName = "STS-105"; :>> launchDate = "2001-08-10"; :>> extensionHours = 73.0; :>> powerKw = 13.9; :>> powerBasis = "ミッション平均の電力"; :>> missionAvgKw = 13.9; :>> extDayHours = 82.0; :>> extDayKw = 12.4; :>> energyKwh = 1014.7; :>> isCounted = true; }
    part <'XCP-068'> xcp_068 : ExtensionCapability { doc /* STS-106 */ :>> flightName = "STS-106"; :>> launchDate = "2000-09-08"; :>> extensionHours = 57.0; :>> powerKw = 14.8; :>> powerBasis = "ミッション平均の電力"; :>> missionAvgKw = 14.8; :>> extDayHours = 64.0; :>> extDayKw = 13.2; :>> energyKwh = 843.6; :>> isCounted = true; }
    part <'XCP-069'> xcp_069 : ExtensionCapability { doc /* STS-108 */ :>> flightName = "STS-108"; :>> launchDate = "2001-12-05"; :>> extensionHours = 78.0; :>> powerKw = 13.8; :>> powerBasis = "ミッション平均の電力"; :>> missionAvgKw = 13.8; :>> energyKwh = 1076.4; :>> isCounted = true; }
    part <'XCP-070'> xcp_070 : ExtensionCapability { doc /* STS-109 */ :>> flightName = "STS-109"; :>> launchDate = "2002-03-01"; :>> extensionHours = 76.0; :>> powerKw = 14.7; :>> powerBasis = "ミッション平均の電力"; :>> missionAvgKw = 14.7; :>> extDayHours = 92.0; :>> extDayKw = 12.1; :>> energyKwh = 1117.2; :>> isCounted = true; }
    part <'XCP-071'> xcp_071 : ExtensionCapability { doc /* STS-110 */ :>> flightName = "STS-110"; :>> launchDate = "2002-04-08"; :>> extensionHours = 103.0; :>> powerKw = 13.6; :>> powerBasis = "ミッション平均の電力"; :>> missionAvgKw = 13.6; :>> extDayHours = 113.0; :>> extDayKw = 12.1; :>> energyKwh = 1400.8; :>> isCounted = true; }
    part <'XCP-072'> xcp_072 : ExtensionCapability { doc /* STS-111 */ :>> flightName = "STS-111"; :>> launchDate = "2002-06-05"; :>> extensionHours = 42.0; :>> powerKw = 13.6; :>> powerBasis = "ミッション平均の電力"; :>> missionAvgKw = 13.6; :>> extDayHours = 43.0; :>> extDayKw = 13.4; :>> energyKwh = 571.2; :>> isCounted = true; }
    part <'XCP-073'> xcp_073 : ExtensionCapability { doc /* STS-112 */ :>> flightName = "STS-112"; :>> launchDate = "2002-10-07"; :>> extensionHours = 118.0; :>> powerKw = 13.4; :>> powerBasis = "ミッション平均の電力"; :>> missionAvgKw = 13.4; :>> extDayHours = 123.0; :>> extDayKw = 12.9; :>> energyKwh = 1581.2; :>> isCounted = true; }
    part <'XCP-074'> xcp_074 : ExtensionCapability { doc /* STS-113 */ :>> flightName = "STS-113"; :>> launchDate = "2002-11-23"; :>> extensionHours = 51.0; :>> powerBasis = "ミッション平均の電力"; :>> missionAvgKw = 13.0; :>> extDayHours = 50.0; :>> extDayKw = 13.3; :>> isCounted = true; }
    part <'XCP-075'> xcp_075 : ExtensionCapability { doc /* STS-114 */ :>> flightName = "STS-114"; :>> launchDate = "2005-07-26"; :>> extensionHours = 36.0; :>> powerKw = 13.6; :>> powerBasis = "ミッション平均の電力"; :>> missionAvgKw = 13.6; :>> energyKwh = 489.6; :>> isCounted = true; }
    part <'XCP-076'> xcp_076 : ExtensionCapability { doc /* STS-115 */ :>> flightName = "STS-115"; :>> launchDate = "2006-09-09"; :>> extensionHours = 71.0; :>> powerKw = 13.5; :>> powerBasis = "ミッション平均の電力"; :>> missionAvgKw = 13.5; :>> extDayHours = 76.0; :>> extDayKw = 12.48; :>> energyKwh = 958.5; :>> isCounted = true; }
    part <'XCP-077'> xcp_077 : ExtensionCapability { doc /* STS-116 */ :>> flightName = "STS-116"; :>> launchDate = "2006-12-09"; :>> extensionHours = 33.0; :>> powerKw = 14.2; :>> powerBasis = "ミッション平均の電力"; :>> missionAvgKw = 14.2; :>> extDayHours = 35.0; :>> extDayKw = 13.491; :>> energyKwh = 468.6; :>> isCounted = true; }
    part <'XCP-078'> xcp_078 : ExtensionCapability { doc /* STS-117 */ :>> flightName = "STS-117"; :>> launchDate = "2007-06-08"; :>> extensionHours = 52.0; :>> powerKw = 12.8; :>> powerBasis = "ミッション平均の電力"; :>> missionAvgKw = 12.8; :>> extDayHours = 53.0; :>> extDayKw = 12.501; :>> energyKwh = 665.6; :>> isCounted = true; }
    part <'XCP-079'> xcp_079 : ExtensionCapability { doc /* STS-118 */ :>> flightName = "STS-118"; :>> launchDate = "2007-08-08"; :>> extensionHours = 170.0; :>> powerKw = 10.0; :>> powerBasis = "ミッション平均の電力"; :>> missionAvgKw = 10.0; :>> extDayHours = 131.0; :>> extDayKw = 13.45; :>> energyKwh = 1700.0; :>> isCounted = true; }
    part <'XCP-080'> xcp_080 : ExtensionCapability { doc /* STS-119 */ :>> flightName = "STS-119"; :>> launchDate = "2009-03-15"; :>> extensionHours = 111.0; :>> powerKw = 10.6; :>> powerBasis = "ミッション平均の電力"; :>> missionAvgKw = 10.6; :>> extDayHours = 95.0; :>> extDayKw = 12.47; :>> energyKwh = 1176.6; :>> isCounted = true; }
    part <'XCP-081'> xcp_081 : ExtensionCapability { doc /* STS-120 */ :>> flightName = "STS-120"; :>> launchDate = "2007-10-23"; :>> extensionHours = 133.0; :>> powerKw = 10.24; :>> powerBasis = "ミッション平均の電力"; :>> missionAvgKw = 10.24; :>> extDayHours = 109.0; :>> extDayKw = 12.524; :>> energyKwh = 1361.9; :>> isCounted = true; }
    part <'XCP-082'> xcp_082 : ExtensionCapability { doc /* STS-121 */ :>> flightName = "STS-121"; :>> launchDate = "2006-07-04"; :>> extensionHours = 57.0; :>> powerKw = 13.6; :>> powerBasis = "ミッション平均の電力"; :>> missionAvgKw = 13.6; :>> extDayHours = 60.0; :>> extDayKw = 12.98; :>> energyKwh = 775.2; :>> isCounted = true; }
    part <'XCP-083'> xcp_083 : ExtensionCapability { doc /* STS-122 */ :>> flightName = "STS-122"; :>> launchDate = "2008-02-07"; :>> extensionHours = 57.0; :>> powerKw = 13.5; :>> powerBasis = "ミッション平均の電力"; :>> missionAvgKw = 13.5; :>> energyKwh = 769.5; :>> isCounted = true; }
    part <'XCP-084'> xcp_084 : ExtensionCapability { doc /* STS-123 */ :>> flightName = "STS-123"; :>> launchDate = "2008-03-11"; :>> extensionHours = 117.0; :>> powerKw = 12.46; :>> powerBasis = "ミッション平均の電力"; :>> missionAvgKw = 9.3; :>> isCounted = false; }
    part <'XCP-085'> xcp_085 : ExtensionCapability { doc /* STS-124 */ :>> flightName = "STS-124"; :>> launchDate = "2008-05-31"; :>> extensionHours = 117.0; :>> powerBasis = "ミッション平均の電力"; :>> missionAvgKw = 9.9; :>> isCounted = false; }
    part <'XCP-086'> xcp_086 : ExtensionCapability { doc /* STS-125 */ :>> flightName = "STS-125"; :>> launchDate = "2009-05-11"; :>> extensionHours = 28.0; :>> powerKw = 15.0; :>> powerBasis = "ミッション平均の電力"; :>> missionAvgKw = 15.0; :>> extDayHours = 32.0; :>> extDayKw = 12.88; :>> energyKwh = 420.0; :>> isCounted = true; }
    part <'XCP-087'> xcp_087 : ExtensionCapability { doc /* STS-126 */ :>> flightName = "STS-126"; :>> launchDate = "2008-11-14"; :>> extensionHours = 106.0; :>> powerKw = 12.24; :>> powerBasis = "ミッション平均の電力"; :>> missionAvgKw = 9.5; :>> isCounted = false; }
    part <'XCP-088'> xcp_088 : ExtensionCapability { doc /* STS-127 */ :>> flightName = "STS-127"; :>> launchDate = "2009-07-15"; :>> extensionHours = 101.0; :>> powerKw = 9.6; :>> powerBasis = "ミッション平均の電力"; :>> missionAvgKw = 9.6; :>> energyKwh = 969.6; :>> isCounted = true; }
    part <'XCP-089'> xcp_089 : ExtensionCapability { doc /* STS-128 */ :>> flightName = "STS-128"; :>> launchDate = "2009-08-28"; :>> extensionHours = 100.0; :>> powerKw = 9.6; :>> powerBasis = "ミッション平均の電力"; :>> energyKwh = 960.0; :>> isCounted = true; }
    part <'XCP-090'> xcp_090 : ExtensionCapability { doc /* STS-129 */ :>> flightName = "STS-129"; :>> launchDate = "2009-11-16"; :>> extensionHours = 99.0; :>> powerKw = 12.68; :>> powerBasis = "ミッション平均の電力"; :>> missionAvgKw = 14.2; :>> isCounted = false; }
    part <'XCP-091'> xcp_091 : ExtensionCapability { doc /* STS-130 */ :>> flightName = "STS-130"; :>> launchDate = "2010-02-08"; :>> extensionHours = 95.0; :>> powerKw = 9.2; :>> powerBasis = "延長（mission extension）の平均電力"; :>> missionAvgKw = 9.2; :>> energyKwh = 874.0; :>> isCounted = true; }
    part <'XCP-092'> xcp_092 : ExtensionCapability { doc /* STS-131 */ :>> flightName = "STS-131"; :>> launchDate = "2010-04-05"; :>> extensionHours = 46.0; :>> powerKw = 13.09; :>> powerBasis = "延長（mission extension）の平均電力"; :>> missionAvgKw = 9.1; :>> isCounted = false; }
    part <'XCP-093'> xcp_093 : ExtensionCapability { doc /* STS-132 */ :>> flightName = "STS-132"; :>> launchDate = "2010-05-14"; :>> extensionHours = 75.0; :>> powerKw = 13.8; :>> powerBasis = "ミッション平均の電力"; :>> missionAvgKw = 13.8; :>> energyKwh = 1035.0; :>> isCounted = true; }
    part <'XCP-094'> xcp_094 : ExtensionCapability { doc /* STS-133 */ :>> flightName = "STS-133"; :>> launchDate = "2011-02-24"; :>> extensionHours = 59.0; :>> powerKw = 12.72; :>> powerBasis = "延長（mission extension）の平均電力"; :>> missionAvgKw = 9.1; :>> isCounted = false; }
    part <'XCP-095'> xcp_095 : ExtensionCapability { doc /* STS-134 */ :>> flightName = "STS-134"; :>> launchDate = "2011-05-16"; :>> extensionHours = 142.0; :>> powerKw = 9.0; :>> powerBasis = "ミッション平均の電力"; :>> missionAvgKw = 9.0; :>> energyKwh = 1278.0; :>> isCounted = true; }
    part <'XCP-096'> xcp_096 : ExtensionCapability { doc /* STS-135 */ :>> flightName = "STS-135"; :>> launchDate = "2011-07-08"; :>> extensionHours = 71.0; :>> powerKw = 13.6; :>> powerBasis = "ミッション平均の電力"; :>> missionAvgKw = 13.6; :>> energyKwh = 965.6; :>> isCounted = true; }
}
